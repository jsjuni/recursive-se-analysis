package MassPropertiesModelAlt {
    private import ScalarValues::Boolean;
    private import ScalarValues::Real;
    private import ScalarValues::String;
    private import Quantities::VectorQuantityValue;

    attribute def RealWithUncertainty specializes VectorQuantityValue {
        attribute nomVal : ISQSpaceTime::Cx;
        attribute uMass :>> ISQ::mass;
        attribute inertiaTensor :> ISQMechanics::momentOfInertiaTensor;
    }

    part <ex1> ExampleComponent1 {
        attribute redefines ISQ::mass;
        attribute :>> ISQMechanics::cartesian;
    }


    part <'C.1'> 'System 1' {
        attribute POIconv : String = "-";
        attribute mass : Real;
        attribute Cx : Real;
        attribute Cy : Real;
        attribute Cz : Real;
        attribute Ixx : Real;
        attribute Iyy : Real;
        attribute Izz : Real;
        attribute Ixy : Real;
        attribute Ixz : Real;
        attribute Iyz : Real;
        attribute Ipoint : Boolean;
        attribute sigma_mass : Real;
        attribute sigma_Cx : Real;
        attribute sigma_Cy : Real;
        attribute sigma_Cz : Real;
        attribute sigma_Ixx : Real;
        attribute sigma_Iyy : Real;
        attribute sigma_Izz : Real;
        attribute sigma_Ixy : Real;
        attribute sigma_Ixz : Real;
        attribute sigma_Iyz : Real;
        part <'C.1.1'> 'Segment 1' {
            attribute POIconv : String = "-";
            attribute mass : Real;
            attribute Cx : Real;
            attribute Cy : Real;
            attribute Cz : Real;
            attribute Ixx : Real;
            attribute Iyy : Real;
            attribute Izz : Real;
            attribute Ixy : Real;
            attribute Ixz : Real;
            attribute Iyz : Real;
            attribute Ipoint : Boolean;
            attribute sigma_mass : Real;
            attribute sigma_Cx : Real;
            attribute sigma_Cy : Real;
            attribute sigma_Cz : Real;
            attribute sigma_Ixx : Real;
            attribute sigma_Iyy : Real;
            attribute sigma_Izz : Real;
            attribute sigma_Ixy : Real;
            attribute sigma_Ixz : Real;
            attribute sigma_Iyz : Real;
            part <'C.1.1.1'> 'Element 1' {
                attribute POIconv : String = "-";
                attribute mass : Real;
                attribute Cx : Real;
                attribute Cy : Real;
                attribute Cz : Real;
                attribute Ixx : Real;
                attribute Iyy : Real;
                attribute Izz : Real;
                attribute Ixy : Real;
                attribute Ixz : Real;
                attribute Iyz : Real;
                attribute Ipoint : Boolean;
                attribute sigma_mass : Real;
                attribute sigma_Cx : Real;
                attribute sigma_Cy : Real;
                attribute sigma_Cz : Real;
                attribute sigma_Ixx : Real;
                attribute sigma_Iyy : Real;
                attribute sigma_Izz : Real;
                attribute sigma_Ixy : Real;
                attribute sigma_Ixz : Real;
                attribute sigma_Iyz : Real;
                part <'C.1.1.1.1'> 'Subsystem 1' {
                    attribute POIconv : String = "-";
                    attribute mass : Real = 24.1827584303201;
                    attribute Cx : Real = 12.7664845070976;
                    attribute Cy : Real = -7.33521243876906;
                    attribute Cz : Real = 4.25063330363471;
                    attribute Ixx : Real = 151242.290612754;
                    attribute Iyy : Real = 151681.439478395;
                    attribute Izz : Real = 140003.007229201;
                    attribute Ixy : Real = -9285.98126973321;
                    attribute Ixz : Real = 11631.0816003715;
                    attribute Iyz : Real = -3665.04870824325;
                    attribute Ipoint : Boolean = false;
                    attribute sigma_mass : Real = 2.00377872522265;
                    attribute sigma_Cx : Real = 6.71223764331936;
                    attribute sigma_Cy : Real = 6.83524201771795;
                    attribute sigma_Cz : Real = 7.05080865006599;
                    attribute sigma_Ixx : Real = 26174.5823782939;
                    attribute sigma_Iyy : Real = 25990.7093429332;
                    attribute sigma_Izz : Real = 24135.2605993766;
                    attribute sigma_Ixy : Real = 11648.8802649171;
                    attribute sigma_Ixz : Real = 12377.8633308676;
                    attribute sigma_Iyz : Real = 12340.520923051;
                }
                part <'C.1.1.1.2'> 'Subsystem 2' {
                    attribute POIconv : String = "-";
                    attribute mass : Real = 21.0534869896481;
                    attribute Cx : Real = -13.278244712436;
                    attribute Cy : Real = 15.7452897577185;
                    attribute Cz : Real = 0.49965856589574;
                    attribute Ixx : Real = 163041.130259192;
                    attribute Iyy : Real = 143884.885357074;
                    attribute Izz : Real = 154262.950249695;
                    attribute Ixy : Real = 14334.2017923855;
                    attribute Ixz : Real = 1519.83286770808;
                    attribute Iyz : Real = -4317.23007860859;
                    attribute Ipoint : Boolean = false;
                    attribute sigma_mass : Real = 1.80618173461854;
                    attribute sigma_Cx : Real = 7.24618585272687;
                    attribute sigma_Cy : Real = 7.63646182821853;
                    attribute sigma_Cz : Real = 7.96772631674887;
                    attribute sigma_Ixx : Real = 27902.8386989279;
                    attribute sigma_Iyy : Real = 26001.0650978797;
                    attribute sigma_Izz : Real = 24651.8644773092;
                    attribute sigma_Ixy : Real = 11579.897800229;
                    attribute sigma_Ixz : Real = 12231.335670426;
                    attribute sigma_Iyz : Real = 12825.0275336518;
                }
            }
            part <'C.1.1.2'> 'Element 2' {
                attribute POIconv : String = "-";
                attribute mass : Real;
                attribute Cx : Real;
                attribute Cy : Real;
                attribute Cz : Real;
                attribute Ixx : Real;
                attribute Iyy : Real;
                attribute Izz : Real;
                attribute Ixy : Real;
                attribute Ixz : Real;
                attribute Iyz : Real;
                attribute Ipoint : Boolean;
                attribute sigma_mass : Real;
                attribute sigma_Cx : Real;
                attribute sigma_Cy : Real;
                attribute sigma_Cz : Real;
                attribute sigma_Ixx : Real;
                attribute sigma_Iyy : Real;
                attribute sigma_Izz : Real;
                attribute sigma_Ixy : Real;
                attribute sigma_Ixz : Real;
                attribute sigma_Iyz : Real;
                part <'C.1.1.2.1'> 'Subsystem 3' {
                    attribute POIconv : String = "-";
                    attribute mass : Real = 32.614045134943;
                    attribute Cx : Real = -5.41640526884451;
                    attribute Cy : Real = 4.35058525414445;
                    attribute Cz : Real = -8.74231806433935;
                    attribute Ixx : Real = 255264.689655231;
                    attribute Iyy : Real = 233424.833421624;
                    attribute Izz : Real = 236512.403954375;
                    attribute Ixy : Real = -11454.2925733218;
                    attribute Ixz : Real = -37583.6938770667;
                    attribute Iyz : Real = -15618.0800463847;
                    attribute Ipoint : Boolean = false;
                    attribute sigma_mass : Real = 2.33177059280054;
                    attribute sigma_Cx : Real = 5.9992691865799;
                    attribute sigma_Cy : Real = 6.16873535559674;
                    attribute sigma_Cz : Real = 6.32882242913628;
                    attribute sigma_Ixx : Real = 32199.5326825848;
                    attribute sigma_Iyy : Real = 31432.4323943996;
                    attribute sigma_Izz : Real = 31009.1709650888;
                    attribute sigma_Ixy : Real = 14813.6809221377;
                    attribute sigma_Ixz : Real = 14988.3622849736;
                    attribute sigma_Iyz : Real = 15574.4247138159;
                }
                part <'C.1.1.2.2'> 'Subsystem 4' {
                    attribute POIconv : String = "-";
                    attribute mass : Real = 18.4435082934506;
                    attribute Cx : Real = 5.94463144399493;
                    attribute Cy : Real = -2.86799230398103;
                    attribute Cz : Real = 1.0825770208325;
                    attribute Ixx : Real = 134251.663665595;
                    attribute Iyy : Real = 108878.512046098;
                    attribute Izz : Real = 127953.741023779;
                    attribute Ixy : Real = -4491.03996089334;
                    attribute Ixz : Real = -8773.56250397014;
                    attribute Iyz : Real = -12660.6957871391;
                    attribute Ipoint : Boolean = false;
                    attribute sigma_mass : Real = 1.78287518741315;
                    attribute sigma_Cx : Real = 7.44588977488085;
                    attribute sigma_Cy : Real = 8.41032952383461;
                    attribute sigma_Cz : Real = 7.7442616049041;
                    attribute sigma_Ixx : Real = 22518.5893559723;
                    attribute sigma_Iyy : Real = 20353.5865203755;
                    attribute sigma_Izz : Real = 21693.129456637;
                    attribute sigma_Ixy : Real = 10239.1353538824;
                    attribute sigma_Ixz : Real = 9843.48376814182;
                    attribute sigma_Iyz : Real = 10856.0874875075;
                }
                part <'C.1.1.2.3'> 'Subsystem 5' {
                    attribute POIconv : String = "-";
                    attribute mass : Real = 32.854061699698;
                    attribute Cx : Real = 6.63173790653558;
                    attribute Cy : Real = -4.19099753064691;
                    attribute Cz : Real = -10.746496172516;
                    attribute Ixx : Real = 211601.360403857;
                    attribute Iyy : Real = 221873.089049087;
                    attribute Izz : Real = 212043.694406801;
                    attribute Ixy : Real = 16207.5604933788;
                    attribute Ixz : Real = -1864.14304236315;
                    attribute Iyz : Real = 1819.44905460975;
                    attribute Ipoint : Boolean = false;
                    attribute sigma_mass : Real = 2.27732486126177;
                    attribute sigma_Cx : Real = 6.17694152216828;
                    attribute sigma_Cy : Real = 6.03841056141357;
                    attribute sigma_Cz : Real = 6.10611061594035;
                    attribute sigma_Ixx : Real = 29257.4817902047;
                    attribute sigma_Iyy : Real = 30974.8733199517;
                    attribute sigma_Izz : Real = 31348.665992972;
                    attribute sigma_Ixy : Real = 14648.7123233555;
                    attribute sigma_Ixz : Real = 14055.6141501707;
                    attribute sigma_Iyz : Real = 13533.108444455;
                }
            }
            part <'C.1.1.3'> 'Element 3' {
                attribute POIconv : String = "-";
                attribute mass : Real;
                attribute Cx : Real;
                attribute Cy : Real;
                attribute Cz : Real;
                attribute Ixx : Real;
                attribute Iyy : Real;
                attribute Izz : Real;
                attribute Ixy : Real;
                attribute Ixz : Real;
                attribute Iyz : Real;
                attribute Ipoint : Boolean;
                attribute sigma_mass : Real;
                attribute sigma_Cx : Real;
                attribute sigma_Cy : Real;
                attribute sigma_Cz : Real;
                attribute sigma_Ixx : Real;
                attribute sigma_Iyy : Real;
                attribute sigma_Izz : Real;
                attribute sigma_Ixy : Real;
                attribute sigma_Ixz : Real;
                attribute sigma_Iyz : Real;
                part <'C.1.1.3.1'> 'Subsystem 6' {
                    attribute POIconv : String = "-";
                    attribute mass : Real = 18.8096716871578;
                    attribute Cx : Real = -11.5693537041329;
                    attribute Cy : Real = 4.6017221358904;
                    attribute Cz : Real = -0.219714635699278;
                    attribute Ixx : Real = 126503.157875308;
                    attribute Iyy : Real = 130821.451897831;
                    attribute Izz : Real = 139832.797713405;
                    attribute Ixy : Real = -27330.4732531558;
                    attribute Ixz : Real = 10213.7409094325;
                    attribute Iyz : Real = -8358.5761496261;
                    attribute Ipoint : Boolean = false;
                    attribute sigma_mass : Real = 1.78287518741315;
                    attribute sigma_Cx : Real = 8.30433602455131;
                    attribute sigma_Cy : Real = 8.6335684974958;
                    attribute sigma_Cz : Real = 8.0886258541753;
                    attribute sigma_Ixx : Real = 25091.8816625925;
                    attribute sigma_Iyy : Real = 23585.298263235;
                    attribute sigma_Izz : Real = 26889.7956328283;
                    attribute sigma_Ixy : Real = 12628.4345876506;
                    attribute sigma_Ixz : Real = 11017.9778680378;
                    attribute sigma_Iyz : Real = 11569.8009620727;
                }
                part <'C.1.1.3.2'> 'Subsystem 7' {
                    attribute POIconv : String = "-";
                    attribute mass : Real = 21.3095719227504;
                    attribute Cx : Real = 3.79505157047352;
                    attribute Cy : Real = -3.76444319817545;
                    attribute Cz : Real = -1.91883342901819;
                    attribute Ixx : Real = 145089.534761721;
                    attribute Iyy : Real = 116755.199265971;
                    attribute Izz : Real = 132187.502501899;
                    attribute Ixy : Real = -11581.1115202784;
                    attribute Ixz : Real = -1088.80580955095;
                    attribute Iyz : Real = -2664.52223195481;
                    attribute Ipoint : Boolean = false;
                    attribute sigma_mass : Real = 2.00377872522265;
                    attribute sigma_Cx : Real = 7.31371617513524;
                    attribute sigma_Cy : Real = 7.94585521390976;
                    attribute sigma_Cz : Real = 7.97380910400273;
                    attribute sigma_Ixx : Real = 27411.5266321667;
                    attribute sigma_Iyy : Real = 25573.8039865834;
                    attribute sigma_Izz : Real = 23897.3724736549;
                    attribute sigma_Ixy : Real = 10772.9485621938;
                    attribute sigma_Ixz : Real = 11482.4955250343;
                    attribute sigma_Iyz : Real = 11591.5476329245;
                }
                part <'C.1.1.3.3'> 'Subsystem 8' {
                    attribute POIconv : String = "-";
                    attribute mass : Real = 28.1070670932306;
                    attribute Cx : Real = 3.87101258117945;
                    attribute Cy : Real = 2.64280855280396;
                    attribute Cz : Real = -8.76071611200178;
                    attribute Ixx : Real = 201630.696656143;
                    attribute Iyy : Real = 204023.207858607;
                    attribute Izz : Real = 213195.563480536;
                    attribute Ixy : Real = -18665.5286513238;
                    attribute Ixz : Real = 12743.3929923866;
                    attribute Iyz : Real = 6524.16188542017;
                    attribute Ipoint : Boolean = false;
                    attribute sigma_mass : Real = 2.20263806046667;
                    attribute sigma_Cx : Real = 6.67920076034155;
                    attribute sigma_Cy : Real = 6.93086702614295;
                    attribute sigma_Cz : Real = 6.86430580154825;
                    attribute sigma_Ixx : Real = 31706.2666324604;
                    attribute sigma_Iyy : Real = 29929.1995119946;
                    attribute sigma_Izz : Real = 30508.3455811518;
                    attribute sigma_Ixy : Real = 14386.601088249;
                    attribute sigma_Ixz : Real = 14177.4240262339;
                    attribute sigma_Iyz : Real = 14768.103444815;
                }
                part <'C.1.1.3.4'> 'Subsystem 9' {
                    attribute POIconv : String = "-";
                    attribute mass : Real = 31.4611066115648;
                    attribute Cx : Real = 16.1782714710149;
                    attribute Cy : Real = 8.4079850487582;
                    attribute Cz : Real = -3.93749141193082;
                    attribute Ixx : Real = 224389.997650165;
                    attribute Iyy : Real = 198755.691925143;
                    attribute Izz : Real = 188721.425868985;
                    attribute Ixy : Real = -13754.6230834669;
                    attribute Ixz : Real = -3597.50802645028;
                    attribute Iyz : Real = 8522.56743334591;
                    attribute Ipoint : Boolean = false;
                    attribute sigma_mass : Real = 2.25888468035551;
                    attribute sigma_Cx : Real = 5.77588490337362;
                    attribute sigma_Cy : Real = 6.14502141604924;
                    attribute sigma_Cz : Real = 6.34201172318158;
                    attribute sigma_Ixx : Real = 31692.2268651019;
                    attribute sigma_Iyy : Real = 27843.2337548889;
                    attribute sigma_Izz : Real = 28779.5423902606;
                    attribute sigma_Ixy : Real = 12981.4055248014;
                    attribute sigma_Ixz : Real = 12470.3762936556;
                    attribute sigma_Iyz : Real = 13886.4837386363;
                }
                part <'C.1.1.3.5'> 'Subsystem 10' {
                    attribute POIconv : String = "-";
                    attribute mass : Real = 23.5851541556024;
                    attribute Cx : Real = 13.1261313737803;
                    attribute Cy : Real = -6.10317775825893;
                    attribute Cz : Real = 3.65987209960019;
                    attribute Ixx : Real = 168849.350057962;
                    attribute Iyy : Real = 152364.811233075;
                    attribute Izz : Real = 172480.749974969;
                    attribute Ixy : Real = 10479.313699566;
                    attribute Ixz : Real = -12953.599506381;
                    attribute Iyz : Real = 2207.66127972509;
                    attribute Ipoint : Boolean = false;
                    attribute sigma_mass : Real = 1.85191509190403;
                    attribute sigma_Cx : Real = 6.88638447038147;
                    attribute sigma_Cy : Real = 7.33841491647362;
                    attribute sigma_Cz : Real = 6.88779144382258;
                    attribute sigma_Ixx : Real = 26751.6754071003;
                    attribute sigma_Iyy : Real = 24184.4394831202;
                    attribute sigma_Izz : Real = 26575.9633906319;
                    attribute sigma_Ixy : Real = 12727.3719883821;
                    attribute sigma_Ixz : Real = 11592.3234004133;
                    attribute sigma_Iyz : Real = 13118.2511576802;
                }
            }
            part <'C.1.1.4'> 'Element 4' {
                attribute POIconv : String = "-";
                attribute mass : Real;
                attribute Cx : Real;
                attribute Cy : Real;
                attribute Cz : Real;
                attribute Ixx : Real;
                attribute Iyy : Real;
                attribute Izz : Real;
                attribute Ixy : Real;
                attribute Ixz : Real;
                attribute Iyz : Real;
                attribute Ipoint : Boolean;
                attribute sigma_mass : Real;
                attribute sigma_Cx : Real;
                attribute sigma_Cy : Real;
                attribute sigma_Cz : Real;
                attribute sigma_Ixx : Real;
                attribute sigma_Iyy : Real;
                attribute sigma_Izz : Real;
                attribute sigma_Ixy : Real;
                attribute sigma_Ixz : Real;
                attribute sigma_Iyz : Real;
                part <'C.1.1.4.1'> 'Subsystem 11' {
                    attribute POIconv : String = "-";
                    attribute mass : Real = 14.9451207783634;
                    attribute Cx : Real = 10.195621860103;
                    attribute Cy : Real = 2.09268187828716;
                    attribute Cz : Real = -19.4235426684203;
                    attribute Ixx : Real = 112296.218760806;
                    attribute Iyy : Real = 99628.241112531;
                    attribute Izz : Real = 119189.4156484;
                    attribute Ixy : Real = -8967.03371025088;
                    attribute Ixz : Real = -17431.1985376789;
                    attribute Iyz : Real = -9165.97296529818;
                    attribute Ipoint : Boolean = false;
                    attribute sigma_mass : Real = 1.58412617467307;
                    attribute sigma_Cx : Real = 9.22806439249496;
                    attribute sigma_Cy : Real = 10.1528553572091;
                    attribute sigma_Cz : Real = 9.21252398505034;
                    attribute sigma_Ixx : Real = 24044.5797036988;
                    attribute sigma_Iyy : Real = 21460.3260008128;
                    attribute sigma_Izz : Real = 24968.4495631058;
                    attribute sigma_Ixy : Real = 11597.2696220113;
                    attribute sigma_Ixz : Real = 10381.8933088551;
                    attribute sigma_Iyz : Real = 11087.4210154941;
                }
                part <'C.1.1.4.2'> 'Subsystem 12' {
                    attribute POIconv : String = "-";
                    attribute mass : Real = 20.6230943700992;
                    attribute Cx : Real = -14.851521278634;
                    attribute Cy : Real = 16.2922001672647;
                    attribute Cz : Real = 11.4779120376036;
                    attribute Ixx : Real = 117592.468721121;
                    attribute Iyy : Real = 131659.48386514;
                    attribute Izz : Real = 128036.986816737;
                    attribute Ixy : Real = -9033.01978707874;
                    attribute Ixz : Real = 16001.4758018274;
                    attribute Iyz : Real = 16261.7554364832;
                    attribute Ipoint : Boolean = false;
                    attribute sigma_mass : Real = 1.80618173461854;
                    attribute sigma_Cx : Real = 7.44076557844457;
                    attribute sigma_Cy : Real = 7.35160535232119;
                    attribute sigma_Cz : Real = 7.37914997820252;
                    attribute sigma_Ixx : Real = 21990.1808073672;
                    attribute sigma_Iyy : Real = 22585.3103430444;
                    attribute sigma_Izz : Real = 22689.9354152703;
                    attribute sigma_Ixy : Real = 10305.4906536849;
                    attribute sigma_Ixz : Real = 10307.7335571446;
                    attribute sigma_Iyz : Real = 10099.1208904971;
                }
                part <'C.1.1.4.3'> 'Subsystem 13' {
                    attribute POIconv : String = "-";
                    attribute mass : Real = 27.1238765764176;
                    attribute Cx : Real = -2.37675536759992;
                    attribute Cy : Real = 2.44839216900147;
                    attribute Cz : Real = -6.11467993592063;
                    attribute Ixx : Real = 148774.140631208;
                    attribute Iyy : Real = 138236.82791642;
                    attribute Izz : Real = 178429.754991866;
                    attribute Ixy : Real = -10292.2877696905;
                    attribute Ixz : Real = -4473.09437297444;
                    attribute Iyz : Real = -3840.00190867498;
                    attribute Ipoint : Boolean = false;
                    attribute sigma_mass : Real = 2.18356724211557;
                    attribute sigma_Cx : Real = 6.58319304506149;
                    attribute sigma_Cy : Real = 6.69978018134556;
                    attribute sigma_Cz : Real = 6.37126451402271;
                    attribute sigma_Ixx : Real = 25494.6293292794;
                    attribute sigma_Iyy : Real = 24393.3283303798;
                    attribute sigma_Izz : Real = 27190.4885289756;
                    attribute sigma_Ixy : Real = 12977.0996377066;
                    attribute sigma_Ixz : Real = 11434.7628316862;
                    attribute sigma_Iyz : Real = 11592.9985881608;
                }
                part <'C.1.1.4.4'> 'Subsystem 14' {
                    attribute POIconv : String = "-";
                    attribute mass : Real = 27.5124860196796;
                    attribute Cx : Real = 12.0096670045282;
                    attribute Cy : Real = 3.91406746883376;
                    attribute Cz : Real = 10.350073548283;
                    attribute Ixx : Real = 171140.858587677;
                    attribute Iyy : Real = 189129.265259758;
                    attribute Izz : Real = 181772.947242659;
                    attribute Ixy : Real = 2690.6911164965;
                    attribute Ixz : Real = -4928.29623742234;
                    attribute Iyz : Real = 21945.7664689141;
                    attribute Ipoint : Boolean = false;
                    attribute sigma_mass : Real = 2.12532828690341;
                    attribute sigma_Cx : Real = 6.89346882740591;
                    attribute sigma_Cy : Real = 6.55378829480442;
                    attribute sigma_Cz : Real = 6.74434654914451;
                    attribute sigma_Ixx : Real = 27563.9228543181;
                    attribute sigma_Iyy : Real = 30129.4070152304;
                    attribute sigma_Izz : Real = 29502.9115482184;
                    attribute sigma_Ixy : Real = 13082.2445987224;
                    attribute sigma_Ixz : Real = 13298.3573102669;
                    attribute sigma_Iyz : Real = 13067.5581374075;
                }
                part <'C.1.1.4.5'> 'Subsystem 15' {
                    attribute POIconv : String = "-";
                    attribute mass : Real = 29.7628066476493;
                    attribute Cx : Real = -1.56538900294168;
                    attribute Cy : Real = -0.0477830648669657;
                    attribute Cz : Real = 0.193278229129337;
                    attribute Ixx : Real = 216801.699143461;
                    attribute Iyy : Real = 193574.314081658;
                    attribute Izz : Real = 211705.405840072;
                    attribute Ixy : Real = -17153.4022595942;
                    attribute Ixz : Real = 625.542397352405;
                    attribute Iyz : Real = -18281.9838649862;
                    attribute Ipoint : Boolean = false;
                    attribute sigma_mass : Real = 2.08559902137479;
                    attribute sigma_Cx : Real = 6.12831577348984;
                    attribute sigma_Cy : Real = 6.63150170336799;
                    attribute sigma_Cz : Real = 6.59851584776245;
                    attribute sigma_Ixx : Real = 32320.028504059;
                    attribute sigma_Iyy : Real = 28887.6658523858;
                    attribute sigma_Izz : Real = 31192.7800708754;
                    attribute sigma_Ixy : Real = 14730.3235973025;
                    attribute sigma_Ixz : Real = 13427.0463586575;
                    attribute sigma_Iyz : Real = 14963.0408590098;
                }
            }
        }
        part <'C.1.2'> 'Segment 2' {
            attribute POIconv : String = "-";
            attribute mass : Real;
            attribute Cx : Real;
            attribute Cy : Real;
            attribute Cz : Real;
            attribute Ixx : Real;
            attribute Iyy : Real;
            attribute Izz : Real;
            attribute Ixy : Real;
            attribute Ixz : Real;
            attribute Iyz : Real;
            attribute Ipoint : Boolean;
            attribute sigma_mass : Real;
            attribute sigma_Cx : Real;
            attribute sigma_Cy : Real;
            attribute sigma_Cz : Real;
            attribute sigma_Ixx : Real;
            attribute sigma_Iyy : Real;
            attribute sigma_Izz : Real;
            attribute sigma_Ixy : Real;
            attribute sigma_Ixz : Real;
            attribute sigma_Iyz : Real;
            part <'C.1.2.1'> 'Element 5' {
                attribute POIconv : String = "-";
                attribute mass : Real;
                attribute Cx : Real;
                attribute Cy : Real;
                attribute Cz : Real;
                attribute Ixx : Real;
                attribute Iyy : Real;
                attribute Izz : Real;
                attribute Ixy : Real;
                attribute Ixz : Real;
                attribute Iyz : Real;
                attribute Ipoint : Boolean;
                attribute sigma_mass : Real;
                attribute sigma_Cx : Real;
                attribute sigma_Cy : Real;
                attribute sigma_Cz : Real;
                attribute sigma_Ixx : Real;
                attribute sigma_Iyy : Real;
                attribute sigma_Izz : Real;
                attribute sigma_Ixy : Real;
                attribute sigma_Ixz : Real;
                attribute sigma_Iyz : Real;
                part <'C.1.2.1.1'> 'Subsystem 16' {
                    attribute POIconv : String = "-";
                    attribute mass : Real = 22.161742162284;
                    attribute Cx : Real = 17.0733844694972;
                    attribute Cy : Real = -8.78939395395855;
                    attribute Cz : Real = -3.15796254577722;
                    attribute Ixx : Real = 135100.031961754;
                    attribute Iyy : Real = 143906.095949314;
                    attribute Izz : Real = 144737.896666725;
                    attribute Ixy : Real = 11700.687810491;
                    attribute Ixz : Real = 14145.752254766;
                    attribute Iyz : Real = 5.30351836989303;
                    attribute Ipoint : Boolean = false;
                    attribute sigma_mass : Real = 1.98279617083521;
                    attribute sigma_Cx : Real = 7.52149517643293;
                    attribute sigma_Cy : Real = 7.34968047981893;
                    attribute sigma_Cz : Real = 7.67487127969833;
                    attribute sigma_Ixx : Real = 24440.4728982298;
                    attribute sigma_Iyy : Real = 25660.6219727362;
                    attribute sigma_Izz : Real = 24771.1285052745;
                    attribute sigma_Ixy : Real = 11581.8736943187;
                    attribute sigma_Ixz : Real = 11775.4925663249;
                    attribute sigma_Iyz : Real = 11005.4176593535;
                }
                part <'C.1.2.1.2'> 'Subsystem 17' {
                    attribute POIconv : String = "-";
                    attribute mass : Real = 29.5423938467773;
                    attribute Cx : Real = -4.03202498174744;
                    attribute Cy : Real = -10.6351330833579;
                    attribute Cz : Real = -1.60347097898702;
                    attribute Ixx : Real = 178572.190216956;
                    attribute Iyy : Real = 175405.602859607;
                    attribute Izz : Real = 195466.280591592;
                    attribute Ixy : Real = -22254.1050182714;
                    attribute Ixz : Real = 6406.17927553671;
                    attribute Iyz : Real = -9853.10089225709;
                    attribute Ipoint : Boolean = false;
                    attribute sigma_mass : Real = 2.16432838919238;
                    attribute sigma_Cx : Real = 6.31696074112838;
                    attribute sigma_Cy : Real = 6.32089904822312;
                    attribute sigma_Cz : Real = 6.22335564072694;
                    attribute sigma_Ixx : Real = 27305.6031931258;
                    attribute sigma_Iyy : Real = 30154.8038762407;
                    attribute sigma_Izz : Real = 31098.866563983;
                    attribute sigma_Ixy : Real = 14395.2503196966;
                    attribute sigma_Ixz : Real = 14118.4712892782;
                    attribute sigma_Iyz : Real = 12714.0465262416;
                }
                part <'C.1.2.1.3'> 'Subsystem 18' {
                    attribute POIconv : String = "-";
                    attribute mass : Real = 19.5154855631189;
                    attribute Cx : Real = -12.2676108483064;
                    attribute Cy : Real = -10.1429712376395;
                    attribute Cz : Real = -5.79690118851004;
                    attribute Ixx : Real = 96462.7418200831;
                    attribute Iyy : Real = 96314.6030727312;
                    attribute Izz : Real = 119650.333724106;
                    attribute Ixy : Real = 8648.8991649171;
                    attribute Ixz : Real = 3211.03296996463;
                    attribute Iyz : Real = 3122.74823541253;
                    attribute Ipoint : Boolean = false;
                    attribute sigma_mass : Real = 1.71105182860282;
                    attribute sigma_Cx : Real = 7.85095717114578;
                    attribute sigma_Cy : Real = 7.43887580395507;
                    attribute sigma_Cz : Real = 7.86463832449247;
                    attribute sigma_Ixx : Real = 21251.3038771656;
                    attribute sigma_Iyy : Real = 22575.7902033839;
                    attribute sigma_Izz : Real = 21748.9379182778;
                    attribute sigma_Ixy : Real = 10248.0308887224;
                    attribute sigma_Ixz : Real = 10693.686475243;
                    attribute sigma_Iyz : Real = 8620.81845499746;
                }
                part <'C.1.2.1.4'> 'Subsystem 19' {
                    attribute POIconv : String = "-";
                    attribute mass : Real = 25.9089503451223;
                    attribute Cx : Real = 7.57322386166162;
                    attribute Cy : Real = 11.6029986338295;
                    attribute Cz : Real = -1.12102005411882;
                    attribute Ixx : Real = 156476.576808826;
                    attribute Iyy : Real = 167898.906458687;
                    attribute Izz : Real = 178778.095643842;
                    attribute Ixy : Real = -2639.82691692906;
                    attribute Ixz : Real = -6387.78305442022;
                    attribute Iyz : Real = -22770.9529063191;
                    attribute Ipoint : Boolean = false;
                    attribute sigma_mass : Real = 1.96158918494741;
                    attribute sigma_Cx : Real = 6.7334331047514;
                    attribute sigma_Cy : Real = 6.72667269444589;
                    attribute sigma_Cz : Real = 6.5346972770742;
                    attribute sigma_Ixx : Real = 25180.931703749;
                    attribute sigma_Iyy : Real = 25676.9194948646;
                    attribute sigma_Izz : Real = 26189.1112463493;
                    attribute sigma_Ixy : Real = 12652.7060317845;
                    attribute sigma_Ixz : Real = 12249.381669955;
                    attribute sigma_Iyz : Real = 11973.5020789252;
                }
            }
            part <'C.1.2.2'> 'Element 6' {
                attribute POIconv : String = "-";
                attribute mass : Real;
                attribute Cx : Real;
                attribute Cy : Real;
                attribute Cz : Real;
                attribute Ixx : Real;
                attribute Iyy : Real;
                attribute Izz : Real;
                attribute Ixy : Real;
                attribute Ixz : Real;
                attribute Iyz : Real;
                attribute Ipoint : Boolean;
                attribute sigma_mass : Real;
                attribute sigma_Cx : Real;
                attribute sigma_Cy : Real;
                attribute sigma_Cz : Real;
                attribute sigma_Ixx : Real;
                attribute sigma_Iyy : Real;
                attribute sigma_Izz : Real;
                attribute sigma_Ixy : Real;
                attribute sigma_Ixz : Real;
                attribute sigma_Iyz : Real;
                part <'C.1.2.2.1'> 'Subsystem 20' {
                    attribute POIconv : String = "-";
                    attribute mass : Real = 12.2561247495885;
                    attribute Cx : Real = -25.7562192337221;
                    attribute Cy : Real = -0.824043594629511;
                    attribute Cz : Real = -10.6351375464037;
                    attribute Ixx : Real = 87544.8073850559;
                    attribute Iyy : Real = 61464.8712126481;
                    attribute Izz : Real = 67216.863784577;
                    attribute Ixy : Real = 10928.2339729024;
                    attribute Ixz : Real = -9715.00644037948;
                    attribute Iyz : Real = 15205.3372786371;
                    attribute Ipoint : Boolean = false;
                    attribute sigma_mass : Real = 1.41688552460227;
                    attribute sigma_Cx : Real = 8.82212872718726;
                    attribute sigma_Cy : Real = 10.2935798255274;
                    attribute sigma_Cz : Real = 9.6856657739437;
                    attribute sigma_Ixx : Real = 18663.6008456877;
                    attribute sigma_Iyy : Real = 15193.2760448708;
                    attribute sigma_Izz : Real = 16940.2447239751;
                    attribute sigma_Ixy : Real = 7747.88322666128;
                    attribute sigma_Ixz : Real = 7035.36585442799;
                    attribute sigma_Iyz : Real = 8892.59488643608;
                }
                part <'C.1.2.2.2'> 'Subsystem 21' {
                    attribute POIconv : String = "-";
                    attribute mass : Real = 24.4467074862055;
                    attribute Cx : Real = -17.8654250832255;
                    attribute Cy : Real = -8.502678657259;
                    attribute Cz : Real = -8.58179651520894;
                    attribute Ixx : Real = 153686.229995657;
                    attribute Iyy : Real = 155943.842536973;
                    attribute Izz : Real = 138841.509462469;
                    attribute Ixy : Real = -9668.02834751517;
                    attribute Ixz : Real = 10857.7609663758;
                    attribute Iyz : Real = -16077.6859636475;
                    attribute Ipoint : Boolean = false;
                    attribute sigma_mass : Real = 2.22154517172001;
                    attribute sigma_Cx : Real = 7.21394469761201;
                    attribute sigma_Cy : Real = 7.09545106201515;
                    attribute sigma_Cz : Real = 7.56169250713857;
                    attribute sigma_Ixx : Real = 27423.2260591856;
                    attribute sigma_Iyy : Real = 30079.6603279328;
                    attribute sigma_Izz : Real = 25397.1422660735;
                    attribute sigma_Ixy : Real = 10968.5436794025;
                    attribute sigma_Ixz : Real = 14186.8021623093;
                    attribute sigma_Iyz : Real = 12136.0276557979;
                }
                part <'C.1.2.2.3'> 'Subsystem 22' {
                    attribute POIconv : String = "-";
                    attribute mass : Real = 9.30971435309062;
                    attribute Cx : Real = -37.4443672682464;
                    attribute Cy : Real = -6.92516492223097;
                    attribute Cz : Real = 14.9983160300981;
                    attribute Ixx : Real = 56514.5487065425;
                    attribute Iyy : Real = 57897.9334477266;
                    attribute Izz : Real = 64554.3534706857;
                    attribute Ixy : Real = 1994.62562039108;
                    attribute Ixz : Real = 2091.31008477506;
                    attribute Iyz : Real = -5237.53139100455;
                    attribute Ipoint : Boolean = false;
                    attribute sigma_mass : Real = 1.29343360537868;
                    attribute sigma_Cx : Real = 12.4594268301692;
                    attribute sigma_Cy : Real = 12.1926701093219;
                    attribute sigma_Cz : Real = 11.314738187504;
                    attribute sigma_Ixx : Real = 15462.2525923388;
                    attribute sigma_Iyy : Real = 16824.5285059316;
                    attribute sigma_Izz : Real = 18590.6160547616;
                    attribute sigma_Ixy : Real = 8961.09063940504;
                    attribute sigma_Ixz : Real = 8126.01173191185;
                    attribute sigma_Iyz : Real = 7598.57899711447;
                }
            }
            part <'C.1.2.3'> 'Element 7' {
                attribute POIconv : String = "-";
                attribute mass : Real;
                attribute Cx : Real;
                attribute Cy : Real;
                attribute Cz : Real;
                attribute Ixx : Real;
                attribute Iyy : Real;
                attribute Izz : Real;
                attribute Ixy : Real;
                attribute Ixz : Real;
                attribute Iyz : Real;
                attribute Ipoint : Boolean;
                attribute sigma_mass : Real;
                attribute sigma_Cx : Real;
                attribute sigma_Cy : Real;
                attribute sigma_Cz : Real;
                attribute sigma_Ixx : Real;
                attribute sigma_Iyy : Real;
                attribute sigma_Izz : Real;
                attribute sigma_Ixy : Real;
                attribute sigma_Ixz : Real;
                attribute sigma_Iyz : Real;
                part <'C.1.2.3.1'> 'Subsystem 23' {
                    attribute POIconv : String = "-";
                    attribute mass : Real = 26.125954121839;
                    attribute Cx : Real = 2.36144524105729;
                    attribute Cy : Real = 7.99620978997108;
                    attribute Cz : Real = 7.62615168618198;
                    attribute Ixx : Real = 155060.549896364;
                    attribute Iyy : Real = 172731.489359635;
                    attribute Izz : Real = 188449.965592821;
                    attribute Ixy : Real = -1180.98832590301;
                    attribute Ixz : Real = 17992.7923991966;
                    attribute Iyz : Real = 6516.43617546473;
                    attribute Ipoint : Boolean = false;
                    attribute sigma_mass : Real = 2.18356724211558;
                    attribute sigma_Cx : Real = 7.34015394852516;
                    attribute sigma_Cy : Real = 6.97132725801459;
                    attribute sigma_Cz : Real = 6.74102210742217;
                    attribute sigma_Ixx : Real = 28157.2623010505;
                    attribute sigma_Iyy : Real = 31224.0314185331;
                    attribute sigma_Izz : Real = 30289.9362478386;
                    attribute sigma_Ixy : Real = 13203.6300585885;
                    attribute sigma_Ixz : Real = 13501.3514003216;
                    attribute sigma_Iyz : Real = 12962.6160505339;
                }
                part <'C.1.2.3.2'> 'Subsystem 24' {
                    attribute POIconv : String = "-";
                    attribute mass : Real = 23.3829052960798;
                    attribute Cx : Real = 18.2483930303304;
                    attribute Cy : Real = -4.68014506183036;
                    attribute Cz : Real = -4.61509828769966;
                    attribute Ixx : Real = 127797.971597442;
                    attribute Iyy : Real = 130060.540573923;
                    attribute Izz : Real = 141189.755991966;
                    attribute Ixy : Real = 6231.14099236619;
                    attribute Ixz : Real = 13234.7825555199;
                    attribute Iyz : Real = -8520.72996240667;
                    attribute Ipoint : Boolean = false;
                    attribute sigma_mass : Real = 2.00377872522265;
                    attribute sigma_Cx : Real = 7.13960301863429;
                    attribute sigma_Cy : Real = 7.17013956576363;
                    attribute sigma_Cz : Real = 6.7661736829219;
                    attribute sigma_Ixx : Real = 23640.4889104681;
                    attribute sigma_Iyy : Real = 23908.8058378682;
                    attribute sigma_Izz : Real = 24132.2763245103;
                    attribute sigma_Ixy : Real = 11362.9953459552;
                    attribute sigma_Ixz : Real = 11351.6082516595;
                    attribute sigma_Iyz : Real = 11012.8805171598;
                }
                part <'C.1.2.3.3'> 'Subsystem 25' {
                    attribute POIconv : String = "-";
                    attribute mass : Real = 35.4504025518682;
                    attribute Cx : Real = -3.51735337008212;
                    attribute Cy : Real = 6.67001105653984;
                    attribute Cz : Real = 0.358798569479314;
                    attribute Ixx : Real = 236295.354712751;
                    attribute Iyy : Real = 218763.167187945;
                    attribute Izz : Real = 244473.952547997;
                    attribute Ixy : Real = 29748.1021771666;
                    attribute Ixz : Real = -4158.05389242568;
                    attribute Iyz : Real = 9962.01205640983;
                    attribute Ipoint : Boolean = false;
                    attribute sigma_mass : Real = 2.48796921577311;
                    attribute sigma_Cx : Real = 5.83282343354277;
                    attribute sigma_Cy : Real = 6.35541396927329;
                    attribute sigma_Cz : Real = 5.92807957386679;
                    attribute sigma_Ixx : Real = 34261.5114312648;
                    attribute sigma_Iyy : Real = 30727.8891293943;
                    attribute sigma_Izz : Real = 33968.9691501079;
                    attribute sigma_Ixy : Real = 15492.8207597648;
                    attribute sigma_Ixz : Real = 14389.8494298297;
                    attribute sigma_Iyz : Real = 15528.9893625539;
                }
                part <'C.1.2.3.4'> 'Subsystem 26' {
                    attribute POIconv : String = "-";
                    attribute mass : Real = 17.6722501646807;
                    attribute Cx : Real = -15.1876417050577;
                    attribute Cy : Real = 6.45654603492478;
                    attribute Cz : Real = 25.1766073276358;
                    attribute Ixx : Real = 133656.235772331;
                    attribute Iyy : Real = 110567.390770016;
                    attribute Izz : Real = 129817.974258635;
                    attribute Ixy : Real = 14334.3947231386;
                    attribute Ixz : Real = -12586.7634995524;
                    attribute Iyz : Real = 11234.043727891;
                    attribute Ipoint : Boolean = false;
                    attribute sigma_mass : Real = 1.73532327960562;
                    attribute sigma_Cx : Real = 8.48564972785461;
                    attribute sigma_Cy : Real = 8.5435180124694;
                    attribute sigma_Cz : Real = 8.82396635256734;
                    attribute sigma_Ixx : Real = 24680.7995004184;
                    attribute sigma_Iyy : Real = 24496.82814455;
                    attribute sigma_Izz : Real = 23317.0813082834;
                    attribute sigma_Ixy : Real = 10934.0290339664;
                    attribute sigma_Ixz : Real = 11144.1410884034;
                    attribute sigma_Iyz : Real = 11452.8824253838;
                }
                part <'C.1.2.3.5'> 'Subsystem 27' {
                    attribute POIconv : String = "-";
                    attribute mass : Real = 17.4997445275516;
                    attribute Cx : Real = -2.03142071936586;
                    attribute Cy : Real = 14.8889481908696;
                    attribute Cz : Real = 14.4091661722222;
                    attribute Ixx : Real = 102298.615848101;
                    attribute Iyy : Real = 95136.553658161;
                    attribute Izz : Real = 111067.089261766;
                    attribute Ixy : Real = 6838.23322753953;
                    attribute Ixz : Real = -11576.7357063685;
                    attribute Iyz : Real = 9468.42763043454;
                    attribute Ipoint : Boolean = false;
                    attribute sigma_mass : Real = 1.71105182860282;
                    attribute sigma_Cx : Real = 7.81355735201804;
                    attribute sigma_Cy : Real = 8.05725815685384;
                    attribute sigma_Cz : Real = 7.79933688593335;
                    attribute sigma_Ixx : Real = 19305.8417531769;
                    attribute sigma_Iyy : Real = 19410.7107572498;
                    attribute sigma_Izz : Real = 20455.5560560962;
                    attribute sigma_Ixy : Real = 9835.92094037721;
                    attribute sigma_Ixz : Real = 9331.51250769986;
                    attribute sigma_Iyz : Real = 9153.4040853191;
                }
            }
        }
    }
}
