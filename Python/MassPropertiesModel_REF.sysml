package MassPropertiesModel_REF {
    private import ScalarValues::Boolean;
    private import ScalarValues::Real;
    private import ScalarValues::String;

    part <'C.1'> 'System 1' {
        attribute POIconv : String = "-";
        attribute Ipoint : Boolean;
        attribute mass : Real;
        attribute 'σ_mass' : Real;
        attribute Cx : Real;
        attribute 'σ_Cx' : Real;
        attribute Cy : Real;
        attribute 'σ_Cy' : Real;
        attribute Cz : Real;
        attribute 'σ_Cz' : Real;
        attribute Ixx : Real;
        attribute 'σ_Ixx' : Real;
        attribute Iyy : Real;
        attribute 'σ_Iyy' : Real;
        attribute Izz : Real;
        attribute 'σ_Izz' : Real;
        attribute Ixy : Real;
        attribute 'σ_Ixy' : Real;
        attribute Ixz : Real;
        attribute 'σ_Ixz' : Real;
        attribute Iyz : Real;
        attribute 'σ_Iyz' : Real;
        part <'C.1.1'> 'Segment 1' {
            attribute POIconv : String = "-";
            attribute Ipoint : Boolean;
            attribute mass : Real;
            attribute 'σ_mass' : Real;
            attribute Cx : Real;
            attribute 'σ_Cx' : Real;
            attribute Cy : Real;
            attribute 'σ_Cy' : Real;
            attribute Cz : Real;
            attribute 'σ_Cz' : Real;
            attribute Ixx : Real;
            attribute 'σ_Ixx' : Real;
            attribute Iyy : Real;
            attribute 'σ_Iyy' : Real;
            attribute Izz : Real;
            attribute 'σ_Izz' : Real;
            attribute Ixy : Real;
            attribute 'σ_Ixy' : Real;
            attribute Ixz : Real;
            attribute 'σ_Ixz' : Real;
            attribute Iyz : Real;
            attribute 'σ_Iyz' : Real;
            part <'C.1.1.1'> 'Element 1' {
                attribute POIconv : String = "-";
                attribute Ipoint : Boolean;
                attribute mass : Real;
                attribute 'σ_mass' : Real;
                attribute Cx : Real;
                attribute 'σ_Cx' : Real;
                attribute Cy : Real;
                attribute 'σ_Cy' : Real;
                attribute Cz : Real;
                attribute 'σ_Cz' : Real;
                attribute Ixx : Real;
                attribute 'σ_Ixx' : Real;
                attribute Iyy : Real;
                attribute 'σ_Iyy' : Real;
                attribute Izz : Real;
                attribute 'σ_Izz' : Real;
                attribute Ixy : Real;
                attribute 'σ_Ixy' : Real;
                attribute Ixz : Real;
                attribute 'σ_Ixz' : Real;
                attribute Iyz : Real;
                attribute 'σ_Iyz' : Real;
                part <'C.1.1.1.1'> 'Subsystem 1' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.1.1.1'> 'Assembly 1' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.1.1.1.1'> 'Subassembly 1' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.1.1.1'> 'Part 1' {
                                attribute POIconv : String = "+";
                                attribute Ipoint : Boolean = false;
                                attribute mass : Real = 0.1521751119736582;
                                attribute 'σ_mass' : Real = 0.28909372274994966;
                                attribute Cx : Real = -34.29865841753781;
                                attribute 'σ_Cx' : Real = 28.721044428837228;
                                attribute Cy : Real = -66.12854544073343;
                                attribute 'σ_Cy' : Real = 28.23690002309109;
                                attribute Cz : Real = -73.53497515432537;
                                attribute 'σ_Cz' : Real = 29.057750463592832;
                                attribute Ixx : Real = 0.18346195470478338;
                                attribute 'σ_Ixx' : Real = 0.37074144170588635;
                                attribute Iyy : Real = 0.15837006341318408;
                                attribute 'σ_Iyy' : Real = 0.3723953238821935;
                                attribute Izz : Real = 0.18470199509290466;
                                attribute 'σ_Izz' : Real = 0.37017423652493897;
                                attribute Ixy : Real = 0.0037985231754760324;
                                attribute 'σ_Ixy' : Real = 0.02351283871158888;
                                attribute Ixz : Real = 0.0037582877147340657;
                                attribute 'σ_Ixz' : Real = 0.022566176940390956;
                                attribute Iyz : Real = -0.014017164148438758;
                                attribute 'σ_Iyz' : Real = 0.02209918015384651;
                            }
                            part <'C.1.1.1.1.1.1.2'> 'Part 2' {
                                attribute POIconv : String = "+";
                                attribute Ipoint : Boolean = false;
                                attribute mass : Real = 0.18868499795440585;
                                attribute 'σ_mass' : Real = 0.28909372274994966;
                                attribute Cx : Real = -34.91070759482682;
                                attribute 'σ_Cx' : Real = 28.721044428837228;
                                attribute Cy : Real = -26.443653739988804;
                                attribute 'σ_Cy' : Real = 28.23690002309109;
                                attribute Cz : Real = 53.87474172748625;
                                attribute 'σ_Cz' : Real = 29.057750463592832;
                                attribute Ixx : Real = 0.27656684418566047;
                                attribute 'σ_Ixx' : Real = 0.37074144170588635;
                                attribute Iyy : Real = 0.27637506714868143;
                                attribute 'σ_Iyy' : Real = 0.3723953238821935;
                                attribute Izz : Real = 0.27051180191523305;
                                attribute 'σ_Izz' : Real = 0.37017423652493897;
                                attribute Ixy : Real = 0.00778657987414301;
                                attribute 'σ_Ixy' : Real = 0.02351283871158888;
                                attribute Ixz : Real = -0.0023871384096893107;
                                attribute 'σ_Ixz' : Real = 0.022566176940390956;
                                attribute Iyz : Real = 0.00589012398047391;
                                attribute 'σ_Iyz' : Real = 0.02209918015384651;
                            }
                            part <'C.1.1.1.1.1.1.3'> 'Part 3' {
                                attribute POIconv : String = "+";
                                attribute Ipoint : Boolean = false;
                                attribute mass : Real = 0.7697069959277287;
                                attribute 'σ_mass' : Real = 0.28909372274994966;
                                attribute Cx : Real = -17.265138030052185;
                                attribute 'σ_Cx' : Real = 28.721044428837228;
                                attribute Cy : Real = 20.49697022885084;
                                attribute 'σ_Cy' : Real = 28.23690002309109;
                                attribute Cz : Real = -53.10265985317528;
                                attribute 'σ_Cz' : Real = 29.057750463592832;
                                attribute Ixx : Real = 0.904850891478444;
                                attribute 'σ_Ixx' : Real = 0.37074144170588635;
                                attribute Iyy : Real = 0.867503905740675;
                                attribute 'σ_Iyy' : Real = 0.3723953238821935;
                                attribute Izz : Real = 0.853946253806776;
                                attribute 'σ_Izz' : Real = 0.37017423652493897;
                                attribute Ixy : Real = -0.01872761180810094;
                                attribute 'σ_Ixy' : Real = 0.02351283871158888;
                                attribute Ixz : Real = 0.007255691281044883;
                                attribute 'σ_Ixz' : Real = 0.022566176940390956;
                                attribute Iyz : Real = 0.003569366743797703;
                                attribute 'σ_Iyz' : Real = 0.02209918015384651;
                            }
                        }
                        part <'C.1.1.1.1.1.2'> 'Subassembly 2' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.1.2.1'> 'Part 4' {
                                attribute POIconv : String = "+";
                                attribute Ipoint : Boolean = false;
                                attribute mass : Real = 0.1454309616452083;
                                attribute 'σ_mass' : Real = 0.28909372274994966;
                                attribute Cx : Real = 41.68215095996857;
                                attribute 'σ_Cx' : Real = 28.721044428837228;
                                attribute Cy : Real = -91.38107933104038;
                                attribute 'σ_Cy' : Real = 28.23690002309109;
                                attribute Cz : Real = -68.34089234471321;
                                attribute 'σ_Cz' : Real = 29.057750463592832;
                                attribute Ixx : Real = 0.1717862834362892;
                                attribute 'σ_Ixx' : Real = 0.37074144170588635;
                                attribute Iyy : Real = 0.20386716344036002;
                                attribute 'σ_Iyy' : Real = 0.3723953238821935;
                                attribute Izz : Real = 0.16809870997644813;
                                attribute 'σ_Izz' : Real = 0.37017423652493897;
                                attribute Ixy : Real = 0.006733403644455866;
                                attribute 'σ_Ixy' : Real = 0.02351283871158888;
                                attribute Ixz : Real = -0.009373831223081025;
                                attribute 'σ_Ixz' : Real = 0.022566176940390956;
                                attribute Iyz : Real = -5.888376607972038e-4;
                                attribute 'σ_Iyz' : Real = 0.02209918015384651;
                            }
                            part <'C.1.1.1.1.1.2.2'> 'Part 5' {
                                attribute POIconv : String = "-";
                                attribute Ipoint : Boolean = false;
                                attribute mass : Real = 0.9522862783651799;
                                attribute 'σ_mass' : Real = 0.28909372274994966;
                                attribute Cx : Real = 79.8512370325625;
                                attribute 'σ_Cx' : Real = 28.721044428837228;
                                attribute Cy : Real = 32.26179811172187;
                                attribute 'σ_Cy' : Real = 28.23690002309109;
                                attribute Cz : Real = -25.890729343518615;
                                attribute 'σ_Cz' : Real = 29.057750463592832;
                                attribute Ixx : Real = 1.2568463851420968;
                                attribute 'σ_Ixx' : Real = 0.37074144170588635;
                                attribute Iyy : Real = 1.1609834388077394;
                                attribute 'σ_Iyy' : Real = 0.3723953238821935;
                                attribute Izz : Real = 1.2267789861314367;
                                attribute 'σ_Izz' : Real = 0.37017423652493897;
                                attribute Ixy : Real = 0.005367798972772337;
                                attribute 'σ_Ixy' : Real = 0.02351283871158888;
                                attribute Ixz : Real = -0.013565949879023667;
                                attribute 'σ_Ixz' : Real = 0.022566176940390956;
                                attribute Iyz : Real = 0.10434382732355574;
                                attribute 'σ_Iyz' : Real = 0.02209918015384651;
                            }
                            part <'C.1.1.1.1.1.2.3'> 'Part 6' {
                                attribute POIconv : String = "+";
                                attribute Ipoint : Boolean = false;
                                attribute mass : Real = 0.8294994919870514;
                                attribute 'σ_mass' : Real = 0.28909372274994966;
                                attribute Cx : Real = 18.63987920805812;
                                attribute 'σ_Cx' : Real = 28.721044428837228;
                                attribute Cy : Real = 12.642979109659791;
                                attribute 'σ_Cy' : Real = 28.23690002309109;
                                attribute Cz : Real = -75.99323713220656;
                                attribute 'σ_Cz' : Real = 29.057750463592832;
                                attribute Ixx : Real = 0.7835029760668094;
                                attribute 'σ_Ixx' : Real = 0.37074144170588635;
                                attribute Iyy : Real = 0.7752406776518191;
                                attribute 'σ_Iyy' : Real = 0.3723953238821935;
                                attribute Izz : Real = 0.7801212941347628;
                                attribute 'σ_Izz' : Real = 0.37017423652493897;
                                attribute Ixy : Real = -0.0015970713176399714;
                                attribute 'σ_Ixy' : Real = 0.02351283871158888;
                                attribute Ixz : Real = -0.023550038977687725;
                                attribute 'σ_Ixz' : Real = 0.022566176940390956;
                                attribute Iyz : Real = 0.01137750065967411;
                                attribute 'σ_Iyz' : Real = 0.02209918015384651;
                            }
                            part <'C.1.1.1.1.1.2.4'> 'Part 7' {
                                attribute POIconv : String = "+";
                                attribute Ipoint : Boolean = false;
                                attribute mass : Real = 0.6792828879216686;
                                attribute 'σ_mass' : Real = 0.28909372274994966;
                                attribute Cx : Real = 27.477146219462156;
                                attribute 'σ_Cx' : Real = 28.721044428837228;
                                attribute Cy : Real = 24.369020108133554;
                                attribute 'σ_Cy' : Real = 28.23690002309109;
                                attribute Cz : Real = 31.537090241909027;
                                attribute 'σ_Cz' : Real = 29.057750463592832;
                                attribute Ixx : Real = 0.8372575836394387;
                                attribute 'σ_Ixx' : Real = 0.37074144170588635;
                                attribute Iyy : Real = 0.943580796291087;
                                attribute 'σ_Iyy' : Real = 0.3723953238821935;
                                attribute Izz : Real = 0.7879040587225734;
                                attribute 'σ_Izz' : Real = 0.37017423652493897;
                                attribute Ixy : Real = 0.0076169696805578994;
                                attribute 'σ_Ixy' : Real = 0.02351283871158888;
                                attribute Ixz : Real = -0.010881734663394874;
                                attribute 'σ_Ixz' : Real = 0.022566176940390956;
                                attribute Iyz : Real = -0.008582621063851836;
                                attribute 'σ_Iyz' : Real = 0.02209918015384651;
                            }
                            part <'C.1.1.1.1.1.2.5'> 'Part 8' {
                                attribute POIconv : String = "-";
                                attribute Ipoint : Boolean = false;
                                attribute mass : Real = 0.9274918380929157;
                                attribute 'σ_mass' : Real = 0.28909372274994966;
                                attribute Cx : Real = 48.09760567732155;
                                attribute 'σ_Cx' : Real = 28.721044428837228;
                                attribute Cy : Real = -80.08880070410669;
                                attribute 'σ_Cy' : Real = 28.23690002309109;
                                attribute Cz : Real = -47.49870989471674;
                                attribute 'σ_Cz' : Real = 29.057750463592832;
                                attribute Ixx : Real = 1.182191375767316;
                                attribute 'σ_Ixx' : Real = 0.37074144170588635;
                                attribute Iyy : Real = 1.1778809746036805;
                                attribute 'σ_Iyy' : Real = 0.3723953238821935;
                                attribute Izz : Real = 1.0313577602875554;
                                attribute 'σ_Izz' : Real = 0.37017423652493897;
                                attribute Ixy : Real = 0.0023185027804681546;
                                attribute 'σ_Ixy' : Real = 0.02351283871158888;
                                attribute Ixz : Real = -0.09811931207805208;
                                attribute 'σ_Ixz' : Real = 0.022566176940390956;
                                attribute Iyz : Real = 0.01526965162144308;
                                attribute 'σ_Iyz' : Real = 0.02209918015384651;
                            }
                        }
                        part <'C.1.1.1.1.1.3'> 'Subassembly 3' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.1.3.1'> 'Part 9' {
                                attribute POIconv : String = "-";
                                attribute Ipoint : Boolean = false;
                                attribute mass : Real = 0.012705426325090228;
                                attribute 'σ_mass' : Real = 0.28909372274994966;
                                attribute Cx : Real = -61.86356646940112;
                                attribute 'σ_Cx' : Real = 28.721044428837228;
                                attribute Cy : Real = 39.72041537053883;
                                attribute 'σ_Cy' : Real = 28.23690002309109;
                                attribute Cz : Real = 39.86886125057936;
                                attribute 'σ_Cz' : Real = 29.057750463592832;
                                attribute Ixx : Real = 0.014102043535239485;
                                attribute 'σ_Ixx' : Real = 0.37074144170588635;
                                attribute Iyy : Real = 0.015186854591097613;
                                attribute 'σ_Iyy' : Real = 0.3723953238821935;
                                attribute Izz : Real = 0.015178208293440349;
                                attribute 'σ_Izz' : Real = 0.37017423652493897;
                                attribute Ixy : Real = -7.571641608683109e-4;
                                attribute 'σ_Ixy' : Real = 0.02351283871158888;
                                attribute Ixz : Real = 9.218718164940613e-4;
                                attribute 'σ_Ixz' : Real = 0.022566176940390956;
                                attribute Iyz : Real = 9.860125308335174e-4;
                                attribute 'σ_Iyz' : Real = 0.02209918015384651;
                            }
                            part <'C.1.1.1.1.1.3.2'> 'Part 10' {
                                attribute POIconv : String = "+";
                                attribute Ipoint : Boolean = false;
                                attribute mass : Real = 0.8187970951176249;
                                attribute 'σ_mass' : Real = 0.28909372274994966;
                                attribute Cx : Real = 45.64918917603791;
                                attribute 'σ_Cx' : Real = 28.721044428837228;
                                attribute Cy : Real = 82.09767998196185;
                                attribute 'σ_Cy' : Real = 28.23690002309109;
                                attribute Cz : Real = -21.63806138560176;
                                attribute 'σ_Cz' : Real = 29.057750463592832;
                                attribute Ixx : Real = 0.7926596080396694;
                                attribute 'σ_Ixx' : Real = 0.37074144170588635;
                                attribute Iyy : Real = 0.7918937658538793;
                                attribute 'σ_Iyy' : Real = 0.3723953238821935;
                                attribute Izz : Real = 0.8374083084660802;
                                attribute 'σ_Izz' : Real = 0.37017423652493897;
                                attribute Ixy : Real = 0.005264876541506831;
                                attribute 'σ_Ixy' : Real = 0.02351283871158888;
                                attribute Ixz : Real = -0.022091082560101775;
                                attribute 'σ_Ixz' : Real = 0.022566176940390956;
                                attribute Iyz : Real = -0.03450787670732504;
                                attribute 'σ_Iyz' : Real = 0.02209918015384651;
                            }
                            part <'C.1.1.1.1.1.3.3'> 'Part 11' {
                                attribute POIconv : String = "-";
                                attribute Ipoint : Boolean = false;
                                attribute mass : Real = 0.48895880657131785;
                                attribute 'σ_mass' : Real = 0.28909372274994966;
                                attribute Cx : Real = -94.86765237525105;
                                attribute 'σ_Cx' : Real = 28.721044428837228;
                                attribute Cy : Real = -71.30342787131667;
                                attribute 'σ_Cy' : Real = 28.23690002309109;
                                attribute Cz : Real = -8.021717378869653;
                                attribute 'σ_Cz' : Real = 29.057750463592832;
                                attribute Ixx : Real = 0.6301673669658536;
                                attribute 'σ_Ixx' : Real = 0.37074144170588635;
                                attribute Iyy : Real = 0.5959242710680464;
                                attribute 'σ_Iyy' : Real = 0.3723953238821935;
                                attribute Izz : Real = 0.5951663723889477;
                                attribute 'σ_Izz' : Real = 0.37017423652493897;
                                attribute Ixy : Real = -0.005026221719268833;
                                attribute 'σ_Ixy' : Real = 0.02351283871158888;
                                attribute Ixz : Real = 0.011158228346530134;
                                attribute 'σ_Ixz' : Real = 0.022566176940390956;
                                attribute Iyz : Real = -0.004689767300963031;
                                attribute 'σ_Iyz' : Real = 0.02209918015384651;
                            }
                            part <'C.1.1.1.1.1.3.4'> 'Part 12' {
                                attribute POIconv : String = "-";
                                attribute Ipoint : Boolean = false;
                                attribute mass : Real = 0.20360899326065554;
                                attribute 'σ_mass' : Real = 0.28909372274994966;
                                attribute Cx : Real = 76.15776215679944;
                                attribute 'σ_Cx' : Real = 28.721044428837228;
                                attribute Cy : Real = 8.406097907572985;
                                attribute 'σ_Cy' : Real = 28.23690002309109;
                                attribute Cz : Real = 39.03013924136758;
                                attribute 'σ_Cz' : Real = 29.057750463592832;
                                attribute Ixx : Real = 0.3128143534696859;
                                attribute 'σ_Ixx' : Real = 0.37074144170588635;
                                attribute Iyy : Real = 0.3152177792644552;
                                attribute 'σ_Iyy' : Real = 0.3723953238821935;
                                attribute Izz : Real = 0.3127604152723791;
                                attribute 'σ_Izz' : Real = 0.37017423652493897;
                                attribute Ixy : Real = 0.008740178069113726;
                                attribute 'σ_Ixy' : Real = 0.02351283871158888;
                                attribute Ixz : Real = -4.100437388877678e-4;
                                attribute 'σ_Ixz' : Real = 0.022566176940390956;
                                attribute Iyz : Real = 9.315418409794618e-4;
                                attribute 'σ_Iyz' : Real = 0.02209918015384651;
                            }
                        }
                        part <'C.1.1.1.1.1.4'> 'Subassembly 4' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.1.4.1'> 'Part 13' {
                                attribute POIconv : String = "-";
                                attribute Ipoint : Boolean = false;
                                attribute mass : Real = 0.3572169222852681;
                                attribute 'σ_mass' : Real = 0.28909372274994966;
                                attribute Cx : Real = 84.20433290302753;
                                attribute 'σ_Cx' : Real = 28.721044428837228;
                                attribute Cy : Real = -54.49259839951992;
                                attribute 'σ_Cy' : Real = 28.23690002309109;
                                attribute Cz : Real = -81.80367383174598;
                                attribute 'σ_Cz' : Real = 29.057750463592832;
                                attribute Ixx : Real = 0.47484915144953266;
                                attribute 'σ_Ixx' : Real = 0.37074144170588635;
                                attribute Iyy : Real = 0.5360134926434229;
                                attribute 'σ_Iyy' : Real = 0.3723953238821935;
                                attribute Izz : Real = 0.42690188421355063;
                                attribute 'σ_Izz' : Real = 0.37017423652493897;
                                attribute Ixy : Real = -0.040837676934439904;
                                attribute 'σ_Ixy' : Real = 0.02351283871158888;
                                attribute Ixz : Real = 0.008546856401091856;
                                attribute 'σ_Ixz' : Real = 0.022566176940390956;
                                attribute Iyz : Real = -0.006819686196795118;
                                attribute 'σ_Iyz' : Real = 0.02209918015384651;
                            }
                            part <'C.1.1.1.1.1.4.2'> 'Part 14' {
                                attribute POIconv : String = "+";
                                attribute Ipoint : Boolean = false;
                                attribute mass : Real = 0.5571071715857834;
                                attribute 'σ_mass' : Real = 0.28909372274994966;
                                attribute Cx : Real = 99.08350468613207;
                                attribute 'σ_Cx' : Real = 28.721044428837228;
                                attribute Cy : Real = -62.094857916235924;
                                attribute 'σ_Cy' : Real = 28.23690002309109;
                                attribute Cz : Real = 51.5940326731652;
                                attribute 'σ_Cz' : Real = 29.057750463592832;
                                attribute Ixx : Real = 0.7362727185191851;
                                attribute 'σ_Ixx' : Real = 0.37074144170588635;
                                attribute Iyy : Real = 0.768145720247189;
                                attribute 'σ_Iyy' : Real = 0.3723953238821935;
                                attribute Izz : Real = 0.7087226870067952;
                                attribute 'σ_Izz' : Real = 0.37017423652493897;
                                attribute Ixy : Real = -0.0596578707553419;
                                attribute 'σ_Ixy' : Real = 0.02351283871158888;
                                attribute Ixz : Real = 0.014016170605811895;
                                attribute 'σ_Ixz' : Real = 0.022566176940390956;
                                attribute Iyz : Real = 0.023145325843034623;
                                attribute 'σ_Iyz' : Real = 0.02209918015384651;
                            }
                            part <'C.1.1.1.1.1.4.3'> 'Part 15' {
                                attribute POIconv : String = "-";
                                attribute Ipoint : Boolean = false;
                                attribute mass : Real = 0.5190961779379286;
                                attribute 'σ_mass' : Real = 0.28909372274994966;
                                attribute Cx : Real = -33.48792656324804;
                                attribute 'σ_Cx' : Real = 28.721044428837228;
                                attribute Cy : Real = -97.70168159157038;
                                attribute 'σ_Cy' : Real = 28.23690002309109;
                                attribute Cz : Real = 60.95813768915832;
                                attribute 'σ_Cz' : Real = 29.057750463592832;
                                attribute Ixx : Real = 0.6284872739303747;
                                attribute 'σ_Ixx' : Real = 0.37074144170588635;
                                attribute Iyy : Real = 0.5800037008023744;
                                attribute 'σ_Iyy' : Real = 0.3723953238821935;
                                attribute Izz : Real = 0.6021852105108795;
                                attribute 'σ_Izz' : Real = 0.37017423652493897;
                                attribute Ixy : Real = -0.047508415561734615;
                                attribute 'σ_Ixy' : Real = 0.02351283871158888;
                                attribute Ixz : Real = -0.0014863199142704706;
                                attribute 'σ_Ixz' : Real = 0.022566176940390956;
                                attribute Iyz : Real = -0.004023124277438803;
                                attribute 'σ_Iyz' : Real = 0.02209918015384651;
                            }
                            part <'C.1.1.1.1.1.4.4'> 'Part 16' {
                                attribute POIconv : String = "+";
                                attribute Ipoint : Boolean = false;
                                attribute mass : Real = 0.7931164753204212;
                                attribute 'σ_mass' : Real = 0.28909372274994966;
                                attribute Cx : Real = 91.02454143576324;
                                attribute 'σ_Cx' : Real = 28.721044428837228;
                                attribute Cy : Real = 65.8065673429519;
                                attribute 'σ_Cy' : Real = 28.23690002309109;
                                attribute Cz : Real = -86.37497588060796;
                                attribute 'σ_Cz' : Real = 29.057750463592832;
                                attribute Ixx : Real = 1.0813363570354253;
                                attribute 'σ_Ixx' : Real = 0.37074144170588635;
                                attribute Iyy : Real = 1.0293142713537367;
                                attribute 'σ_Iyy' : Real = 0.3723953238821935;
                                attribute Izz : Real = 0.9894751949948105;
                                attribute 'σ_Izz' : Real = 0.37017423652493897;
                                attribute Ixy : Real = 0.043647868381421054;
                                attribute 'σ_Ixy' : Real = 0.02351283871158888;
                                attribute Ixz : Real = 0.054978072317282925;
                                attribute 'σ_Ixz' : Real = 0.022566176940390956;
                                attribute Iyz : Real = 0.010604305309151851;
                                attribute 'σ_Iyz' : Real = 0.02209918015384651;
                            }
                        }
                        part <'C.1.1.1.1.1.5'> 'Subassembly 5' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.1.5.1'> 'Part 17' {
                                attribute POIconv : String = "+";
                                attribute Ipoint : Boolean = false;
                                attribute mass : Real = 0.26025292832637203;
                                attribute 'σ_mass' : Real = 0.28909372274994966;
                                attribute Cx : Real = -41.36475306004286;
                                attribute 'σ_Cx' : Real = 28.721044428837228;
                                attribute Cy : Real = -73.9494463428855;
                                attribute 'σ_Cy' : Real = 28.23690002309109;
                                attribute Cz : Real = 89.89339577965438;
                                attribute 'σ_Cz' : Real = 29.057750463592832;
                                attribute Ixx : Real = 0.3116709562430628;
                                attribute 'σ_Ixx' : Real = 0.37074144170588635;
                                attribute Iyy : Real = 0.3530933369496171;
                                attribute 'σ_Iyy' : Real = 0.3723953238821935;
                                attribute Izz : Real = 0.2972344682989129;
                                attribute 'σ_Izz' : Real = 0.37017423652493897;
                                attribute Ixy : Real = 0.0018383202757886082;
                                attribute 'σ_Ixy' : Real = 0.02351283871158888;
                                attribute Ixz : Real = 0.01412175398157994;
                                attribute 'σ_Ixz' : Real = 0.022566176940390956;
                                attribute Iyz : Real = -0.018449147825117758;
                                attribute 'σ_Iyz' : Real = 0.02209918015384651;
                            }
                            part <'C.1.1.1.1.1.5.2'> 'Part 18' {
                                attribute POIconv : String = "-";
                                attribute Ipoint : Boolean = false;
                                attribute mass : Real = 0.7820831922453363;
                                attribute 'σ_mass' : Real = 0.28909372274994966;
                                attribute Cx : Real = -27.885227696970105;
                                attribute 'σ_Cx' : Real = 28.721044428837228;
                                attribute Cy : Real = 14.93952446617186;
                                attribute 'σ_Cy' : Real = 28.23690002309109;
                                attribute Cz : Real = -2.1522313822060823;
                                attribute 'σ_Cz' : Real = 29.057750463592832;
                                attribute Ixx : Real = 0.8518186503340801;
                                attribute 'σ_Ixx' : Real = 0.37074144170588635;
                                attribute Iyy : Real = 0.8871099261236091;
                                attribute 'σ_Iyy' : Real = 0.3723953238821935;
                                attribute Izz : Real = 0.9621465209277352;
                                attribute 'σ_Izz' : Real = 0.37017423652493897;
                                attribute Ixy : Real = 0.005493539823235515;
                                attribute 'σ_Ixy' : Real = 0.02351283871158888;
                                attribute Ixz : Real = 0.015048475976331601;
                                attribute 'σ_Ixz' : Real = 0.022566176940390956;
                                attribute Iyz : Real = -0.029676148897113057;
                                attribute 'σ_Iyz' : Real = 0.02209918015384651;
                            }
                        }
                    }
                    part <'C.1.1.1.1.2'> 'Assembly 2' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.1.1.2.1'> 'Subassembly 6' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.2.1.1'> 'Part 19' {
                                attribute POIconv : String = "+";
                                attribute Ipoint : Boolean = false;
                                attribute mass : Real = 0.5135785475107841;
                                attribute 'σ_mass' : Real = 0.28909372274994966;
                                attribute Cx : Real = 70.91835285536945;
                                attribute 'σ_Cx' : Real = 28.721044428837228;
                                attribute Cy : Real = -88.44160186126828;
                                attribute 'σ_Cy' : Real = 28.23690002309109;
                                attribute Cz : Real = 89.99599302187562;
                                attribute 'σ_Cz' : Real = 29.057750463592832;
                                attribute Ixx : Real = 0.5418073046051372;
                                attribute 'σ_Ixx' : Real = 0.37074144170588635;
                                attribute Iyy : Real = 0.5932172548868199;
                                attribute 'σ_Iyy' : Real = 0.3723953238821935;
                                attribute Izz : Real = 0.5824304131793494;
                                attribute 'σ_Izz' : Real = 0.37017423652493897;
                                attribute Ixy : Real = 0.0016399993397964328;
                                attribute 'σ_Ixy' : Real = 0.02351283871158888;
                                attribute Ixz : Real = -0.017114214656449286;
                                attribute 'σ_Ixz' : Real = 0.022566176940390956;
                                attribute Iyz : Real = -0.0011244915949632785;
                                attribute 'σ_Iyz' : Real = 0.02209918015384651;
                            }
                            part <'C.1.1.1.1.2.1.2'> 'Part 20' {
                                attribute POIconv : String = "-";
                                attribute Ipoint : Boolean = false;
                                attribute mass : Real = 0.7413986765367444;
                                attribute 'σ_mass' : Real = 0.28909372274994966;
                                attribute Cx : Real = -89.23627063632011;
                                attribute 'σ_Cx' : Real = 28.721044428837228;
                                attribute Cy : Real = 76.23628829605877;
                                attribute 'σ_Cy' : Real = 28.23690002309109;
                                attribute Cz : Real = -80.8549493085593;
                                attribute 'σ_Cz' : Real = 29.057750463592832;
                                attribute Ixx : Real = 0.7888714458993766;
                                attribute 'σ_Ixx' : Real = 0.37074144170588635;
                                attribute Iyy : Real = 0.8292074355111392;
                                attribute 'σ_Iyy' : Real = 0.3723953238821935;
                                attribute Izz : Real = 0.7861894780092485;
                                attribute 'σ_Izz' : Real = 0.37017423652493897;
                                attribute Ixy : Real = -0.008352315737316422;
                                attribute 'σ_Ixy' : Real = 0.02351283871158888;
                                attribute Ixz : Real = 0.032743987892089356;
                                attribute 'σ_Ixz' : Real = 0.022566176940390956;
                                attribute Iyz : Real = 0.007893626385324908;
                                attribute 'σ_Iyz' : Real = 0.02209918015384651;
                            }
                            part <'C.1.1.1.1.2.1.3'> 'Part 21' {
                                attribute POIconv : String = "-";
                                attribute Ipoint : Boolean = false;
                                attribute mass : Real = 0.8808226748576854;
                                attribute 'σ_mass' : Real = 0.28909372274994966;
                                attribute Cx : Real = 85.35944437608123;
                                attribute 'σ_Cx' : Real = 28.721044428837228;
                                attribute Cy : Real = 77.34298836439848;
                                attribute 'σ_Cy' : Real = 28.23690002309109;
                                attribute Cz : Real = 4.569195583462715;
                                attribute 'σ_Cz' : Real = 29.057750463592832;
                                attribute Ixx : Real = 0.9338089361498445;
                                attribute 'σ_Ixx' : Real = 0.37074144170588635;
                                attribute Iyy : Real = 0.9559248959713871;
                                attribute 'σ_Iyy' : Real = 0.3723953238821935;
                                attribute Izz : Real = 0.8498839843522831;
                                attribute 'σ_Izz' : Real = 0.37017423652493897;
                                attribute Ixy : Real = -0.026741949099851788;
                                attribute 'σ_Ixy' : Real = 0.02351283871158888;
                                attribute Ixz : Real = -0.015093191609550995;
                                attribute 'σ_Ixz' : Real = 0.022566176940390956;
                                attribute Iyz : Real = 0.016018618533133334;
                                attribute 'σ_Iyz' : Real = 0.02209918015384651;
                            }
                        }
                        part <'C.1.1.1.1.2.2'> 'Subassembly 7' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.2.2.1'> 'Part 22' {
                                attribute POIconv : String = "-";
                                attribute Ipoint : Boolean = false;
                                attribute mass : Real = 0.7712820994718932;
                                attribute 'σ_mass' : Real = 0.28909372274994966;
                                attribute Cx : Real = 12.463552132248878;
                                attribute 'σ_Cx' : Real = 28.721044428837228;
                                attribute Cy : Real = 33.60808356665075;
                                attribute 'σ_Cy' : Real = 28.23690002309109;
                                attribute Cz : Real = 28.75491394661367;
                                attribute 'σ_Cz' : Real = 29.057750463592832;
                                attribute Ixx : Real = 0.9896094194201455;
                                attribute 'σ_Ixx' : Real = 0.37074144170588635;
                                attribute Iyy : Real = 0.9995423118036598;
                                attribute 'σ_Iyy' : Real = 0.3723953238821935;
                                attribute Izz : Real = 0.7714555629277365;
                                attribute 'σ_Izz' : Real = 0.37017423652493897;
                                attribute Ixy : Real = -0.042997255698823456;
                                attribute 'σ_Ixy' : Real = 0.02351283871158888;
                                attribute Ixz : Real = 0.01937819990961847;
                                attribute 'σ_Ixz' : Real = 0.022566176940390956;
                                attribute Iyz : Real = 0.04890118300263788;
                                attribute 'σ_Iyz' : Real = 0.02209918015384651;
                            }
                            part <'C.1.1.1.1.2.2.2'> 'Part 23' {
                                attribute POIconv : String = "-";
                                attribute Ipoint : Boolean = false;
                                attribute mass : Real = 0.6032088426768314;
                                attribute 'σ_mass' : Real = 0.28909372274994966;
                                attribute Cx : Real = 42.426528595387936;
                                attribute 'σ_Cx' : Real = 28.721044428837228;
                                attribute Cy : Real = -50.0353897921741;
                                attribute 'σ_Cy' : Real = 28.23690002309109;
                                attribute Cz : Real = -22.477717651054263;
                                attribute 'σ_Cz' : Real = 29.057750463592832;
                                attribute Ixx : Real = 0.6082759830375095;
                                attribute 'σ_Ixx' : Real = 0.37074144170588635;
                                attribute Iyy : Real = 0.7294572504843319;
                                attribute 'σ_Iyy' : Real = 0.3723953238821935;
                                attribute Izz : Real = 0.732360445450684;
                                attribute 'σ_Izz' : Real = 0.37017423652493897;
                                attribute Ixy : Real = 0.0864758372841277;
                                attribute 'σ_Ixy' : Real = 0.02351283871158888;
                                attribute Ixz : Real = -0.04663228031792355;
                                attribute 'σ_Ixz' : Real = 0.022566176940390956;
                                attribute Iyz : Real = 0.01064362876184336;
                                attribute 'σ_Iyz' : Real = 0.02209918015384651;
                            }
                            part <'C.1.1.1.1.2.2.3'> 'Part 24' {
                                attribute POIconv : String = "+";
                                attribute Ipoint : Boolean = false;
                                attribute mass : Real = 0.8692736305550206;
                                attribute 'σ_mass' : Real = 0.28909372274994966;
                                attribute Cx : Real = 66.44520820118487;
                                attribute 'σ_Cx' : Real = 28.721044428837228;
                                attribute Cy : Real = -11.240406800061464;
                                attribute 'σ_Cy' : Real = 28.23690002309109;
                                attribute Cz : Real = -94.49159284122288;
                                attribute 'σ_Cz' : Real = 29.057750463592832;
                                attribute Ixx : Real = 1.0648305957090487;
                                attribute 'σ_Ixx' : Real = 0.37074144170588635;
                                attribute Iyy : Real = 0.9793059901999447;
                                attribute 'σ_Iyy' : Real = 0.3723953238821935;
                                attribute Izz : Real = 0.9980270038897266;
                                attribute 'σ_Izz' : Real = 0.37017423652493897;
                                attribute Ixy : Real = -0.08187407144464187;
                                attribute 'σ_Ixy' : Real = 0.02351283871158888;
                                attribute Ixz : Real = -0.03451382343710634;
                                attribute 'σ_Ixz' : Real = 0.022566176940390956;
                                attribute Iyz : Real = 0.0853480077839882;
                                attribute 'σ_Iyz' : Real = 0.02209918015384651;
                            }
                        }
                        part <'C.1.1.1.1.2.3'> 'Subassembly 8' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.2.3.1'> 'Part 25' {
                                attribute POIconv : String = "-";
                                attribute Ipoint : Boolean = false;
                                attribute mass : Real = 0.43263949803891594;
                                attribute 'σ_mass' : Real = 0.28909372274994966;
                                attribute Cx : Real = 71.7912663705647;
                                attribute 'σ_Cx' : Real = 28.721044428837228;
                                attribute Cy : Real = -8.486271928995848;
                                attribute 'σ_Cy' : Real = 28.23690002309109;
                                attribute Cz : Real = 42.408562218770385;
                                attribute 'σ_Cz' : Real = 29.057750463592832;
                                attribute Ixx : Real = 0.4110113670047712;
                                attribute 'σ_Ixx' : Real = 0.37074144170588635;
                                attribute Iyy : Real = 0.5230117612574051;
                                attribute 'σ_Iyy' : Real = 0.3723953238821935;
                                attribute Izz : Real = 0.5064963110824754;
                                attribute 'σ_Izz' : Real = 0.37017423652493897;
                                attribute Ixy : Real = -0.027218124716260356;
                                attribute 'σ_Ixy' : Real = 0.02351283871158888;
                                attribute Ixz : Real = -0.0554366259456813;
                                attribute 'σ_Ixz' : Real = 0.022566176940390956;
                                attribute Iyz : Real = -0.004615459387363461;
                                attribute 'σ_Iyz' : Real = 0.02209918015384651;
                            }
                            part <'C.1.1.1.1.2.3.2'> 'Part 26' {
                                attribute POIconv : String = "+";
                                attribute Ipoint : Boolean = false;
                                attribute mass : Real = 0.5616151409610175;
                                attribute 'σ_mass' : Real = 0.28909372274994966;
                                attribute Cx : Real = 23.045656364411116;
                                attribute 'σ_Cx' : Real = 28.721044428837228;
                                attribute Cy : Real = -40.90169197879732;
                                attribute 'σ_Cy' : Real = 28.23690002309109;
                                attribute Cz : Real = -78.23526933789253;
                                attribute 'σ_Cz' : Real = 29.057750463592832;
                                attribute Ixx : Real = 0.6726617743261615;
                                attribute 'σ_Ixx' : Real = 0.37074144170588635;
                                attribute Iyy : Real = 0.6535860322980943;
                                attribute 'σ_Iyy' : Real = 0.3723953238821935;
                                attribute Izz : Real = 0.6483018815249533;
                                attribute 'σ_Izz' : Real = 0.37017423652493897;
                                attribute Ixy : Real = 0.0047905078751247256;
                                attribute 'σ_Ixy' : Real = 0.02351283871158888;
                                attribute Ixz : Real = -0.02586964620047131;
                                attribute 'σ_Ixz' : Real = 0.022566176940390956;
                                attribute Iyz : Real = -0.01652036659346097;
                                attribute 'σ_Iyz' : Real = 0.02209918015384651;
                            }
                            part <'C.1.1.1.1.2.3.3'> 'Part 27' {
                                attribute POIconv : String = "-";
                                attribute Ipoint : Boolean = false;
                                attribute mass : Real = 0.8929159117490053;
                                attribute 'σ_mass' : Real = 0.28909372274994966;
                                attribute Cx : Real = 15.40752169676125;
                                attribute 'σ_Cx' : Real = 28.721044428837228;
                                attribute Cy : Real = -68.8828909303993;
                                attribute 'σ_Cy' : Real = 28.23690002309109;
                                attribute Cz : Real = -37.21725856885314;
                                attribute 'σ_Cz' : Real = 29.057750463592832;
                                attribute Ixx : Real = 1.3836969050186676;
                                attribute 'σ_Ixx' : Real = 0.37074144170588635;
                                attribute Iyy : Real = 1.1247671667969468;
                                attribute 'σ_Iyy' : Real = 0.3723953238821935;
                                attribute Izz : Real = 1.184343945119268;
                                attribute 'σ_Izz' : Real = 0.37017423652493897;
                                attribute Ixy : Real = -0.04590787104991288;
                                attribute 'σ_Ixy' : Real = 0.02351283871158888;
                                attribute Ixz : Real = -0.03864313172501027;
                                attribute 'σ_Ixz' : Real = 0.022566176940390956;
                                attribute Iyz : Real = 0.021437510926272454;
                                attribute 'σ_Iyz' : Real = 0.02209918015384651;
                            }
                            part <'C.1.1.1.1.2.3.4'> 'Part 28' {
                                attribute POIconv : String = "-";
                                attribute Ipoint : Boolean = false;
                                attribute mass : Real = 0.7840164996779058;
                                attribute 'σ_mass' : Real = 0.28909372274994966;
                                attribute Cx : Real = 70.36396483890712;
                                attribute 'σ_Cx' : Real = 28.721044428837228;
                                attribute Cy : Real = -49.943631794303656;
                                attribute 'σ_Cy' : Real = 28.23690002309109;
                                attribute Cz : Real = 84.3402674421668;
                                attribute 'σ_Cz' : Real = 29.057750463592832;
                                attribute Ixx : Real = 0.7498778096224765;
                                attribute 'σ_Ixx' : Real = 0.37074144170588635;
                                attribute Iyy : Real = 0.7420379089018556;
                                attribute 'σ_Iyy' : Real = 0.3723953238821935;
                                attribute Izz : Real = 0.7675189025218033;
                                attribute 'σ_Izz' : Real = 0.37017423652493897;
                                attribute Ixy : Real = -0.0018618220508169769;
                                attribute 'σ_Ixy' : Real = 0.02351283871158888;
                                attribute Ixz : Real = -1.6751341913394552e-5;
                                attribute 'σ_Ixz' : Real = 0.022566176940390956;
                                attribute Iyz : Real = 0.002102450383311292;
                                attribute 'σ_Iyz' : Real = 0.02209918015384651;
                            }
                            part <'C.1.1.1.1.2.3.5'> 'Part 29' {
                                attribute POIconv : String = "+";
                                attribute Ipoint : Boolean = false;
                                attribute mass : Real = 0.695954920454882;
                                attribute 'σ_mass' : Real = 0.28909372274994966;
                                attribute Cx : Real = -49.38840065151453;
                                attribute 'σ_Cx' : Real = 28.721044428837228;
                                attribute Cy : Real = 64.11762246862054;
                                attribute 'σ_Cy' : Real = 28.23690002309109;
                                attribute Cz : Real = -93.65140623413026;
                                attribute 'σ_Cz' : Real = 29.057750463592832;
                                attribute Ixx : Real = 0.7776619133776641;
                                attribute 'σ_Ixx' : Real = 0.37074144170588635;
                                attribute Iyy : Real = 0.7350937571569712;
                                attribute 'σ_Iyy' : Real = 0.3723953238821935;
                                attribute Izz : Real = 0.7850556748371398;
                                attribute 'σ_Izz' : Real = 0.37017423652493897;
                                attribute Ixy : Real = 0.005618900920627741;
                                attribute 'σ_Ixy' : Real = 0.02351283871158888;
                                attribute Ixz : Real = 0.047816837860602326;
                                attribute 'σ_Ixz' : Real = 0.022566176940390956;
                                attribute Iyz : Real = -4.039556146849208e-4;
                                attribute 'σ_Iyz' : Real = 0.02209918015384651;
                            }
                        }
                        part <'C.1.1.1.1.2.4'> 'Subassembly 9' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.2.4.1'> 'Part 30' {
                                attribute POIconv : String = "-";
                                attribute Ipoint : Boolean = false;
                                attribute mass : Real = 0.9436988299102522;
                                attribute 'σ_mass' : Real = 0.28909372274994966;
                                attribute Cx : Real = -66.92492282018065;
                                attribute 'σ_Cx' : Real = 28.721044428837228;
                                attribute Cy : Real = 49.732256261631846;
                                attribute 'σ_Cy' : Real = 28.23690002309109;
                                attribute Cz : Real = 93.86770399287343;
                                attribute 'σ_Cz' : Real = 29.057750463592832;
                                attribute Ixx : Real = 1.2886768949444425;
                                attribute 'σ_Ixx' : Real = 0.37074144170588635;
                                attribute Iyy : Real = 1.2217401945586743;
                                attribute 'σ_Iyy' : Real = 0.3723953238821935;
                                attribute Izz : Real = 1.1206466271500322;
                                attribute 'σ_Izz' : Real = 0.37017423652493897;
                                attribute Ixy : Real = 0.06072433196133281;
                                attribute 'σ_Ixy' : Real = 0.02351283871158888;
                                attribute Ixz : Real = -0.08619452278113188;
                                attribute 'σ_Ixz' : Real = 0.022566176940390956;
                                attribute Iyz : Real = -0.04547609834927677;
                                attribute 'σ_Iyz' : Real = 0.02209918015384651;
                            }
                            part <'C.1.1.1.1.2.4.2'> 'Part 31' {
                                attribute POIconv : String = "+";
                                attribute Ipoint : Boolean = false;
                                attribute mass : Real = 0.673545587467961;
                                attribute 'σ_mass' : Real = 0.28909372274994966;
                                attribute Cx : Real = 97.01616941019893;
                                attribute 'σ_Cx' : Real = 28.721044428837228;
                                attribute Cy : Real = 69.5228427182883;
                                attribute 'σ_Cy' : Real = 28.23690002309109;
                                attribute Cz : Real = 35.328703513368964;
                                attribute 'σ_Cz' : Real = 29.057750463592832;
                                attribute Ixx : Real = 0.8473901395472749;
                                attribute 'σ_Ixx' : Real = 0.37074144170588635;
                                attribute Iyy : Real = 0.8234551849261366;
                                attribute 'σ_Iyy' : Real = 0.3723953238821935;
                                attribute Izz : Real = 0.7668203241750924;
                                attribute 'σ_Izz' : Real = 0.37017423652493897;
                                attribute Ixy : Real = 0.041488819265171846;
                                attribute 'σ_Ixy' : Real = 0.02351283871158888;
                                attribute Ixz : Real = 0.050520560228710466;
                                attribute 'σ_Ixz' : Real = 0.022566176940390956;
                                attribute Iyz : Real = -0.021624172208190406;
                                attribute 'σ_Iyz' : Real = 0.02209918015384651;
                            }
                            part <'C.1.1.1.1.2.4.3'> 'Part 32' {
                                attribute POIconv : String = "+";
                                attribute Ipoint : Boolean = false;
                                attribute mass : Real = 0.11553020319505594;
                                attribute 'σ_mass' : Real = 0.28909372274994966;
                                attribute Cx : Real = -0.730050215497613;
                                attribute 'σ_Cx' : Real = 28.721044428837228;
                                attribute Cy : Real = 24.466659035533667;
                                attribute 'σ_Cy' : Real = 28.23690002309109;
                                attribute Cz : Real = 57.09592984057963;
                                attribute 'σ_Cz' : Real = 29.057750463592832;
                                attribute Ixx : Real = 0.13509820083969448;
                                attribute 'σ_Ixx' : Real = 0.37074144170588635;
                                attribute Iyy : Real = 0.1452609027797815;
                                attribute 'σ_Iyy' : Real = 0.3723953238821935;
                                attribute Izz : Real = 0.1495497763298617;
                                attribute 'σ_Izz' : Real = 0.37017423652493897;
                                attribute Ixy : Real = -0.0026632551093619668;
                                attribute 'σ_Ixy' : Real = 0.02351283871158888;
                                attribute Ixz : Real = 0.0023267850009609675;
                                attribute 'σ_Ixz' : Real = 0.022566176940390956;
                                attribute Iyz : Real = -8.189717595237061e-4;
                                attribute 'σ_Iyz' : Real = 0.02209918015384651;
                            }
                            part <'C.1.1.1.1.2.4.4'> 'Part 33' {
                                attribute POIconv : String = "+";
                                attribute Ipoint : Boolean = false;
                                attribute mass : Real = 0.34857530738203785;
                                attribute 'σ_mass' : Real = 0.28909372274994966;
                                attribute Cx : Real = -63.98548884317279;
                                attribute 'σ_Cx' : Real = 28.721044428837228;
                                attribute Cy : Real = -74.24236019141972;
                                attribute 'σ_Cy' : Real = 28.23690002309109;
                                attribute Cz : Real = 76.13917263224721;
                                attribute 'σ_Cz' : Real = 29.057750463592832;
                                attribute Ixx : Real = 0.4715985839694769;
                                attribute 'σ_Ixx' : Real = 0.37074144170588635;
                                attribute Iyy : Real = 0.41674429063310514;
                                attribute 'σ_Iyy' : Real = 0.3723953238821935;
                                attribute Izz : Real = 0.43622683259144296;
                                attribute 'σ_Izz' : Real = 0.37017423652493897;
                                attribute Ixy : Real = 0.019312334336277263;
                                attribute 'σ_Ixy' : Real = 0.02351283871158888;
                                attribute Ixz : Real = 0.0041147134064364824;
                                attribute 'σ_Ixz' : Real = 0.022566176940390956;
                                attribute Iyz : Real = -0.007185592006803824;
                                attribute 'σ_Iyz' : Real = 0.02209918015384651;
                            }
                        }
                        part <'C.1.1.1.1.2.5'> 'Subassembly 10' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.2.5.1'> 'Part 34' {
                                attribute POIconv : String = "+";
                                attribute Ipoint : Boolean = false;
                                attribute mass : Real = 0.8280004888649565;
                                attribute 'σ_mass' : Real = 0.28909372274994966;
                                attribute Cx : Real = 51.439374685287476;
                                attribute 'σ_Cx' : Real = 28.721044428837228;
                                attribute Cy : Real = -62.66789431683719;
                                attribute 'σ_Cy' : Real = 28.23690002309109;
                                attribute Cz : Real = -57.598067820072174;
                                attribute 'σ_Cz' : Real = 29.057750463592832;
                                attribute Ixx : Real = 0.9017238691922955;
                                attribute 'σ_Ixx' : Real = 0.37074144170588635;
                                attribute Iyy : Real = 0.9002202716176154;
                                attribute 'σ_Iyy' : Real = 0.3723953238821935;
                                attribute Izz : Real = 0.9105615537368861;
                                attribute 'σ_Izz' : Real = 0.37017423652493897;
                                attribute Ixy : Real = -0.021639086044565475;
                                attribute 'σ_Ixy' : Real = 0.02351283871158888;
                                attribute Ixz : Real = -0.018413166917529266;
                                attribute 'σ_Ixz' : Real = 0.022566176940390956;
                                attribute Iyz : Real = -0.004759512616736874;
                                attribute 'σ_Iyz' : Real = 0.02209918015384651;
                            }
                            part <'C.1.1.1.1.2.5.2'> 'Part 35' {
                                attribute POIconv : String = "-";
                                attribute Ipoint : Boolean = false;
                                attribute mass : Real = 0.15809483261196874;
                                attribute 'σ_mass' : Real = 0.28909372274994966;
                                attribute Cx : Real = 48.91085121780634;
                                attribute 'σ_Cx' : Real = 28.721044428837228;
                                attribute Cy : Real = 4.567188955843449;
                                attribute 'σ_Cy' : Real = 28.23690002309109;
                                attribute Cz : Real = -73.94922659732401;
                                attribute 'σ_Cz' : Real = 29.057750463592832;
                                attribute Ixx : Real = 0.16368212381628913;
                                attribute 'σ_Ixx' : Real = 0.37074144170588635;
                                attribute Iyy : Real = 0.18943937654425835;
                                attribute 'σ_Iyy' : Real = 0.3723953238821935;
                                attribute Izz : Real = 0.18782810692943028;
                                attribute 'σ_Izz' : Real = 0.37017423652493897;
                                attribute Ixy : Real = 0.014759018051930757;
                                attribute 'σ_Ixy' : Real = 0.02351283871158888;
                                attribute Ixz : Real = 0.001260635244357189;
                                attribute 'σ_Ixz' : Real = 0.022566176940390956;
                                attribute Iyz : Real = 0.005826912991183145;
                                attribute 'σ_Iyz' : Real = 0.02209918015384651;
                            }
                            part <'C.1.1.1.1.2.5.3'> 'Part 36' {
                                attribute POIconv : String = "-";
                                attribute Ipoint : Boolean = false;
                                attribute mass : Real = 0.3790072734153364;
                                attribute 'σ_mass' : Real = 0.28909372274994966;
                                attribute Cx : Real = -39.83527738600969;
                                attribute 'σ_Cx' : Real = 28.721044428837228;
                                attribute Cy : Real = -20.327910967171192;
                                attribute 'σ_Cy' : Real = 28.23690002309109;
                                attribute Cz : Real = 26.927303662523627;
                                attribute 'σ_Cz' : Real = 29.057750463592832;
                                attribute Ixx : Real = 0.3206503236592797;
                                attribute 'σ_Ixx' : Real = 0.37074144170588635;
                                attribute Iyy : Real = 0.33904506000963136;
                                attribute 'σ_Iyy' : Real = 0.3723953238821935;
                                attribute Izz : Real = 0.3391154753793135;
                                attribute 'σ_Izz' : Real = 0.37017423652493897;
                                attribute Ixy : Real = -0.0026212176125589106;
                                attribute 'σ_Ixy' : Real = 0.02351283871158888;
                                attribute Ixz : Real = 9.86966653668253e-4;
                                attribute 'σ_Ixz' : Real = 0.022566176940390956;
                                attribute Iyz : Real = 0.0017618757083064402;
                                attribute 'σ_Iyz' : Real = 0.02209918015384651;
                            }
                            part <'C.1.1.1.1.2.5.4'> 'Part 37' {
                                attribute POIconv : String = "+";
                                attribute Ipoint : Boolean = false;
                                attribute mass : Real = 0.8809562529905234;
                                attribute 'σ_mass' : Real = 0.28909372274994966;
                                attribute Cx : Real = 3.8416769355535507;
                                attribute 'σ_Cx' : Real = 28.721044428837228;
                                attribute Cy : Real = -29.869883647188544;
                                attribute 'σ_Cy' : Real = 28.23690002309109;
                                attribute Cz : Real = -63.54120313189924;
                                attribute 'σ_Cz' : Real = 29.057750463592832;
                                attribute Ixx : Real = 1.1398817251819047;
                                attribute 'σ_Ixx' : Real = 0.37074144170588635;
                                attribute Iyy : Real = 1.0770260638110756;
                                attribute 'σ_Iyy' : Real = 0.3723953238821935;
                                attribute Izz : Real = 1.0212118495769824;
                                attribute 'σ_Izz' : Real = 0.37017423652493897;
                                attribute Ixy : Real = 0.007045131470129704;
                                attribute 'σ_Ixy' : Real = 0.02351283871158888;
                                attribute Ixz : Real = -0.052201494660640384;
                                attribute 'σ_Ixz' : Real = 0.022566176940390956;
                                attribute Iyz : Real = -0.026616296064105982;
                                attribute 'σ_Iyz' : Real = 0.02209918015384651;
                            }
                        }
                    }
                    part <'C.1.1.1.1.3'> 'Assembly 3' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.1.1.3.1'> 'Subassembly 11' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.3.1.1'> 'Part 38' {
                                attribute POIconv : String = "+";
                                attribute Ipoint : Boolean = false;
                                attribute mass : Real = 0.14622153044352307;
                                attribute 'σ_mass' : Real = 0.28909372274994966;
                                attribute Cx : Real = 99.21634825877845;
                                attribute 'σ_Cx' : Real = 28.721044428837228;
                                attribute Cy : Real = 93.6696857213974;
                                attribute 'σ_Cy' : Real = 28.23690002309109;
                                attribute Cz : Real = -56.561761954799294;
                                attribute 'σ_Cz' : Real = 29.057750463592832;
                                attribute Ixx : Real = 0.19643423394214446;
                                attribute 'σ_Ixx' : Real = 0.37074144170588635;
                                attribute Iyy : Real = 0.21343720542294503;
                                attribute 'σ_Iyy' : Real = 0.3723953238821935;
                                attribute Izz : Real = 0.2165462492762795;
                                attribute 'σ_Izz' : Real = 0.37017423652493897;
                                attribute Ixy : Real = 0.0034981924195316228;
                                attribute 'σ_Ixy' : Real = 0.02351283871158888;
                                attribute Ixz : Real = 7.380366460453652e-4;
                                attribute 'σ_Ixz' : Real = 0.022566176940390956;
                                attribute Iyz : Real = -0.0025580736595108944;
                                attribute 'σ_Iyz' : Real = 0.02209918015384651;
                            }
                            part <'C.1.1.1.1.3.1.2'> 'Part 39' {
                                attribute POIconv : String = "+";
                                attribute Ipoint : Boolean = false;
                                attribute mass : Real = 0.816904512305744;
                                attribute 'σ_mass' : Real = 0.28909372274994966;
                                attribute Cx : Real = 6.2335321214050055;
                                attribute 'σ_Cx' : Real = 28.721044428837228;
                                attribute Cy : Real = -64.85962145961821;
                                attribute 'σ_Cy' : Real = 28.23690002309109;
                                attribute Cz : Real = -7.743510697036982;
                                attribute 'σ_Cz' : Real = 29.057750463592832;
                                attribute Ixx : Real = 1.038350924273957;
                                attribute 'σ_Ixx' : Real = 0.37074144170588635;
                                attribute Iyy : Real = 1.0347491496685401;
                                attribute 'σ_Iyy' : Real = 0.3723953238821935;
                                attribute Izz : Real = 0.9761404323672223;
                                attribute 'σ_Izz' : Real = 0.37017423652493897;
                                attribute Ixy : Real = -0.04433959896401238;
                                attribute 'σ_Ixy' : Real = 0.02351283871158888;
                                attribute Ixz : Real = 0.05027237609822839;
                                attribute 'σ_Ixz' : Real = 0.022566176940390956;
                                attribute Iyz : Real = -9.845609253663632e-4;
                                attribute 'σ_Iyz' : Real = 0.02209918015384651;
                            }
                            part <'C.1.1.1.1.3.1.3'> 'Part 40' {
                                attribute POIconv : String = "-";
                                attribute Ipoint : Boolean = false;
                                attribute mass : Real = 0.40549652369623074;
                                attribute 'σ_mass' : Real = 0.28909372274994966;
                                attribute Cx : Real = 22.764458088204265;
                                attribute 'σ_Cx' : Real = 28.721044428837228;
                                attribute Cy : Real = -58.645621640607715;
                                attribute 'σ_Cy' : Real = 28.23690002309109;
                                attribute Cz : Real = -0.36920011043548584;
                                attribute 'σ_Cz' : Real = 29.057750463592832;
                                attribute Ixx : Real = 0.4741372858970175;
                                attribute 'σ_Ixx' : Real = 0.37074144170588635;
                                attribute Iyy : Real = 0.47921536567576256;
                                attribute 'σ_Iyy' : Real = 0.3723953238821935;
                                attribute Izz : Real = 0.4957670874285284;
                                attribute 'σ_Izz' : Real = 0.37017423652493897;
                                attribute Ixy : Real = -0.02011384283695799;
                                attribute 'σ_Ixy' : Real = 0.02351283871158888;
                                attribute Ixz : Real = -0.023900615622589542;
                                attribute 'σ_Ixz' : Real = 0.022566176940390956;
                                attribute Iyz : Real = 0.022832951488102535;
                                attribute 'σ_Iyz' : Real = 0.02209918015384651;
                            }
                            part <'C.1.1.1.1.3.1.4'> 'Part 41' {
                                attribute POIconv : String = "+";
                                attribute Ipoint : Boolean = false;
                                attribute mass : Real = 0.7099413991076872;
                                attribute 'σ_mass' : Real = 0.28909372274994966;
                                attribute Cx : Real = 97.23394718021154;
                                attribute 'σ_Cx' : Real = 28.721044428837228;
                                attribute Cy : Real = 44.218095391988754;
                                attribute 'σ_Cy' : Real = 28.23690002309109;
                                attribute Cz : Real = -6.449255114421248;
                                attribute 'σ_Cz' : Real = 29.057750463592832;
                                attribute Ixx : Real = 1.0227921520512584;
                                attribute 'σ_Ixx' : Real = 0.37074144170588635;
                                attribute Iyy : Real = 0.9486777174797226;
                                attribute 'σ_Iyy' : Real = 0.3723953238821935;
                                attribute Izz : Real = 0.9175400538101954;
                                attribute 'σ_Izz' : Real = 0.37017423652493897;
                                attribute Ixy : Real = 0.00217001469178261;
                                attribute 'σ_Ixy' : Real = 0.02351283871158888;
                                attribute Ixz : Real = -0.02200696957430804;
                                attribute 'σ_Ixz' : Real = 0.022566176940390956;
                                attribute Iyz : Real = 0.035404389834662875;
                                attribute 'σ_Iyz' : Real = 0.02209918015384651;
                            }
                            part <'C.1.1.1.1.3.1.5'> 'Part 42' {
                                attribute POIconv : String = "-";
                                attribute Ipoint : Boolean = false;
                                attribute mass : Real = 0.5422065042119939;
                                attribute 'σ_mass' : Real = 0.28909372274994966;
                                attribute Cx : Real = 8.036752883344889;
                                attribute 'σ_Cx' : Real = 28.721044428837228;
                                attribute Cy : Real = 59.67299812473357;
                                attribute 'σ_Cy' : Real = 28.23690002309109;
                                attribute Cz : Real = -6.505430908873677;
                                attribute 'σ_Cz' : Real = 29.057750463592832;
                                attribute Ixx : Real = 0.7466881832263661;
                                attribute 'σ_Ixx' : Real = 0.37074144170588635;
                                attribute Iyy : Real = 0.702733627768533;
                                attribute 'σ_Iyy' : Real = 0.3723953238821935;
                                attribute Izz : Real = 0.7751268247199941;
                                attribute 'σ_Izz' : Real = 0.37017423652493897;
                                attribute Ixy : Real = 0.05699878736535637;
                                attribute 'σ_Ixy' : Real = 0.02351283871158888;
                                attribute Ixz : Real = 0.010630338942310573;
                                attribute 'σ_Ixz' : Real = 0.022566176940390956;
                                attribute Iyz : Real = 0.014773749222682722;
                                attribute 'σ_Iyz' : Real = 0.02209918015384651;
                            }
                        }
                        part <'C.1.1.1.1.3.2'> 'Subassembly 12' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.3.2.1'> 'Part 43' {
                                attribute POIconv : String = "+";
                                attribute Ipoint : Boolean = false;
                                attribute mass : Real = 0.26679534564120694;
                                attribute 'σ_mass' : Real = 0.28909372274994966;
                                attribute Cx : Real = -42.3387766815722;
                                attribute 'σ_Cx' : Real = 28.721044428837228;
                                attribute Cy : Real = 78.68632734753191;
                                attribute 'σ_Cy' : Real = 28.23690002309109;
                                attribute Cz : Real = 88.77342287451029;
                                attribute 'σ_Cz' : Real = 29.057750463592832;
                                attribute Ixx : Real = 0.3653197529961761;
                                attribute 'σ_Ixx' : Real = 0.37074144170588635;
                                attribute Iyy : Real = 0.3586917892626038;
                                attribute 'σ_Iyy' : Real = 0.3723953238821935;
                                attribute Izz : Real = 0.36761850142652697;
                                attribute 'σ_Izz' : Real = 0.37017423652493897;
                                attribute Ixy : Real = 3.9382814022135513e-4;
                                attribute 'σ_Ixy' : Real = 0.02351283871158888;
                                attribute Ixz : Real = 0.0012502970559738385;
                                attribute 'σ_Ixz' : Real = 0.022566176940390956;
                                attribute Iyz : Real = 0.004304778296552754;
                                attribute 'σ_Iyz' : Real = 0.02209918015384651;
                            }
                            part <'C.1.1.1.1.3.2.2'> 'Part 44' {
                                attribute POIconv : String = "+";
                                attribute Ipoint : Boolean = false;
                                attribute mass : Real = 0.6980398972455878;
                                attribute 'σ_mass' : Real = 0.28909372274994966;
                                attribute Cx : Real = -95.86311224848032;
                                attribute 'σ_Cx' : Real = 28.721044428837228;
                                attribute Cy : Real = -85.33331966027617;
                                attribute 'σ_Cy' : Real = 28.23690002309109;
                                attribute Cz : Real = -77.88576940074563;
                                attribute 'σ_Cz' : Real = 29.057750463592832;
                                attribute Ixx : Real = 1.080027327993266;
                                attribute 'σ_Ixx' : Real = 0.37074144170588635;
                                attribute Iyy : Real = 1.0201478091470655;
                                attribute 'σ_Iyy' : Real = 0.3723953238821935;
                                attribute Izz : Real = 0.9847903172482783;
                                attribute 'σ_Izz' : Real = 0.37017423652493897;
                                attribute Ixy : Real = -0.0490600347873377;
                                attribute 'σ_Ixy' : Real = 0.02351283871158888;
                                attribute Ixz : Real = -0.004266232778660036;
                                attribute 'σ_Ixz' : Real = 0.022566176940390956;
                                attribute Iyz : Real = -0.002338528783125025;
                                attribute 'σ_Iyz' : Real = 0.02209918015384651;
                            }
                            part <'C.1.1.1.1.3.2.3'> 'Part 45' {
                                attribute POIconv : String = "+";
                                attribute Ipoint : Boolean = false;
                                attribute mass : Real = 0.2595371792665683;
                                attribute 'σ_mass' : Real = 0.28909372274994966;
                                attribute Cx : Real = -70.06597449071705;
                                attribute 'σ_Cx' : Real = 28.721044428837228;
                                attribute Cy : Real = 78.65505330264568;
                                attribute 'σ_Cy' : Real = 28.23690002309109;
                                attribute Cz : Real = 47.46227124705911;
                                attribute 'σ_Cz' : Real = 29.057750463592832;
                                attribute Ixx : Real = 0.3640537628749178;
                                attribute 'σ_Ixx' : Real = 0.37074144170588635;
                                attribute Iyy : Real = 0.32188428910221606;
                                attribute 'σ_Iyy' : Real = 0.3723953238821935;
                                attribute Izz : Real = 0.3221347434432082;
                                attribute 'σ_Izz' : Real = 0.37017423652493897;
                                attribute Ixy : Real = 0.012409809486083848;
                                attribute 'σ_Ixy' : Real = 0.02351283871158888;
                                attribute Ixz : Real = -0.010835166549848991;
                                attribute 'σ_Ixz' : Real = 0.022566176940390956;
                                attribute Iyz : Real = -0.02253309996441543;
                                attribute 'σ_Iyz' : Real = 0.02209918015384651;
                            }
                            part <'C.1.1.1.1.3.2.4'> 'Part 46' {
                                attribute POIconv : String = "-";
                                attribute Ipoint : Boolean = false;
                                attribute mass : Real = 0.4108353999129031;
                                attribute 'σ_mass' : Real = 0.28909372274994966;
                                attribute Cx : Real = -47.83589071594179;
                                attribute 'σ_Cx' : Real = 28.721044428837228;
                                attribute Cy : Real = 78.8680911064148;
                                attribute 'σ_Cy' : Real = 28.23690002309109;
                                attribute Cz : Real = -21.74429977312684;
                                attribute 'σ_Cz' : Real = 29.057750463592832;
                                attribute Ixx : Real = 0.5047676335272006;
                                attribute 'σ_Ixx' : Real = 0.37074144170588635;
                                attribute Iyy : Real = 0.4809239587456611;
                                attribute 'σ_Iyy' : Real = 0.3723953238821935;
                                attribute Izz : Real = 0.4511124983651898;
                                attribute 'σ_Izz' : Real = 0.37017423652493897;
                                attribute Ixy : Real = -0.022156578472749162;
                                attribute 'σ_Ixy' : Real = 0.02351283871158888;
                                attribute Ixz : Real = 0.008016888608753586;
                                attribute 'σ_Ixz' : Real = 0.022566176940390956;
                                attribute Iyz : Real = 0.01539359014453958;
                                attribute 'σ_Iyz' : Real = 0.02209918015384651;
                            }
                        }
                        part <'C.1.1.1.1.3.3'> 'Subassembly 13' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.1.3.3.1'> 'Part 47' {
                                attribute POIconv : String = "-";
                                attribute Ipoint : Boolean = false;
                                attribute mass : Real = 0.634985460388707;
                                attribute 'σ_mass' : Real = 0.28909372274994966;
                                attribute Cx : Real = -18.305410584434867;
                                attribute 'σ_Cx' : Real = 28.721044428837228;
                                attribute Cy : Real = 17.44096572510898;
                                attribute 'σ_Cy' : Real = 28.23690002309109;
                                attribute Cz : Real = -1.0011337231844664;
                                attribute 'σ_Cz' : Real = 29.057750463592832;
                                attribute Ixx : Real = 0.8913730410721291;
                                attribute 'σ_Ixx' : Real = 0.37074144170588635;
                                attribute Iyy : Real = 0.8316278723741327;
                                attribute 'σ_Iyy' : Real = 0.3723953238821935;
                                attribute Izz : Real = 0.7318105744566464;
                                attribute 'σ_Izz' : Real = 0.37017423652493897;
                                attribute Ixy : Real = -0.0914367115521594;
                                attribute 'σ_Ixy' : Real = 0.02351283871158888;
                                attribute Ixz : Real = -0.006115827586336267;
                                attribute 'σ_Ixz' : Real = 0.022566176940390956;
                                attribute Iyz : Real = -0.04307338553088562;
                                attribute 'σ_Iyz' : Real = 0.02209918015384651;
                            }
                            part <'C.1.1.1.1.3.3.2'> 'Part 48' {
                                attribute POIconv : String = "+";
                                attribute Ipoint : Boolean = false;
                                attribute mass : Real = 0.590746205801377;
                                attribute 'σ_mass' : Real = 0.28909372274994966;
                                attribute Cx : Real = -22.072292352095246;
                                attribute 'σ_Cx' : Real = 28.721044428837228;
                                attribute Cy : Real = -98.88322618789971;
                                attribute 'σ_Cy' : Real = 28.23690002309109;
                                attribute Cz : Real = 7.5308040250092745;
                                attribute 'σ_Cz' : Real = 29.057750463592832;
                                attribute Ixx : Real = 0.6452928842272114;
                                attribute 'σ_Ixx' : Real = 0.37074144170588635;
                                attribute Iyy : Real = 0.7347706669129337;
                                attribute 'σ_Iyy' : Real = 0.3723953238821935;
                                attribute Izz : Real = 0.7089715318353176;
                                attribute 'σ_Izz' : Real = 0.37017423652493897;
                                attribute Ixy : Real = 0.0022180955597196797;
                                attribute 'σ_Ixy' : Real = 0.02351283871158888;
                                attribute Ixz : Real = 0.05961121056537379;
                                attribute 'σ_Ixz' : Real = 0.022566176940390956;
                                attribute Iyz : Real = -0.03234114015540693;
                                attribute 'σ_Iyz' : Real = 0.02209918015384651;
                            }
                        }
                    }
                }
                part <'C.1.1.1.2'> 'Subsystem 2' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.1.2.1'> 'Assembly 4' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.1.2.1.1'> 'Subassembly 14' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.2.1.1.1'> 'Part 49' {
                                attribute POIconv : String = "+";
                                attribute Ipoint : Boolean = false;
                                attribute mass : Real = 0.5218669216977433;
                                attribute 'σ_mass' : Real = 0.28909372274994966;
                                attribute Cx : Real = -94.74931973963976;
                                attribute 'σ_Cx' : Real = 28.721044428837228;
                                attribute Cy : Real = -5.726963002234697;
                                attribute 'σ_Cy' : Real = 28.23690002309109;
                                attribute Cz : Real = -89.35355059802532;
                                attribute 'σ_Cz' : Real = 29.057750463592832;
                                attribute Ixx : Real = 0.7684898093613619;
                                attribute 'σ_Ixx' : Real = 0.37074144170588635;
                                attribute Iyy : Real = 0.7282929874850371;
                                attribute 'σ_Iyy' : Real = 0.3723953238821935;
                                attribute Izz : Real = 0.7585793360053665;
                                attribute 'σ_Izz' : Real = 0.37017423652493897;
                                attribute Ixy : Real = 0.006459898419936109;
                                attribute 'σ_Ixy' : Real = 0.02351283871158888;
                                attribute Ixz : Real = 1.8921784647928908e-4;
                                attribute 'σ_Ixz' : Real = 0.022566176940390956;
                                attribute Iyz : Real = -0.009041759965398723;
                                attribute 'σ_Iyz' : Real = 0.02209918015384651;
                            }
                            part <'C.1.1.1.2.1.1.2'> 'Part 50' {
                                attribute POIconv : String = "+";
                                attribute Ipoint : Boolean = false;
                                attribute mass : Real = 0.7470984810600058;
                                attribute 'σ_mass' : Real = 0.28909372274994966;
                                attribute Cx : Real = -59.83006777241826;
                                attribute 'σ_Cx' : Real = 28.721044428837228;
                                attribute Cy : Real = 82.42514738813043;
                                attribute 'σ_Cy' : Real = 28.23690002309109;
                                attribute Cz : Real = -69.5905792992562;
                                attribute 'σ_Cz' : Real = 29.057750463592832;
                                attribute Ixx : Real = 0.9216839362577209;
                                attribute 'σ_Ixx' : Real = 0.37074144170588635;
                                attribute Iyy : Real = 0.9411256344934409;
                                attribute 'σ_Iyy' : Real = 0.3723953238821935;
                                attribute Izz : Real = 0.7732515990727997;
                                attribute 'σ_Izz' : Real = 0.37017423652493897;
                                attribute Ixy : Real = 0.06294775827641705;
                                attribute 'σ_Ixy' : Real = 0.02351283871158888;
                                attribute Ixz : Real = 0.0447360618638525;
                                attribute 'σ_Ixz' : Real = 0.022566176940390956;
                                attribute Iyz : Real = 0.01937433844389028;
                                attribute 'σ_Iyz' : Real = 0.02209918015384651;
                            }
                            part <'C.1.1.1.2.1.1.3'> 'Part 51' {
                                attribute POIconv : String = "+";
                                attribute Ipoint : Boolean = false;
                                attribute mass : Real = 0.2837263432755135;
                                attribute 'σ_mass' : Real = 0.28909372274994966;
                                attribute Cx : Real = -73.3916062861681;
                                attribute 'σ_Cx' : Real = 28.721044428837228;
                                attribute Cy : Real = -0.018426543101668358;
                                attribute 'σ_Cy' : Real = 28.23690002309109;
                                attribute Cz : Real = -76.85401369817555;
                                attribute 'σ_Cz' : Real = 29.057750463592832;
                                attribute Ixx : Real = 0.42319231989813316;
                                attribute 'σ_Ixx' : Real = 0.37074144170588635;
                                attribute Iyy : Real = 0.42173626068599446;
                                attribute 'σ_Iyy' : Real = 0.3723953238821935;
                                attribute Izz : Real = 0.40446692907991805;
                                attribute 'σ_Izz' : Real = 0.37017423652493897;
                                attribute Ixy : Real = 0.003297595921162696;
                                attribute 'σ_Ixy' : Real = 0.02351283871158888;
                                attribute Ixz : Real = 0.0054009229062743766;
                                attribute 'σ_Ixz' : Real = 0.022566176940390956;
                                attribute Iyz : Real = 0.002900604633331045;
                                attribute 'σ_Iyz' : Real = 0.02209918015384651;
                            }
                        }
                        part <'C.1.1.1.2.1.2'> 'Subassembly 15' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.2.1.2.1'> 'Part 52' {
                                attribute POIconv : String = "-";
                                attribute Ipoint : Boolean = false;
                                attribute mass : Real = 0.3497393322051503;
                                attribute 'σ_mass' : Real = 0.28909372274994966;
                                attribute Cx : Real = 90.42232581414282;
                                attribute 'σ_Cx' : Real = 28.721044428837228;
                                attribute Cy : Real = -73.29918104223907;
                                attribute 'σ_Cy' : Real = 28.23690002309109;
                                attribute Cz : Real = 70.73393822647631;
                                attribute 'σ_Cz' : Real = 29.057750463592832;
                                attribute Ixx : Real = 0.48129434662801535;
                                attribute 'σ_Ixx' : Real = 0.37074144170588635;
                                attribute Iyy : Real = 0.42940927822364294;
                                attribute 'σ_Iyy' : Real = 0.3723953238821935;
                                attribute Izz : Real = 0.44369393395620965;
                                attribute 'σ_Izz' : Real = 0.37017423652493897;
                                attribute Ixy : Real = -0.059034113629182816;
                                attribute 'σ_Ixy' : Real = 0.02351283871158888;
                                attribute Ixz : Real = 0.0015432537273156236;
                                attribute 'σ_Ixz' : Real = 0.022566176940390956;
                                attribute Iyz : Real = 0.003548681987400733;
                                attribute 'σ_Iyz' : Real = 0.02209918015384651;
                            }
                            part <'C.1.1.1.2.1.2.2'> 'Part 53' {
                                attribute POIconv : String = "+";
                                attribute Ipoint : Boolean = false;
                                attribute mass : Real = 0.8794165587418247;
                                attribute 'σ_mass' : Real = 0.28909372274994966;
                                attribute Cx : Real = -29.14036763831973;
                                attribute 'σ_Cx' : Real = 28.721044428837228;
                                attribute Cy : Real = 26.189054362475872;
                                attribute 'σ_Cy' : Real = 28.23690002309109;
                                attribute Cz : Real = 27.455057902261615;
                                attribute 'σ_Cz' : Real = 29.057750463592832;
                                attribute Ixx : Real = 1.2116122134738396;
                                attribute 'σ_Ixx' : Real = 0.37074144170588635;
                                attribute Iyy : Real = 1.2426066559451039;
                                attribute 'σ_Iyy' : Real = 0.3723953238821935;
                                attribute Izz : Real = 1.2076981166633518;
                                attribute 'σ_Izz' : Real = 0.37017423652493897;
                                attribute Ixy : Real = -0.02881338669679237;
                                attribute 'σ_Ixy' : Real = 0.02351283871158888;
                                attribute Ixz : Real = 0.02638315617137038;
                                attribute 'σ_Ixz' : Real = 0.022566176940390956;
                                attribute Iyz : Real = 0.038840310391896185;
                                attribute 'σ_Iyz' : Real = 0.02209918015384651;
                            }
                            part <'C.1.1.1.2.1.2.3'> 'Part 54' {
                                attribute POIconv : String = "-";
                                attribute Ipoint : Boolean = false;
                                attribute mass : Real = 0.669483742558863;
                                attribute 'σ_mass' : Real = 0.28909372274994966;
                                attribute Cx : Real = 58.65882928483188;
                                attribute 'σ_Cx' : Real = 28.721044428837228;
                                attribute Cy : Real = 86.78798843175173;
                                attribute 'σ_Cy' : Real = 28.23690002309109;
                                attribute Cz : Real = 68.53770180605352;
                                attribute 'σ_Cz' : Real = 29.057750463592832;
                                attribute Ixx : Real = 0.8660795315379488;
                                attribute 'σ_Ixx' : Real = 0.37074144170588635;
                                attribute Iyy : Real = 0.789060856532035;
                                attribute 'σ_Iyy' : Real = 0.3723953238821935;
                                attribute Izz : Real = 0.8011005056184142;
                                attribute 'σ_Izz' : Real = 0.37017423652493897;
                                attribute Ixy : Real = -0.0047560944535491225;
                                attribute 'σ_Ixy' : Real = 0.02351283871158888;
                                attribute Ixz : Real = 0.04915970114870735;
                                attribute 'σ_Ixz' : Real = 0.022566176940390956;
                                attribute Iyz : Real = -0.02358444629675939;
                                attribute 'σ_Iyz' : Real = 0.02209918015384651;
                            }
                            part <'C.1.1.1.2.1.2.4'> 'Part 55' {
                                attribute POIconv : String = "+";
                                attribute Ipoint : Boolean = false;
                                attribute mass : Real = 0.9484717072607018;
                                attribute 'σ_mass' : Real = 0.28909372274994966;
                                attribute Cx : Real = 95.47817502170801;
                                attribute 'σ_Cx' : Real = 28.721044428837228;
                                attribute Cy : Real = 62.14317181147635;
                                attribute 'σ_Cy' : Real = 28.23690002309109;
                                attribute Cz : Real = -65.79681993462145;
                                attribute 'σ_Cz' : Real = 29.057750463592832;
                                attribute Ixx : Real = 1.2546791853375412;
                                attribute 'σ_Ixx' : Real = 0.37074144170588635;
                                attribute Iyy : Real = 1.226248233993727;
                                attribute 'σ_Iyy' : Real = 0.3723953238821935;
                                attribute Izz : Real = 1.1748731285389662;
                                attribute 'σ_Izz' : Real = 0.37017423652493897;
                                attribute Ixy : Real = -0.023894569743970417;
                                attribute 'σ_Ixy' : Real = 0.02351283871158888;
                                attribute Ixz : Real = 0.030223377798457254;
                                attribute 'σ_Ixz' : Real = 0.022566176940390956;
                                attribute Iyz : Real = -0.06763778130919393;
                                attribute 'σ_Iyz' : Real = 0.02209918015384651;
                            }
                        }
                        part <'C.1.1.1.2.1.3'> 'Subassembly 16' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.2.1.3.1'> 'Part 56' {
                                attribute POIconv : String = "-";
                                attribute Ipoint : Boolean = false;
                                attribute mass : Real = 0.4260679590126965;
                                attribute 'σ_mass' : Real = 0.28909372274994966;
                                attribute Cx : Real = 19.299472263082862;
                                attribute 'σ_Cx' : Real = 28.721044428837228;
                                attribute Cy : Real = -37.00572685338557;
                                attribute 'σ_Cy' : Real = 28.23690002309109;
                                attribute Cz : Real = 11.499222228303552;
                                attribute 'σ_Cz' : Real = 29.057750463592832;
                                attribute Ixx : Real = 0.5624370538017689;
                                attribute 'σ_Ixx' : Real = 0.37074144170588635;
                                attribute Iyy : Real = 0.5036909703258995;
                                attribute 'σ_Iyy' : Real = 0.3723953238821935;
                                attribute Izz : Real = 0.5368108141322708;
                                attribute 'σ_Izz' : Real = 0.37017423652493897;
                                attribute Ixy : Real = -0.013077850299350869;
                                attribute 'σ_Ixy' : Real = 0.02351283871158888;
                                attribute Ixz : Real = -0.004149335543551784;
                                attribute 'σ_Ixz' : Real = 0.022566176940390956;
                                attribute Iyz : Real = 0.03063573249296033;
                                attribute 'σ_Iyz' : Real = 0.02209918015384651;
                            }
                            part <'C.1.1.1.2.1.3.2'> 'Part 57' {
                                attribute POIconv : String = "-";
                                attribute Ipoint : Boolean = false;
                                attribute mass : Real = 0.7554786639297381;
                                attribute 'σ_mass' : Real = 0.28909372274994966;
                                attribute Cx : Real = 5.929126497358084;
                                attribute 'σ_Cx' : Real = 28.721044428837228;
                                attribute Cy : Real = 52.547507267445326;
                                attribute 'σ_Cy' : Real = 28.23690002309109;
                                attribute Cz : Real = -4.727424122393131;
                                attribute 'σ_Cz' : Real = 29.057750463592832;
                                attribute Ixx : Real = 1.0251652487671645;
                                attribute 'σ_Ixx' : Real = 0.37074144170588635;
                                attribute Iyy : Real = 0.9811623597373842;
                                attribute 'σ_Iyy' : Real = 0.3723953238821935;
                                attribute Izz : Real = 1.002838146866474;
                                attribute 'σ_Izz' : Real = 0.37017423652493897;
                                attribute Ixy : Real = -0.07430656772976525;
                                attribute 'σ_Ixy' : Real = 0.02351283871158888;
                                attribute Ixz : Real = 0.08615317106975548;
                                attribute 'σ_Ixz' : Real = 0.022566176940390956;
                                attribute Iyz : Real = -0.06522962006746337;
                                attribute 'σ_Iyz' : Real = 0.02209918015384651;
                            }
                            part <'C.1.1.1.2.1.3.3'> 'Part 58' {
                                attribute POIconv : String = "-";
                                attribute Ipoint : Boolean = false;
                                attribute mass : Real = 0.2523808718936052;
                                attribute 'σ_mass' : Real = 0.28909372274994966;
                                attribute Cx : Real = -51.382982172071934;
                                attribute 'σ_Cx' : Real = 28.721044428837228;
                                attribute Cy : Real = -96.5985853690654;
                                attribute 'σ_Cy' : Real = 28.23690002309109;
                                attribute Cz : Real = 71.31787086836994;
                                attribute 'σ_Cz' : Real = 29.057750463592832;
                                attribute Ixx : Real = 0.3371728688082054;
                                attribute 'σ_Ixx' : Real = 0.37074144170588635;
                                attribute Iyy : Real = 0.28081668905200063;
                                attribute 'σ_Iyy' : Real = 0.3723953238821935;
                                attribute Izz : Real = 0.2850610195326052;
                                attribute 'σ_Izz' : Real = 0.37017423652493897;
                                attribute Ixy : Real = 0.02310969099420511;
                                attribute 'σ_Ixy' : Real = 0.02351283871158888;
                                attribute Ixz : Real = -0.006070164475370973;
                                attribute 'σ_Ixz' : Real = 0.022566176940390956;
                                attribute Iyz : Real = -1.9415714886170636e-4;
                                attribute 'σ_Iyz' : Real = 0.02209918015384651;
                            }
                            part <'C.1.1.1.2.1.3.4'> 'Part 59' {
                                attribute POIconv : String = "-";
                                attribute Ipoint : Boolean = false;
                                attribute mass : Real = 0.9880897538557183;
                                attribute 'σ_mass' : Real = 0.28909372274994966;
                                attribute Cx : Real = 96.5033090673387;
                                attribute 'σ_Cx' : Real = 28.721044428837228;
                                attribute Cy : Real = -65.71766454726458;
                                attribute 'σ_Cy' : Real = 28.23690002309109;
                                attribute Cz : Real = 83.37932345457375;
                                attribute 'σ_Cz' : Real = 29.057750463592832;
                                attribute Ixx : Real = 1.2902819703811412;
                                attribute 'σ_Ixx' : Real = 0.37074144170588635;
                                attribute Iyy : Real = 1.311263679631395;
                                attribute 'σ_Iyy' : Real = 0.3723953238821935;
                                attribute Izz : Real = 1.3765730656949615;
                                attribute 'σ_Izz' : Real = 0.37017423652493897;
                                attribute Ixy : Real = -0.020929296776081862;
                                attribute 'σ_Ixy' : Real = 0.02351283871158888;
                                attribute Ixz : Real = -0.004299549732964904;
                                attribute 'σ_Ixz' : Real = 0.022566176940390956;
                                attribute Iyz : Real = 3.507446615881047e-4;
                                attribute 'σ_Iyz' : Real = 0.02209918015384651;
                            }
                            part <'C.1.1.1.2.1.3.5'> 'Part 60' {
                                attribute POIconv : String = "-";
                                attribute Ipoint : Boolean = false;
                                attribute mass : Real = 0.2704563324097544;
                                attribute 'σ_mass' : Real = 0.28909372274994966;
                                attribute Cx : Real = -51.99252562597394;
                                attribute 'σ_Cx' : Real = 28.721044428837228;
                                attribute Cy : Real = -63.93344886600971;
                                attribute 'σ_Cy' : Real = 28.23690002309109;
                                attribute Cz : Real = -28.686578618362546;
                                attribute 'σ_Cz' : Real = 29.057750463592832;
                                attribute Ixx : Real = 0.34860902662002913;
                                attribute 'σ_Ixx' : Real = 0.37074144170588635;
                                attribute Iyy : Real = 0.359321042096914;
                                attribute 'σ_Iyy' : Real = 0.3723953238821935;
                                attribute Izz : Real = 0.35927295925538605;
                                attribute 'σ_Izz' : Real = 0.37017423652493897;
                                attribute Ixy : Real = 9.10367688005906e-4;
                                attribute 'σ_Ixy' : Real = 0.02351283871158888;
                                attribute Ixz : Real = -0.0018871768727899488;
                                attribute 'σ_Ixz' : Real = 0.022566176940390956;
                                attribute Iyz : Real = 8.024887626780901e-5;
                                attribute 'σ_Iyz' : Real = 0.02209918015384651;
                            }
                        }
                        part <'C.1.1.1.2.1.4'> 'Subassembly 17' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.2.1.4.1'> 'Part 61' {
                                attribute POIconv : String = "+";
                                attribute Ipoint : Boolean = false;
                                attribute mass : Real = 0.271978923043469;
                                attribute 'σ_mass' : Real = 0.28909372274994966;
                                attribute Cx : Real = -60.715602710843086;
                                attribute 'σ_Cx' : Real = 28.721044428837228;
                                attribute Cy : Real = -25.645897444337606;
                                attribute 'σ_Cy' : Real = 28.23690002309109;
                                attribute Cz : Real = 25.933133577927947;
                                attribute 'σ_Cz' : Real = 29.057750463592832;
                                attribute Ixx : Real = 0.34442468234819473;
                                attribute 'σ_Ixx' : Real = 0.37074144170588635;
                                attribute Iyy : Real = 0.34263607584570394;
                                attribute 'σ_Iyy' : Real = 0.3723953238821935;
                                attribute Izz : Real = 0.35338258294955327;
                                attribute 'σ_Izz' : Real = 0.37017423652493897;
                                attribute Ixy : Real = 6.889441683797253e-4;
                                attribute 'σ_Ixy' : Real = 0.02351283871158888;
                                attribute Ixz : Real = 0.008059866703174554;
                                attribute 'σ_Ixz' : Real = 0.022566176940390956;
                                attribute Iyz : Real = -2.2100830910817712e-4;
                                attribute 'σ_Iyz' : Real = 0.02209918015384651;
                            }
                            part <'C.1.1.1.2.1.4.2'> 'Part 62' {
                                attribute POIconv : String = "+";
                                attribute Ipoint : Boolean = false;
                                attribute mass : Real = 0.3950687476214953;
                                attribute 'σ_mass' : Real = 0.28909372274994966;
                                attribute Cx : Real = -56.759323040023446;
                                attribute 'σ_Cx' : Real = 28.721044428837228;
                                attribute Cy : Real = -72.16552658937871;
                                attribute 'σ_Cy' : Real = 28.23690002309109;
                                attribute Cz : Real = 24.581784661859274;
                                attribute 'σ_Cz' : Real = 29.057750463592832;
                                attribute Ixx : Real = 0.5900102928380874;
                                attribute 'σ_Ixx' : Real = 0.37074144170588635;
                                attribute Iyy : Real = 0.5960194067137053;
                                attribute 'σ_Iyy' : Real = 0.3723953238821935;
                                attribute Izz : Real = 0.6086748960895008;
                                attribute 'σ_Izz' : Real = 0.37017423652493897;
                                attribute Ixy : Real = -0.002011022898645948;
                                attribute 'σ_Ixy' : Real = 0.02351283871158888;
                                attribute Ixz : Real = -0.012879150202092043;
                                attribute 'σ_Ixz' : Real = 0.022566176940390956;
                                attribute Iyz : Real = -0.01806574977154448;
                                attribute 'σ_Iyz' : Real = 0.02209918015384651;
                            }
                            part <'C.1.1.1.2.1.4.3'> 'Part 63' {
                                attribute POIconv : String = "-";
                                attribute Ipoint : Boolean = false;
                                attribute mass : Real = 0.45132643448049203;
                                attribute 'σ_mass' : Real = 0.28909372274994966;
                                attribute Cx : Real = 22.585051227360964;
                                attribute 'σ_Cx' : Real = 28.721044428837228;
                                attribute Cy : Real = -56.67813732288778;
                                attribute 'σ_Cy' : Real = 28.23690002309109;
                                attribute Cz : Real = -23.093143943697214;
                                attribute 'σ_Cz' : Real = 29.057750463592832;
                                attribute Ixx : Real = 0.6592479832442258;
                                attribute 'σ_Ixx' : Real = 0.37074144170588635;
                                attribute Iyy : Real = 0.5905540003939;
                                attribute 'σ_Iyy' : Real = 0.3723953238821935;
                                attribute Izz : Real = 0.604170243779568;
                                attribute 'σ_Izz' : Real = 0.37017423652493897;
                                attribute Ixy : Real = 0.02751133215598491;
                                attribute 'σ_Ixy' : Real = 0.02351283871158888;
                                attribute Ixz : Real = 0.046859209745853336;
                                attribute 'σ_Ixz' : Real = 0.022566176940390956;
                                attribute Iyz : Real = 0.018318092065488015;
                                attribute 'σ_Iyz' : Real = 0.02209918015384651;
                            }
                        }
                    }
                    part <'C.1.1.1.2.2'> 'Assembly 5' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.1.2.2.1'> 'Subassembly 18' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.2.2.1.1'> 'Part 64' {
                                attribute POIconv : String = "-";
                                attribute Ipoint : Boolean = false;
                                attribute mass : Real = 0.9828562500306871;
                                attribute 'σ_mass' : Real = 0.28909372274994966;
                                attribute Cx : Real = -33.119674399495125;
                                attribute 'σ_Cx' : Real = 28.721044428837228;
                                attribute Cy : Real = 59.440611535683274;
                                attribute 'σ_Cy' : Real = 28.23690002309109;
                                attribute Cz : Real = -31.26640967093408;
                                attribute 'σ_Cz' : Real = 29.057750463592832;
                                attribute Ixx : Real = 0.9128730607994954;
                                attribute 'σ_Ixx' : Real = 0.37074144170588635;
                                attribute Iyy : Real = 1.0531611829184802;
                                attribute 'σ_Iyy' : Real = 0.3723953238821935;
                                attribute Izz : Real = 0.9831509706365098;
                                attribute 'σ_Izz' : Real = 0.37017423652493897;
                                attribute Ixy : Real = 0.03615669069591548;
                                attribute 'σ_Ixy' : Real = 0.02351283871158888;
                                attribute Ixz : Real = -3.9552185897018824e-4;
                                attribute 'σ_Ixz' : Real = 0.022566176940390956;
                                attribute Iyz : Real = -0.005404154703424167;
                                attribute 'σ_Iyz' : Real = 0.02209918015384651;
                            }
                            part <'C.1.1.1.2.2.1.2'> 'Part 65' {
                                attribute POIconv : String = "-";
                                attribute Ipoint : Boolean = false;
                                attribute mass : Real = 0.12627824692009018;
                                attribute 'σ_mass' : Real = 0.28909372274994966;
                                attribute Cx : Real = 76.15239098668098;
                                attribute 'σ_Cx' : Real = 28.721044428837228;
                                attribute Cy : Real = 30.404927721247077;
                                attribute 'σ_Cy' : Real = 28.23690002309109;
                                attribute Cz : Real = -55.07273371331394;
                                attribute 'σ_Cz' : Real = 29.057750463592832;
                                attribute Ixx : Real = 0.17865814493628002;
                                attribute 'σ_Ixx' : Real = 0.37074144170588635;
                                attribute Iyy : Real = 0.18449415187102183;
                                attribute 'σ_Iyy' : Real = 0.3723953238821935;
                                attribute Izz : Real = 0.17750760496726264;
                                attribute 'σ_Izz' : Real = 0.37017423652493897;
                                attribute Ixy : Real = 1.241612111880214e-4;
                                attribute 'σ_Ixy' : Real = 0.02351283871158888;
                                attribute Ixz : Real = -0.0037461530554957737;
                                attribute 'σ_Ixz' : Real = 0.022566176940390956;
                                attribute Iyz : Real = 3.9726211620278037e-4;
                                attribute 'σ_Iyz' : Real = 0.02209918015384651;
                            }
                            part <'C.1.1.1.2.2.1.3'> 'Part 66' {
                                attribute POIconv : String = "-";
                                attribute Ipoint : Boolean = false;
                                attribute mass : Real = 0.7898205938499887;
                                attribute 'σ_mass' : Real = 0.28909372274994966;
                                attribute Cx : Real = -38.762542232871056;
                                attribute 'σ_Cx' : Real = 28.721044428837228;
                                attribute Cy : Real = -34.38987135887146;
                                attribute 'σ_Cy' : Real = 28.23690002309109;
                                attribute Cz : Real = 73.17715771496296;
                                attribute 'σ_Cz' : Real = 29.057750463592832;
                                attribute Ixx : Real = 0.9091259717832947;
                                attribute 'σ_Ixx' : Real = 0.37074144170588635;
                                attribute Iyy : Real = 0.9063963777014893;
                                attribute 'σ_Iyy' : Real = 0.3723953238821935;
                                attribute Izz : Real = 1.009195772290123;
                                attribute 'σ_Izz' : Real = 0.37017423652493897;
                                attribute Ixy : Real = -0.017849097830616653;
                                attribute 'σ_Ixy' : Real = 0.02351283871158888;
                                attribute Ixz : Real = 0.004864170464651306;
                                attribute 'σ_Ixz' : Real = 0.022566176940390956;
                                attribute Iyz : Real = -0.03145188336427279;
                                attribute 'σ_Iyz' : Real = 0.02209918015384651;
                            }
                            part <'C.1.1.1.2.2.1.4'> 'Part 67' {
                                attribute POIconv : String = "+";
                                attribute Ipoint : Boolean = false;
                                attribute mass : Real = 0.36688056779210454;
                                attribute 'σ_mass' : Real = 0.28909372274994966;
                                attribute Cx : Real = -64.71347692422569;
                                attribute 'σ_Cx' : Real = 28.721044428837228;
                                attribute Cy : Real = -93.05689525790513;
                                attribute 'σ_Cy' : Real = 28.23690002309109;
                                attribute Cz : Real = -17.94682159088552;
                                attribute 'σ_Cz' : Real = 29.057750463592832;
                                attribute Ixx : Real = 0.47382907252434264;
                                attribute 'σ_Ixx' : Real = 0.37074144170588635;
                                attribute Iyy : Real = 0.455105099554942;
                                attribute 'σ_Iyy' : Real = 0.3723953238821935;
                                attribute Izz : Real = 0.5438434321860209;
                                attribute 'σ_Izz' : Real = 0.37017423652493897;
                                attribute Ixy : Real = -0.03237732142462442;
                                attribute 'σ_Ixy' : Real = 0.02351283871158888;
                                attribute Ixz : Real = 0.012749409023009622;
                                attribute 'σ_Ixz' : Real = 0.022566176940390956;
                                attribute Iyz : Real = 0.011452654694815215;
                                attribute 'σ_Iyz' : Real = 0.02209918015384651;
                            }
                            part <'C.1.1.1.2.2.1.5'> 'Part 68' {
                                attribute POIconv : String = "+";
                                attribute Ipoint : Boolean = false;
                                attribute mass : Real = 0.7198834493104368;
                                attribute 'σ_mass' : Real = 0.28909372274994966;
                                attribute Cx : Real = -21.555669093504548;
                                attribute 'σ_Cx' : Real = 28.721044428837228;
                                attribute Cy : Real = -65.7669379375875;
                                attribute 'σ_Cy' : Real = 28.23690002309109;
                                attribute Cz : Real = 62.732501514256;
                                attribute 'σ_Cz' : Real = 29.057750463592832;
                                attribute Ixx : Real = 0.9597635211222975;
                                attribute 'σ_Ixx' : Real = 0.37074144170588635;
                                attribute Iyy : Real = 1.011073047390852;
                                attribute 'σ_Iyy' : Real = 0.3723953238821935;
                                attribute Izz : Real = 1.0585198933053375;
                                attribute 'σ_Izz' : Real = 0.37017423652493897;
                                attribute Ixy : Real = 0.012916934232068049;
                                attribute 'σ_Ixy' : Real = 0.02351283871158888;
                                attribute Ixz : Real = -0.04768159311665033;
                                attribute 'σ_Ixz' : Real = 0.022566176940390956;
                                attribute Iyz : Real = -0.04316320045199108;
                                attribute 'σ_Iyz' : Real = 0.02209918015384651;
                            }
                        }
                        part <'C.1.1.1.2.2.2'> 'Subassembly 19' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.2.2.2.1'> 'Part 69' {
                                attribute POIconv : String = "+";
                                attribute Ipoint : Boolean = false;
                                attribute mass : Real = 0.1236639610095881;
                                attribute 'σ_mass' : Real = 0.28909372274994966;
                                attribute Cx : Real = -2.366035059094429;
                                attribute 'σ_Cx' : Real = 28.721044428837228;
                                attribute Cy : Real = 98.62749241292477;
                                attribute 'σ_Cy' : Real = 28.23690002309109;
                                attribute Cz : Real = 71.87450714409351;
                                attribute 'σ_Cz' : Real = 29.057750463592832;
                                attribute Ixx : Real = 0.15674375452644598;
                                attribute 'σ_Ixx' : Real = 0.37074144170588635;
                                attribute Iyy : Real = 0.13430617816724458;
                                attribute 'σ_Iyy' : Real = 0.3723953238821935;
                                attribute Izz : Real = 0.17271513635151836;
                                attribute 'σ_Izz' : Real = 0.37017423652493897;
                                attribute Ixy : Real = 0.005734368938563279;
                                attribute 'σ_Ixy' : Real = 0.02351283871158888;
                                attribute Ixz : Real = -3.335246358656305e-4;
                                attribute 'σ_Ixz' : Real = 0.022566176940390956;
                                attribute Iyz : Real = -2.1345377969578402e-4;
                                attribute 'σ_Iyz' : Real = 0.02209918015384651;
                            }
                            part <'C.1.1.1.2.2.2.2'> 'Part 70' {
                                attribute POIconv : String = "+";
                                attribute Ipoint : Boolean = false;
                                attribute mass : Real = 0.36694321964122356;
                                attribute 'σ_mass' : Real = 0.28909372274994966;
                                attribute Cx : Real = -52.6706965174526;
                                attribute 'σ_Cx' : Real = 28.721044428837228;
                                attribute Cy : Real = 74.22661487944424;
                                attribute 'σ_Cy' : Real = 28.23690002309109;
                                attribute Cz : Real = -13.584513124078512;
                                attribute 'σ_Cz' : Real = 29.057750463592832;
                                attribute Ixx : Real = 0.41429691516717526;
                                attribute 'σ_Ixx' : Real = 0.37074144170588635;
                                attribute Iyy : Real = 0.3722785154372464;
                                attribute 'σ_Iyy' : Real = 0.3723953238821935;
                                attribute Izz : Real = 0.449921237142715;
                                attribute 'σ_Izz' : Real = 0.37017423652493897;
                                attribute Ixy : Real = 0.009960438694383851;
                                attribute 'σ_Ixy' : Real = 0.02351283871158888;
                                attribute Ixz : Real = 0.02333089822050821;
                                attribute 'σ_Ixz' : Real = 0.022566176940390956;
                                attribute Iyz : Real = -0.014201410038346945;
                                attribute 'σ_Iyz' : Real = 0.02209918015384651;
                            }
                        }
                    }
                    part <'C.1.1.1.2.3'> 'Assembly 6' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.1.2.3.1'> 'Subassembly 20' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.2.3.1.1'> 'Part 71' {
                                attribute POIconv : String = "-";
                                attribute Ipoint : Boolean = false;
                                attribute mass : Real = 0.007822998428484426;
                                attribute 'σ_mass' : Real = 0.28909372274994966;
                                attribute Cx : Real = -40.83584323525429;
                                attribute 'σ_Cx' : Real = 28.721044428837228;
                                attribute Cy : Real = -44.801608100533485;
                                attribute 'σ_Cy' : Real = 28.23690002309109;
                                attribute Cz : Real = -29.819833021610975;
                                attribute 'σ_Cz' : Real = 29.057750463592832;
                                attribute Ixx : Real = 0.011551502738626424;
                                attribute 'σ_Ixx' : Real = 0.37074144170588635;
                                attribute Iyy : Real = 0.009992170720280432;
                                attribute 'σ_Iyy' : Real = 0.3723953238821935;
                                attribute Izz : Real = 0.01109635881646229;
                                attribute 'σ_Izz' : Real = 0.37017423652493897;
                                attribute Ixy : Real = -5.143711310470591e-4;
                                attribute 'σ_Ixy' : Real = 0.02351283871158888;
                                attribute Ixz : Real = 1.2237390421771047e-4;
                                attribute 'σ_Ixz' : Real = 0.022566176940390956;
                                attribute Iyz : Real = 1.1134597662428806e-4;
                                attribute 'σ_Iyz' : Real = 0.02209918015384651;
                            }
                            part <'C.1.1.1.2.3.1.2'> 'Part 72' {
                                attribute POIconv : String = "+";
                                attribute Ipoint : Boolean = false;
                                attribute mass : Real = 0.011006234406260775;
                                attribute 'σ_mass' : Real = 0.28909372274994966;
                                attribute Cx : Real = -27.485495479777455;
                                attribute 'σ_Cx' : Real = 28.721044428837228;
                                attribute Cy : Real = 62.73811003193259;
                                attribute 'σ_Cy' : Real = 28.23690002309109;
                                attribute Cz : Real = -79.21771402470767;
                                attribute 'σ_Cz' : Real = 29.057750463592832;
                                attribute Ixx : Real = 0.0095934949163012009;
                                attribute 'σ_Ixx' : Real = 0.37074144170588635;
                                attribute Iyy : Real = 0.009551116869749752;
                                attribute 'σ_Iyy' : Real = 0.3723953238821935;
                                attribute Izz : Real = 0.009548968077839387;
                                attribute 'σ_Izz' : Real = 0.37017423652493897;
                                attribute Ixy : Real = -7.056898905150784e-5;
                                attribute 'σ_Ixy' : Real = 0.02351283871158888;
                                attribute Ixz : Real = 3.202951665268411e-6;
                                attribute 'σ_Ixz' : Real = 0.022566176940390956;
                                attribute Iyz : Real = 3.877224547558983e-6;
                                attribute 'σ_Iyz' : Real = 0.02209918015384651;
                            }
                            part <'C.1.1.1.2.3.1.3'> 'Part 73' {
                                attribute POIconv : String = "+";
                                attribute Ipoint : Boolean = false;
                                attribute mass : Real = 0.9737113904533907;
                                attribute 'σ_mass' : Real = 0.28909372274994966;
                                attribute Cx : Real = 88.39750867336988;
                                attribute 'σ_Cx' : Real = 28.721044428837228;
                                attribute Cy : Real = 85.73678876273334;
                                attribute 'σ_Cy' : Real = 28.23690002309109;
                                attribute Cz : Real = -2.154058776795864;
                                attribute 'σ_Cz' : Real = 29.057750463592832;
                                attribute Ixx : Real = 1.3340938923761394;
                                attribute 'σ_Ixx' : Real = 0.37074144170588635;
                                attribute Iyy : Real = 1.1372455338629872;
                                attribute 'σ_Iyy' : Real = 0.3723953238821935;
                                attribute Izz : Real = 1.1498063946713875;
                                attribute 'σ_Izz' : Real = 0.37017423652493897;
                                attribute Ixy : Real = 0.039170954392874296;
                                attribute 'σ_Ixy' : Real = 0.02351283871158888;
                                attribute Ixz : Real = 0.09851781162341479;
                                attribute 'σ_Ixz' : Real = 0.022566176940390956;
                                attribute Iyz : Real = -0.01302421448174621;
                                attribute 'σ_Iyz' : Real = 0.02209918015384651;
                            }
                            part <'C.1.1.1.2.3.1.4'> 'Part 74' {
                                attribute POIconv : String = "-";
                                attribute Ipoint : Boolean = false;
                                attribute mass : Real = 0.858947238052031;
                                attribute 'σ_mass' : Real = 0.28909372274994966;
                                attribute Cx : Real = 55.83097371272743;
                                attribute 'σ_Cx' : Real = 28.721044428837228;
                                attribute Cy : Real = -36.66782295331359;
                                attribute 'σ_Cy' : Real = 28.23690002309109;
                                attribute Cz : Real = 54.58871033042669;
                                attribute 'σ_Cz' : Real = 29.057750463592832;
                                attribute Ixx : Real = 1.1024439505074801;
                                attribute 'σ_Ixx' : Real = 0.37074144170588635;
                                attribute Iyy : Real = 0.9761638561988891;
                                attribute 'σ_Iyy' : Real = 0.3723953238821935;
                                attribute Izz : Real = 1.0304223115500033;
                                attribute 'σ_Izz' : Real = 0.37017423652493897;
                                attribute Ixy : Real = -0.05459600758184348;
                                attribute 'σ_Ixy' : Real = 0.02351283871158888;
                                attribute Ixz : Real = 0.03096943892350617;
                                attribute 'σ_Ixz' : Real = 0.022566176940390956;
                                attribute Iyz : Real = -0.017644373721022545;
                                attribute 'σ_Iyz' : Real = 0.02209918015384651;
                            }
                        }
                        part <'C.1.1.1.2.3.2'> 'Subassembly 21' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.2.3.2.1'> 'Part 75' {
                                attribute POIconv : String = "+";
                                attribute Ipoint : Boolean = false;
                                attribute mass : Real = 0.26481551376148127;
                                attribute 'σ_mass' : Real = 0.28909372274994966;
                                attribute Cx : Real = -53.63753028213978;
                                attribute 'σ_Cx' : Real = 28.721044428837228;
                                attribute Cy : Real = -46.66466596536338;
                                attribute 'σ_Cy' : Real = 28.23690002309109;
                                attribute Cz : Real = -0.9244846645742655;
                                attribute 'σ_Cz' : Real = 29.057750463592832;
                                attribute Ixx : Real = 0.31155615203788484;
                                attribute 'σ_Ixx' : Real = 0.37074144170588635;
                                attribute Iyy : Real = 0.3374063449454626;
                                attribute 'σ_Iyy' : Real = 0.3723953238821935;
                                attribute Izz : Real = 0.2642084792059911;
                                attribute 'σ_Izz' : Real = 0.37017423652493897;
                                attribute Ixy : Real = -0.0028651342545981395;
                                attribute 'σ_Ixy' : Real = 0.02351283871158888;
                                attribute Ixz : Real = 0.004376458327808952;
                                attribute 'σ_Ixz' : Real = 0.022566176940390956;
                                attribute Iyz : Real = 0.00671981313787727;
                                attribute 'σ_Iyz' : Real = 0.02209918015384651;
                            }
                            part <'C.1.1.1.2.3.2.2'> 'Part 76' {
                                attribute POIconv : String = "-";
                                attribute Ipoint : Boolean = false;
                                attribute mass : Real = 0.7251628128180746;
                                attribute 'σ_mass' : Real = 0.28909372274994966;
                                attribute Cx : Real = 50.216217106208205;
                                attribute 'σ_Cx' : Real = 28.721044428837228;
                                attribute Cy : Real = -18.339439621195197;
                                attribute 'σ_Cy' : Real = 28.23690002309109;
                                attribute Cz : Real = 68.33912990987301;
                                attribute 'σ_Cz' : Real = 29.057750463592832;
                                attribute Ixx : Real = 0.9231240841585072;
                                attribute 'σ_Ixx' : Real = 0.37074144170588635;
                                attribute Iyy : Real = 1.030388570836557;
                                attribute 'σ_Iyy' : Real = 0.3723953238821935;
                                attribute Izz : Real = 0.912180235028248;
                                attribute 'σ_Izz' : Real = 0.37017423652493897;
                                attribute Ixy : Real = -0.08272681975307605;
                                attribute 'σ_Ixy' : Real = 0.02351283871158888;
                                attribute Ixz : Real = 0.019280188350300147;
                                attribute 'σ_Ixz' : Real = 0.022566176940390956;
                                attribute Iyz : Real = 0.07808673286905413;
                                attribute 'σ_Iyz' : Real = 0.02209918015384651;
                            }
                            part <'C.1.1.1.2.3.2.3'> 'Part 77' {
                                attribute POIconv : String = "+";
                                attribute Ipoint : Boolean = false;
                                attribute mass : Real = 0.8274399111559615;
                                attribute 'σ_mass' : Real = 0.28909372274994966;
                                attribute Cx : Real = 50.84372856654227;
                                attribute 'σ_Cx' : Real = 28.721044428837228;
                                attribute Cy : Real = 27.238840935751796;
                                attribute 'σ_Cy' : Real = 28.23690002309109;
                                attribute Cz : Real = -2.8501118533313274;
                                attribute 'σ_Cz' : Real = 29.057750463592832;
                                attribute Ixx : Real = 1.0936122645996538;
                                attribute 'σ_Ixx' : Real = 0.37074144170588635;
                                attribute Iyy : Real = 1.197534737156608;
                                attribute 'σ_Iyy' : Real = 0.3723953238821935;
                                attribute Izz : Real = 1.1891672224475878;
                                attribute 'σ_Izz' : Real = 0.37017423652493897;
                                attribute Ixy : Real = 0.041248748883859945;
                                attribute 'σ_Ixy' : Real = 0.02351283871158888;
                                attribute Ixz : Real = 0.05433118366225956;
                                attribute 'σ_Ixz' : Real = 0.022566176940390956;
                                attribute Iyz : Real = 0.02561028488680142;
                                attribute 'σ_Iyz' : Real = 0.02209918015384651;
                            }
                        }
                        part <'C.1.1.1.2.3.3'> 'Subassembly 22' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.2.3.3.1'> 'Part 78' {
                                attribute POIconv : String = "+";
                                attribute Ipoint : Boolean = false;
                                attribute mass : Real = 0.7546356687473599;
                                attribute 'σ_mass' : Real = 0.28909372274994966;
                                attribute Cx : Real = -88.97826941683888;
                                attribute 'σ_Cx' : Real = 28.721044428837228;
                                attribute Cy : Real = -42.908964306116104;
                                attribute 'σ_Cy' : Real = 28.23690002309109;
                                attribute Cz : Real = 26.664093229919672;
                                attribute 'σ_Cz' : Real = 29.057750463592832;
                                attribute Ixx : Real = 0.9921469082791691;
                                attribute 'σ_Ixx' : Real = 0.37074144170588635;
                                attribute Iyy : Real = 0.8911001917120183;
                                attribute 'σ_Iyy' : Real = 0.3723953238821935;
                                attribute Izz : Real = 0.9996333147935802;
                                attribute 'σ_Izz' : Real = 0.37017423652493897;
                                attribute Ixy : Real = 0.03243077703484606;
                                attribute 'σ_Ixy' : Real = 0.02351283871158888;
                                attribute Ixz : Real = -0.03418935154774299;
                                attribute 'σ_Ixz' : Real = 0.022566176940390956;
                                attribute Iyz : Real = -0.02459281388571486;
                                attribute 'σ_Iyz' : Real = 0.02209918015384651;
                            }
                            part <'C.1.1.1.2.3.3.2'> 'Part 79' {
                                attribute POIconv : String = "+";
                                attribute Ipoint : Boolean = false;
                                attribute mass : Real = 0.6828366940831766;
                                attribute 'σ_mass' : Real = 0.28909372274994966;
                                attribute Cx : Real = -60.35300688818097;
                                attribute 'σ_Cx' : Real = 28.721044428837228;
                                attribute Cy : Real = -56.18043448776007;
                                attribute 'σ_Cy' : Real = 28.23690002309109;
                                attribute Cz : Real = -3.304198244586587;
                                attribute 'σ_Cz' : Real = 29.057750463592832;
                                attribute Ixx : Real = 0.9102177883118019;
                                attribute 'σ_Ixx' : Real = 0.37074144170588635;
                                attribute Iyy : Real = 0.7294773717185047;
                                attribute 'σ_Iyy' : Real = 0.3723953238821935;
                                attribute Izz : Real = 0.9001911488394024;
                                attribute 'σ_Izz' : Real = 0.37017423652493897;
                                attribute Ixy : Real = -0.03685921735404289;
                                attribute 'σ_Ixy' : Real = 0.02351283871158888;
                                attribute Ixz : Real = -0.013568581638424355;
                                attribute 'σ_Ixz' : Real = 0.022566176940390956;
                                attribute Iyz : Real = 0.03117987508106529;
                                attribute 'σ_Iyz' : Real = 0.02209918015384651;
                            }
                            part <'C.1.1.1.2.3.3.3'> 'Part 80' {
                                attribute POIconv : String = "+";
                                attribute Ipoint : Boolean = false;
                                attribute mass : Real = 0.8028958896433469;
                                attribute 'σ_mass' : Real = 0.28909372274994966;
                                attribute Cx : Real = 51.41779645346105;
                                attribute 'σ_Cx' : Real = 28.721044428837228;
                                attribute Cy : Real = 59.67926140874624;
                                attribute 'σ_Cy' : Real = 28.23690002309109;
                                attribute Cz : Real = 9.603276010602713;
                                attribute 'σ_Cz' : Real = 29.057750463592832;
                                attribute Ixx : Real = 1.0079054880811766;
                                attribute 'σ_Ixx' : Real = 0.37074144170588635;
                                attribute Iyy : Real = 1.1149655243882572;
                                attribute 'σ_Iyy' : Real = 0.3723953238821935;
                                attribute Izz : Real = 1.0768822499710498;
                                attribute 'σ_Izz' : Real = 0.37017423652493897;
                                attribute Ixy : Real = 0.06785926147745266;
                                attribute 'σ_Ixy' : Real = 0.02351283871158888;
                                attribute Ixz : Real = -2.93820157681978e-4;
                                attribute 'σ_Ixz' : Real = 0.022566176940390956;
                                attribute Iyz : Real = 0.0012403797470538157;
                                attribute 'σ_Iyz' : Real = 0.02209918015384651;
                            }
                            part <'C.1.1.1.2.3.3.4'> 'Part 81' {
                                attribute POIconv : String = "+";
                                attribute Ipoint : Boolean = false;
                                attribute mass : Real = 0.6417334571871907;
                                attribute 'σ_mass' : Real = 0.28909372274994966;
                                attribute Cx : Real = -58.70668143033981;
                                attribute 'σ_Cx' : Real = 28.721044428837228;
                                attribute Cy : Real = -6.36283541098237;
                                attribute 'σ_Cy' : Real = 28.23690002309109;
                                attribute Cz : Real = -55.96758760511875;
                                attribute 'σ_Cz' : Real = 29.057750463592832;
                                attribute Ixx : Real = 0.8669762979884124;
                                attribute 'σ_Ixx' : Real = 0.37074144170588635;
                                attribute Iyy : Real = 0.7364008855226749;
                                attribute 'σ_Iyy' : Real = 0.3723953238821935;
                                attribute Izz : Real = 0.8964697487583941;
                                attribute 'σ_Izz' : Real = 0.37017423652493897;
                                attribute Ixy : Real = 0.010010641488802109;
                                attribute 'σ_Ixy' : Real = 0.02351283871158888;
                                attribute Ixz : Real = 0.02707546893380521;
                                attribute 'σ_Ixz' : Real = 0.022566176940390956;
                                attribute Iyz : Real = 0.012281919114728987;
                                attribute 'σ_Iyz' : Real = 0.02209918015384651;
                            }
                        }
                        part <'C.1.1.1.2.3.4'> 'Subassembly 23' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.2.3.4.1'> 'Part 82' {
                                attribute POIconv : String = "+";
                                attribute Ipoint : Boolean = false;
                                attribute mass : Real = 0.218199021138018;
                                attribute 'σ_mass' : Real = 0.28909372274994966;
                                attribute Cx : Real = -84.89080280996859;
                                attribute 'σ_Cx' : Real = 28.721044428837228;
                                attribute Cy : Real = -87.14131964370608;
                                attribute 'σ_Cy' : Real = 28.23690002309109;
                                attribute Cz : Real = -35.78796214424074;
                                attribute 'σ_Cz' : Real = 29.057750463592832;
                                attribute Ixx : Real = 0.26089645683230894;
                                attribute 'σ_Ixx' : Real = 0.37074144170588635;
                                attribute Iyy : Real = 0.24367161848884702;
                                attribute 'σ_Iyy' : Real = 0.3723953238821935;
                                attribute Izz : Real = 0.23179783658841557;
                                attribute 'σ_Izz' : Real = 0.37017423652493897;
                                attribute Ixy : Real = -0.002261864155376762;
                                attribute 'σ_Ixy' : Real = 0.02351283871158888;
                                attribute Ixz : Real = -0.010163627779620796;
                                attribute 'σ_Ixz' : Real = 0.022566176940390956;
                                attribute Iyz : Real = -7.032633569100514e-4;
                                attribute 'σ_Iyz' : Real = 0.02209918015384651;
                            }
                            part <'C.1.1.1.2.3.4.2'> 'Part 83' {
                                attribute POIconv : String = "+";
                                attribute Ipoint : Boolean = false;
                                attribute mass : Real = 0.24151459474605508;
                                attribute 'σ_mass' : Real = 0.28909372274994966;
                                attribute Cx : Real = 91.12854218110442;
                                attribute 'σ_Cx' : Real = 28.721044428837228;
                                attribute Cy : Real = -60.79755173996091;
                                attribute 'σ_Cy' : Real = 28.23690002309109;
                                attribute Cz : Real = 23.188514169305563;
                                attribute 'σ_Cz' : Real = 29.057750463592832;
                                attribute Ixx : Real = 0.2507853333779884;
                                attribute 'σ_Ixx' : Real = 0.37074144170588635;
                                attribute Iyy : Real = 0.24790091248970633;
                                attribute 'σ_Iyy' : Real = 0.3723953238821935;
                                attribute Izz : Real = 0.2495395381580272;
                                attribute 'σ_Izz' : Real = 0.37017423652493897;
                                attribute Ixy : Real = -0.00641294803320176;
                                attribute 'σ_Ixy' : Real = 0.02351283871158888;
                                attribute Ixz : Real = -0.006484474832168237;
                                attribute 'σ_Ixz' : Real = 0.022566176940390956;
                                attribute Iyz : Real = 0.004517412851417688;
                                attribute 'σ_Iyz' : Real = 0.02209918015384651;
                            }
                            part <'C.1.1.1.2.3.4.3'> 'Part 84' {
                                attribute POIconv : String = "-";
                                attribute Ipoint : Boolean = false;
                                attribute mass : Real = 0.13108227028069086;
                                attribute 'σ_mass' : Real = 0.28909372274994966;
                                attribute Cx : Real = -55.105545883998275;
                                attribute 'σ_Cx' : Real = 28.721044428837228;
                                attribute Cy : Real = 50.29907142743468;
                                attribute 'σ_Cy' : Real = 28.23690002309109;
                                attribute Cz : Real = -28.523652302101254;
                                attribute 'σ_Cz' : Real = 29.057750463592832;
                                attribute Ixx : Real = 0.17823414938489507;
                                attribute 'σ_Ixx' : Real = 0.37074144170588635;
                                attribute Iyy : Real = 0.16899774076443264;
                                attribute 'σ_Iyy' : Real = 0.3723953238821935;
                                attribute Izz : Real = 0.1773958050477111;
                                attribute 'σ_Izz' : Real = 0.37017423652493897;
                                attribute Ixy : Real = 0.005422380925786991;
                                attribute 'σ_Ixy' : Real = 0.02351283871158888;
                                attribute Ixz : Real = 7.495704353869361e-4;
                                attribute 'σ_Ixz' : Real = 0.022566176940390956;
                                attribute Iyz : Real = -8.682237867695884e-4;
                                attribute 'σ_Iyz' : Real = 0.02209918015384651;
                            }
                            part <'C.1.1.1.2.3.4.4'> 'Part 85' {
                                attribute POIconv : String = "-";
                                attribute Ipoint : Boolean = false;
                                attribute mass : Real = 0.9114522569233086;
                                attribute 'σ_mass' : Real = 0.28909372274994966;
                                attribute Cx : Real = 99.45832034572959;
                                attribute 'σ_Cx' : Real = 28.721044428837228;
                                attribute Cy : Real = -48.21691857650876;
                                attribute 'σ_Cy' : Real = 28.23690002309109;
                                attribute Cz : Real = -69.26424028351903;
                                attribute 'σ_Cz' : Real = 29.057750463592832;
                                attribute Ixx : Real = 1.3067320479293425;
                                attribute 'σ_Ixx' : Real = 0.37074144170588635;
                                attribute Iyy : Real = 1.1125524444129244;
                                attribute 'σ_Iyy' : Real = 0.3723953238821935;
                                attribute Izz : Real = 1.0533387588658123;
                                attribute 'σ_Izz' : Real = 0.37017423652493897;
                                attribute Ixy : Real = -0.012055424370845285;
                                attribute 'σ_Ixy' : Real = 0.02351283871158888;
                                attribute Ixz : Real = -0.05322908217825536;
                                attribute 'σ_Ixz' : Real = 0.022566176940390956;
                                attribute Iyz : Real = -0.030729263493735334;
                                attribute 'σ_Iyz' : Real = 0.02209918015384651;
                            }
                        }
                        part <'C.1.1.1.2.3.5'> 'Subassembly 24' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.1.2.3.5.1'> 'Part 86' {
                                attribute POIconv : String = "-";
                                attribute Ipoint : Boolean = false;
                                attribute mass : Real = 0.4338953122391831;
                                attribute 'σ_mass' : Real = 0.28909372274994966;
                                attribute Cx : Real = -12.77408441528678;
                                attribute 'σ_Cx' : Real = 28.721044428837228;
                                attribute Cy : Real = -13.969493936747313;
                                attribute 'σ_Cy' : Real = 28.23690002309109;
                                attribute Cz : Real = -44.24185575917363;
                                attribute 'σ_Cz' : Real = 29.057750463592832;
                                attribute Ixx : Real = 0.49270015055474464;
                                attribute 'σ_Ixx' : Real = 0.37074144170588635;
                                attribute Iyy : Real = 0.5016157042249995;
                                attribute 'σ_Iyy' : Real = 0.3723953238821935;
                                attribute Izz : Real = 0.5268220749094653;
                                attribute 'σ_Izz' : Real = 0.37017423652493897;
                                attribute Ixy : Real = 0.0433617550509799;
                                attribute 'σ_Ixy' : Real = 0.02351283871158888;
                                attribute Ixz : Real = -0.004072994004007659;
                                attribute 'σ_Ixz' : Real = 0.022566176940390956;
                                attribute Iyz : Real = -0.03862226545273363;
                                attribute 'σ_Iyz' : Real = 0.02209918015384651;
                            }
                            part <'C.1.1.1.2.3.5.2'> 'Part 87' {
                                attribute POIconv : String = "+";
                                attribute Ipoint : Boolean = false;
                                attribute mass : Real = 0.5910588249377906;
                                attribute 'σ_mass' : Real = 0.28909372274994966;
                                attribute Cx : Real = 29.65973257087171;
                                attribute 'σ_Cx' : Real = 28.721044428837228;
                                attribute Cy : Real = -51.554149482399225;
                                attribute 'σ_Cy' : Real = 28.23690002309109;
                                attribute Cz : Real = 13.282808754593134;
                                attribute 'σ_Cz' : Real = 29.057750463592832;
                                attribute Ixx : Real = 0.8345633971161253;
                                attribute 'σ_Ixx' : Real = 0.37074144170588635;
                                attribute Iyy : Real = 0.7921890857522789;
                                attribute 'σ_Iyy' : Real = 0.3723953238821935;
                                attribute Izz : Real = 0.7591917307542413;
                                attribute 'σ_Izz' : Real = 0.37017423652493897;
                                attribute Ixy : Real = -0.019399802419791883;
                                attribute 'σ_Ixy' : Real = 0.02351283871158888;
                                attribute Ixz : Real = -0.009460651472754125;
                                attribute 'σ_Ixz' : Real = 0.022566176940390956;
                                attribute Iyz : Real = 0.001293269805567248;
                                attribute 'σ_Iyz' : Real = 0.02209918015384651;
                            }
                        }
                    }
                }
            }
            part <'C.1.1.2'> 'Element 2' {
                attribute POIconv : String = "-";
                attribute Ipoint : Boolean;
                attribute mass : Real;
                attribute 'σ_mass' : Real;
                attribute Cx : Real;
                attribute 'σ_Cx' : Real;
                attribute Cy : Real;
                attribute 'σ_Cy' : Real;
                attribute Cz : Real;
                attribute 'σ_Cz' : Real;
                attribute Ixx : Real;
                attribute 'σ_Ixx' : Real;
                attribute Iyy : Real;
                attribute 'σ_Iyy' : Real;
                attribute Izz : Real;
                attribute 'σ_Izz' : Real;
                attribute Ixy : Real;
                attribute 'σ_Ixy' : Real;
                attribute Ixz : Real;
                attribute 'σ_Ixz' : Real;
                attribute Iyz : Real;
                attribute 'σ_Iyz' : Real;
                part <'C.1.1.2.1'> 'Subsystem 3' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.2.1.1'> 'Assembly 7' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.1.1.1'> 'Subassembly 25' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.1.1.1'> 'Part 88' {
                                attribute POIconv : String = "+";
                                attribute Ipoint : Boolean = false;
                                attribute mass : Real = 0.6574666414444801;
                                attribute 'σ_mass' : Real = 0.28909372274994966;
                                attribute Cx : Real = -9.622719464823604;
                                attribute 'σ_Cx' : Real = 28.721044428837228;
                                attribute Cy : Real = -82.01006525196135;
                                attribute 'σ_Cy' : Real = 28.23690002309109;
                                attribute Cz : Real = 46.11129076220095;
                                attribute 'σ_Cz' : Real = 29.057750463592832;
                                attribute Ixx : Real = 0.7924319434190586;
                                attribute 'σ_Ixx' : Real = 0.37074144170588635;
                                attribute Iyy : Real = 0.7951552296965433;
                                attribute 'σ_Iyy' : Real = 0.3723953238821935;
                                attribute Izz : Real = 0.8517165241991727;
                                attribute 'σ_Izz' : Real = 0.37017423652493897;
                                attribute Ixy : Real = 0.018472004886994693;
                                attribute 'σ_Ixy' : Real = 0.02351283871158888;
                                attribute Ixz : Real = 0.02031593818065161;
                                attribute 'σ_Ixz' : Real = 0.022566176940390956;
                                attribute Iyz : Real = -0.0405560443178258;
                                attribute 'σ_Iyz' : Real = 0.02209918015384651;
                            }
                            part <'C.1.1.2.1.1.1.2'> 'Part 89' {
                                attribute POIconv : String = "+";
                                attribute Ipoint : Boolean = false;
                                attribute mass : Real = 0.4924646405968815;
                                attribute 'σ_mass' : Real = 0.28909372274994966;
                                attribute Cx : Real = -52.681920398026705;
                                attribute 'σ_Cx' : Real = 28.721044428837228;
                                attribute Cy : Real = 50.23396322503686;
                                attribute 'σ_Cy' : Real = 28.23690002309109;
                                attribute Cz : Real = 24.14228324778378;
                                attribute 'σ_Cz' : Real = 29.057750463592832;
                                attribute Ixx : Real = 0.5381535340322877;
                                attribute 'σ_Ixx' : Real = 0.37074144170588635;
                                attribute Iyy : Real = 0.5285273533443069;
                                attribute 'σ_Iyy' : Real = 0.3723953238821935;
                                attribute Izz : Real = 0.5669012014808583;
                                attribute 'σ_Izz' : Real = 0.37017423652493897;
                                attribute Ixy : Real = -0.05549247648288142;
                                attribute 'σ_Ixy' : Real = 0.02351283871158888;
                                attribute Ixz : Real = -0.02178819035792537;
                                attribute 'σ_Ixz' : Real = 0.022566176940390956;
                                attribute Iyz : Real = 0.02070791522660934;
                                attribute 'σ_Iyz' : Real = 0.02209918015384651;
                            }
                            part <'C.1.1.2.1.1.1.3'> 'Part 90' {
                                attribute POIconv : String = "+";
                                attribute Ipoint : Boolean = false;
                                attribute mass : Real = 0.46895969050144776;
                                attribute 'σ_mass' : Real = 0.28909372274994966;
                                attribute Cx : Real = 0.40842434391379356;
                                attribute 'σ_Cx' : Real = 28.721044428837228;
                                attribute Cy : Real = -53.29704228788614;
                                attribute 'σ_Cy' : Real = 28.23690002309109;
                                attribute Cz : Real = -0.8331109769642353;
                                attribute 'σ_Cz' : Real = 29.057750463592832;
                                attribute Ixx : Real = 0.4546870890483837;
                                attribute 'σ_Ixx' : Real = 0.37074144170588635;
                                attribute Iyy : Real = 0.4412517242475275;
                                attribute 'σ_Iyy' : Real = 0.3723953238821935;
                                attribute Izz : Real = 0.487322858126521;
                                attribute 'σ_Izz' : Real = 0.37017423652493897;
                                attribute Ixy : Real = -0.024311548527731784;
                                attribute 'σ_Ixy' : Real = 0.02351283871158888;
                                attribute Ixz : Real = -0.017274549465124384;
                                attribute 'σ_Ixz' : Real = 0.022566176940390956;
                                attribute Iyz : Real = 0.004452458694065321;
                                attribute 'σ_Iyz' : Real = 0.02209918015384651;
                            }
                            part <'C.1.1.2.1.1.1.4'> 'Part 91' {
                                attribute POIconv : String = "+";
                                attribute Ipoint : Boolean = false;
                                attribute mass : Real = 0.47378089074534363;
                                attribute 'σ_mass' : Real = 0.28909372274994966;
                                attribute Cx : Real = 83.87293019331992;
                                attribute 'σ_Cx' : Real = 28.721044428837228;
                                attribute Cy : Real = -53.824869310483336;
                                attribute 'σ_Cy' : Real = 28.23690002309109;
                                attribute Cz : Real = -86.99310440570116;
                                attribute 'σ_Cz' : Real = 29.057750463592832;
                                attribute Ixx : Real = 0.5702519029418239;
                                attribute 'σ_Ixx' : Real = 0.37074144170588635;
                                attribute Iyy : Real = 0.5707611064209885;
                                attribute 'σ_Iyy' : Real = 0.3723953238821935;
                                attribute Izz : Real = 0.44679084025344334;
                                attribute 'σ_Izz' : Real = 0.37017423652493897;
                                attribute Ixy : Real = 0.013209199407745268;
                                attribute 'σ_Ixy' : Real = 0.02351283871158888;
                                attribute Ixz : Real = 0.0405193281179539;
                                attribute 'σ_Ixz' : Real = 0.022566176940390956;
                                attribute Iyz : Real = -0.00669167558083413;
                                attribute 'σ_Iyz' : Real = 0.02209918015384651;
                            }
                        }
                        part <'C.1.1.2.1.1.2'> 'Subassembly 26' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.1.2.1'> 'Part 92' {
                                attribute POIconv : String = "-";
                                attribute Ipoint : Boolean = false;
                                attribute mass : Real = 0.4027995278642047;
                                attribute 'σ_mass' : Real = 0.28909372274994966;
                                attribute Cx : Real = 0.4480175208300352;
                                attribute 'σ_Cx' : Real = 28.721044428837228;
                                attribute Cy : Real = -63.00972164608538;
                                attribute 'σ_Cy' : Real = 28.23690002309109;
                                attribute Cz : Real = -78.95387476310134;
                                attribute 'σ_Cz' : Real = 29.057750463592832;
                                attribute Ixx : Real = 0.4273179242513523;
                                attribute 'σ_Ixx' : Real = 0.37074144170588635;
                                attribute Iyy : Real = 0.4206934605165544;
                                attribute 'σ_Iyy' : Real = 0.3723953238821935;
                                attribute Izz : Real = 0.4108415499291919;
                                attribute 'σ_Izz' : Real = 0.37017423652493897;
                                attribute Ixy : Real = -0.03166915929328816;
                                attribute 'σ_Ixy' : Real = 0.02351283871158888;
                                attribute Ixz : Real = -0.001699789323999096;
                                attribute 'σ_Ixz' : Real = 0.022566176940390956;
                                attribute Iyz : Real = -0.016090761653504978;
                                attribute 'σ_Iyz' : Real = 0.02209918015384651;
                            }
                            part <'C.1.1.2.1.1.2.2'> 'Part 93' {
                                attribute POIconv : String = "-";
                                attribute Ipoint : Boolean = false;
                                attribute mass : Real = 0.04444675383158028;
                                attribute 'σ_mass' : Real = 0.28909372274994966;
                                attribute Cx : Real = 18.939207401126623;
                                attribute 'σ_Cx' : Real = 28.721044428837228;
                                attribute Cy : Real = -36.474997038021684;
                                attribute 'σ_Cy' : Real = 28.23690002309109;
                                attribute Cz : Real = -48.239379934966564;
                                attribute 'σ_Cz' : Real = 29.057750463592832;
                                attribute Ixx : Real = 0.05910955818898015;
                                attribute 'σ_Ixx' : Real = 0.37074144170588635;
                                attribute Iyy : Real = 0.05911488550148282;
                                attribute 'σ_Iyy' : Real = 0.3723953238821935;
                                attribute Izz : Real = 0.04541863753698516;
                                attribute 'σ_Izz' : Real = 0.37017423652493897;
                                attribute Ixy : Real = 6.552667550428597e-5;
                                attribute 'σ_Ixy' : Real = 0.02351283871158888;
                                attribute Ixz : Real = 7.730737843838365e-4;
                                attribute 'σ_Ixz' : Real = 0.022566176940390956;
                                attribute Iyz : Real = -0.0011082519822138797;
                                attribute 'σ_Iyz' : Real = 0.02209918015384651;
                            }
                        }
                        part <'C.1.1.2.1.1.3'> 'Subassembly 27' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.1.3.1'> 'Part 94' {
                                attribute POIconv : String = "-";
                                attribute Ipoint : Boolean = false;
                                attribute mass : Real = 0.9471763216597028;
                                attribute 'σ_mass' : Real = 0.28909372274994966;
                                attribute Cx : Real = 54.03835880570114;
                                attribute 'σ_Cx' : Real = 28.721044428837228;
                                attribute Cy : Real = 27.56751603446901;
                                attribute 'σ_Cy' : Real = 28.23690002309109;
                                attribute Cz : Real = -28.08032790198922;
                                attribute 'σ_Cz' : Real = 29.057750463592832;
                                attribute Ixx : Real = 0.9798330028301497;
                                attribute 'σ_Ixx' : Real = 0.37074144170588635;
                                attribute Iyy : Real = 0.9949873229584618;
                                attribute 'σ_Iyy' : Real = 0.3723953238821935;
                                attribute Izz : Real = 0.9417741044320632;
                                attribute 'σ_Izz' : Real = 0.37017423652493897;
                                attribute Ixy : Real = 0.01744203300808802;
                                attribute 'σ_Ixy' : Real = 0.02351283871158888;
                                attribute Ixz : Real = -0.004605669246334959;
                                attribute 'σ_Ixz' : Real = 0.022566176940390956;
                                attribute Iyz : Real = -0.010021208555445638;
                                attribute 'σ_Iyz' : Real = 0.02209918015384651;
                            }
                            part <'C.1.1.2.1.1.3.2'> 'Part 95' {
                                attribute POIconv : String = "+";
                                attribute Ipoint : Boolean = false;
                                attribute mass : Real = 0.439736515764147;
                                attribute 'σ_mass' : Real = 0.28909372274994966;
                                attribute Cx : Real = 28.606248274445534;
                                attribute 'σ_Cx' : Real = 28.721044428837228;
                                attribute Cy : Real = 47.5991518702358;
                                attribute 'σ_Cy' : Real = 28.23690002309109;
                                attribute Cz : Real = 71.80758225731552;
                                attribute 'σ_Cz' : Real = 29.057750463592832;
                                attribute Ixx : Real = 0.6568081797107248;
                                attribute 'σ_Ixx' : Real = 0.37074144170588635;
                                attribute Iyy : Real = 0.6625887377436849;
                                attribute 'σ_Iyy' : Real = 0.3723953238821935;
                                attribute Izz : Real = 0.6563679169580535;
                                attribute 'σ_Izz' : Real = 0.37017423652493897;
                                attribute Ixy : Real = -0.0015424657956183627;
                                attribute 'σ_Ixy' : Real = 0.02351283871158888;
                                attribute Ixz : Real = 0.0016945065018968268;
                                attribute 'σ_Ixz' : Real = 0.022566176940390956;
                                attribute Iyz : Real = 7.54642355537635e-4;
                                attribute 'σ_Iyz' : Real = 0.02209918015384651;
                            }
                        }
                    }
                    part <'C.1.1.2.1.2'> 'Assembly 8' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.1.2.1'> 'Subassembly 28' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.2.1.1'> 'Part 96' {
                                attribute POIconv : String = "-";
                                attribute Ipoint : Boolean = false;
                                attribute mass : Real = 0.5393943031483796;
                                attribute 'σ_mass' : Real = 0.28909372274994966;
                                attribute Cx : Real = -68.81726724095643;
                                attribute 'σ_Cx' : Real = 28.721044428837228;
                                attribute Cy : Real = 91.93735397420824;
                                attribute 'σ_Cy' : Real = 28.23690002309109;
                                attribute Cz : Real = 64.3666127230972;
                                attribute 'σ_Cz' : Real = 29.057750463592832;
                                attribute Ixx : Real = 0.6301237938341671;
                                attribute 'σ_Ixx' : Real = 0.37074144170588635;
                                attribute Iyy : Real = 0.5888884112792817;
                                attribute 'σ_Iyy' : Real = 0.3723953238821935;
                                attribute Izz : Real = 0.6293742206466112;
                                attribute 'σ_Izz' : Real = 0.37017423652493897;
                                attribute Ixy : Real = 4.626238561429355e-4;
                                attribute 'σ_Ixy' : Real = 0.02351283871158888;
                                attribute Ixz : Real = 0.012250424958473064;
                                attribute 'σ_Ixz' : Real = 0.022566176940390956;
                                attribute Iyz : Real = -0.026700290258722614;
                                attribute 'σ_Iyz' : Real = 0.02209918015384651;
                            }
                            part <'C.1.1.2.1.2.1.2'> 'Part 97' {
                                attribute POIconv : String = "-";
                                attribute Ipoint : Boolean = false;
                                attribute mass : Real = 0.20204887738917024;
                                attribute 'σ_mass' : Real = 0.28909372274994966;
                                attribute Cx : Real = 88.53948577307165;
                                attribute 'σ_Cx' : Real = 28.721044428837228;
                                attribute Cy : Real = 14.164153439924121;
                                attribute 'σ_Cy' : Real = 28.23690002309109;
                                attribute Cz : Real = 41.46328601054847;
                                attribute 'σ_Cz' : Real = 29.057750463592832;
                                attribute Ixx : Real = 0.28607160305904084;
                                attribute 'σ_Ixx' : Real = 0.37074144170588635;
                                attribute Iyy : Real = 0.28517430896600515;
                                attribute 'σ_Iyy' : Real = 0.3723953238821935;
                                attribute Izz : Real = 0.25346213061390016;
                                attribute 'σ_Izz' : Real = 0.37017423652493897;
                                attribute Ixy : Real = -0.029609555966824234;
                                attribute 'σ_Ixy' : Real = 0.02351283871158888;
                                attribute Ixz : Real = 0.002036837234827192;
                                attribute 'σ_Ixz' : Real = 0.022566176940390956;
                                attribute Iyz : Real = 0.00784235452367836;
                                attribute 'σ_Iyz' : Real = 0.02209918015384651;
                            }
                        }
                        part <'C.1.1.2.1.2.2'> 'Subassembly 29' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.2.2.1'> 'Part 98' {
                                attribute POIconv : String = "-";
                                attribute Ipoint : Boolean = false;
                                attribute mass : Real = 0.31876291493442843;
                                attribute 'σ_mass' : Real = 0.28909372274994966;
                                attribute Cx : Real = 9.423621464520693;
                                attribute 'σ_Cx' : Real = 28.721044428837228;
                                attribute Cy : Real = -76.59441861324012;
                                attribute 'σ_Cy' : Real = 28.23690002309109;
                                attribute Cz : Real = 34.241784596815705;
                                attribute 'σ_Cz' : Real = 29.057750463592832;
                                attribute Ixx : Real = 0.45276553903435485;
                                attribute 'σ_Ixx' : Real = 0.37074144170588635;
                                attribute Iyy : Real = 0.4477806520181036;
                                attribute 'σ_Iyy' : Real = 0.3723953238821935;
                                attribute Izz : Real = 0.44939573846567454;
                                attribute 'σ_Izz' : Real = 0.37017423652493897;
                                attribute Ixy : Real = 3.8987387953538257e-4;
                                attribute 'σ_Ixy' : Real = 0.02351283871158888;
                                attribute Ixz : Real = 0.012101613284788024;
                                attribute 'σ_Ixz' : Real = 0.022566176940390956;
                                attribute Iyz : Real = 9.6679887112024e-4;
                                attribute 'σ_Iyz' : Real = 0.02209918015384651;
                            }
                            part <'C.1.1.2.1.2.2.2'> 'Part 99' {
                                attribute POIconv : String = "+";
                                attribute Ipoint : Boolean = false;
                                attribute mass : Real = 0.999165522782132;
                                attribute 'σ_mass' : Real = 0.28909372274994966;
                                attribute Cx : Real = 82.50024197623134;
                                attribute 'σ_Cx' : Real = 28.721044428837228;
                                attribute Cy : Real = -33.414676040410995;
                                attribute 'σ_Cy' : Real = 28.23690002309109;
                                attribute Cz : Real = 81.18700222112238;
                                attribute 'σ_Cz' : Real = 29.057750463592832;
                                attribute Ixx : Real = 1.1615261593187678;
                                attribute 'σ_Ixx' : Real = 0.37074144170588635;
                                attribute Iyy : Real = 1.290035689438555;
                                attribute 'σ_Iyy' : Real = 0.3723953238821935;
                                attribute Izz : Real = 1.168166682415794;
                                attribute 'σ_Izz' : Real = 0.37017423652493897;
                                attribute Ixy : Real = -0.06772558979515193;
                                attribute 'σ_Ixy' : Real = 0.02351283871158888;
                                attribute Ixz : Real = -0.028036399076493256;
                                attribute 'σ_Ixz' : Real = 0.022566176940390956;
                                attribute Iyz : Real = -0.06935514753619343;
                                attribute 'σ_Iyz' : Real = 0.02209918015384651;
                            }
                            part <'C.1.1.2.1.2.2.3'> 'Part 100' {
                                attribute POIconv : String = "+";
                                attribute Ipoint : Boolean = false;
                                attribute mass : Real = 0.24935771647607907;
                                attribute 'σ_mass' : Real = 0.28909372274994966;
                                attribute Cx : Real = 11.009952751919627;
                                attribute 'σ_Cx' : Real = 28.721044428837228;
                                attribute Cy : Real = -39.608294470235705;
                                attribute 'σ_Cy' : Real = 28.23690002309109;
                                attribute Cz : Real = 17.131019476801157;
                                attribute 'σ_Cz' : Real = 29.057750463592832;
                                attribute Ixx : Real = 0.33388424797610067;
                                attribute 'σ_Ixx' : Real = 0.37074144170588635;
                                attribute Iyy : Real = 0.2942537482264843;
                                attribute 'σ_Iyy' : Real = 0.3723953238821935;
                                attribute Izz : Real = 0.29891979413677994;
                                attribute 'σ_Izz' : Real = 0.37017423652493897;
                                attribute Ixy : Real = -0.011388587464819112;
                                attribute 'σ_Ixy' : Real = 0.02351283871158888;
                                attribute Ixz : Real = -0.02256524728127142;
                                attribute 'σ_Ixz' : Real = 0.022566176940390956;
                                attribute Iyz : Real = -0.005011723668057726;
                                attribute 'σ_Iyz' : Real = 0.02209918015384651;
                            }
                            part <'C.1.1.2.1.2.2.4'> 'Part 101' {
                                attribute POIconv : String = "-";
                                attribute Ipoint : Boolean = false;
                                attribute mass : Real = 0.5708077931087464;
                                attribute 'σ_mass' : Real = 0.28909372274994966;
                                attribute Cx : Real = -41.36252854950726;
                                attribute 'σ_Cx' : Real = 28.721044428837228;
                                attribute Cy : Real = -1.1480579618364573;
                                attribute 'σ_Cy' : Real = 28.23690002309109;
                                attribute Cz : Real = -45.905264373868704;
                                attribute 'σ_Cz' : Real = 29.057750463592832;
                                attribute Ixx : Real = 0.7606852600168091;
                                attribute 'σ_Ixx' : Real = 0.37074144170588635;
                                attribute Iyy : Real = 0.8736279477916913;
                                attribute 'σ_Iyy' : Real = 0.3723953238821935;
                                attribute Izz : Real = 0.7134443470120105;
                                attribute 'σ_Izz' : Real = 0.37017423652493897;
                                attribute Ixy : Real = 0.04281651319206434;
                                attribute 'σ_Ixy' : Real = 0.02351283871158888;
                                attribute Ixz : Real = 0.025386948155731837;
                                attribute 'σ_Ixz' : Real = 0.022566176940390956;
                                attribute Iyz : Real = 0.010743995688391616;
                                attribute 'σ_Iyz' : Real = 0.02209918015384651;
                            }
                            part <'C.1.1.2.1.2.2.5'> 'Part 102' {
                                attribute POIconv : String = "+";
                                attribute Ipoint : Boolean = false;
                                attribute mass : Real = 0.5080840814998373;
                                attribute 'σ_mass' : Real = 0.28909372274994966;
                                attribute Cx : Real = -60.853754449635744;
                                attribute 'σ_Cx' : Real = 28.721044428837228;
                                attribute Cy : Real = -17.909912252798676;
                                attribute 'σ_Cy' : Real = 28.23690002309109;
                                attribute Cz : Real = 12.717081978917122;
                                attribute 'σ_Cz' : Real = 29.057750463592832;
                                attribute Ixx : Real = 0.7214159180406441;
                                attribute 'σ_Ixx' : Real = 0.37074144170588635;
                                attribute Iyy : Real = 0.8067006977063836;
                                attribute 'σ_Iyy' : Real = 0.3723953238821935;
                                attribute Izz : Real = 0.7445761369363252;
                                attribute 'σ_Izz' : Real = 0.37017423652493897;
                                attribute Ixy : Real = 0.02329447671543433;
                                attribute 'σ_Ixy' : Real = 0.02351283871158888;
                                attribute Ixz : Real = -0.015864256628876652;
                                attribute 'σ_Ixz' : Real = 0.022566176940390956;
                                attribute Iyz : Real = 0.04908564739978493;
                                attribute 'σ_Iyz' : Real = 0.02209918015384651;
                            }
                        }
                        part <'C.1.1.2.1.2.3'> 'Subassembly 30' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.2.3.1'> 'Part 103' {
                                attribute POIconv : String = "+";
                                attribute Ipoint : Boolean = false;
                                attribute mass : Real = 0.581501622005133;
                                attribute 'σ_mass' : Real = 0.28909372274994966;
                                attribute Cx : Real = 24.297722475603223;
                                attribute 'σ_Cx' : Real = 28.721044428837228;
                                attribute Cy : Real = -29.563105758279562;
                                attribute 'σ_Cy' : Real = 28.23690002309109;
                                attribute Cz : Real = -60.83531677722931;
                                attribute 'σ_Cz' : Real = 29.057750463592832;
                                attribute Ixx : Real = 0.6869823446580784;
                                attribute 'σ_Ixx' : Real = 0.37074144170588635;
                                attribute Iyy : Real = 0.7357506812592337;
                                attribute 'σ_Iyy' : Real = 0.3723953238821935;
                                attribute Izz : Real = 0.7255234154866275;
                                attribute 'σ_Izz' : Real = 0.37017423652493897;
                                attribute Ixy : Real = 0.023871852892238234;
                                attribute 'σ_Ixy' : Real = 0.02351283871158888;
                                attribute Ixz : Real = 0.02182471828754266;
                                attribute 'σ_Ixz' : Real = 0.022566176940390956;
                                attribute Iyz : Real = -0.04390258665021367;
                                attribute 'σ_Iyz' : Real = 0.02209918015384651;
                            }
                            part <'C.1.1.2.1.2.3.2'> 'Part 104' {
                                attribute POIconv : String = "-";
                                attribute Ipoint : Boolean = false;
                                attribute mass : Real = 0.01941261755884625;
                                attribute 'σ_mass' : Real = 0.28909372274994966;
                                attribute Cx : Real = -39.41521588712931;
                                attribute 'σ_Cx' : Real = 28.721044428837228;
                                attribute Cy : Real = 86.56577104702592;
                                attribute 'σ_Cy' : Real = 28.23690002309109;
                                attribute Cz : Real = -61.78977703675628;
                                attribute 'σ_Cz' : Real = 29.057750463592832;
                                attribute Ixx : Real = 0.0230874765117583;
                                attribute 'σ_Ixx' : Real = 0.37074144170588635;
                                attribute Iyy : Real = 0.021308903506686388;
                                attribute 'σ_Iyy' : Real = 0.3723953238821935;
                                attribute Izz : Real = 0.022986244700695838;
                                attribute 'σ_Izz' : Real = 0.37017423652493897;
                                attribute Ixy : Real = -4.941765127886633e-4;
                                attribute 'σ_Ixy' : Real = 0.02351283871158888;
                                attribute Ixz : Real = -0.001607974957150781;
                                attribute 'σ_Ixz' : Real = 0.022566176940390956;
                                attribute Iyz : Real = 6.699659480864147e-4;
                                attribute 'σ_Iyz' : Real = 0.02209918015384651;
                            }
                            part <'C.1.1.2.1.2.3.3'> 'Part 105' {
                                attribute POIconv : String = "-";
                                attribute Ipoint : Boolean = false;
                                attribute mass : Real = 0.3169937257275451;
                                attribute 'σ_mass' : Real = 0.28909372274994966;
                                attribute Cx : Real = 60.75515071861446;
                                attribute 'σ_Cx' : Real = 28.721044428837228;
                                attribute Cy : Real = 2.8717597015202045;
                                attribute 'σ_Cy' : Real = 28.23690002309109;
                                attribute Cz : Real = -86.10042594373226;
                                attribute 'σ_Cz' : Real = 29.057750463592832;
                                attribute Ixx : Real = 0.3780976956715486;
                                attribute 'σ_Ixx' : Real = 0.37074144170588635;
                                attribute Iyy : Real = 0.38337554064719276;
                                attribute 'σ_Iyy' : Real = 0.3723953238821935;
                                attribute Izz : Real = 0.430035437146418;
                                attribute 'σ_Izz' : Real = 0.37017423652493897;
                                attribute Ixy : Real = -0.0010617603542956782;
                                attribute 'σ_Ixy' : Real = 0.02351283871158888;
                                attribute Ixz : Real = 0.00481900730311614;
                                attribute 'σ_Ixz' : Real = 0.022566176940390956;
                                attribute Iyz : Real = -0.011816701013258917;
                                attribute 'σ_Iyz' : Real = 0.02209918015384651;
                            }
                            part <'C.1.1.2.1.2.3.4'> 'Part 106' {
                                attribute POIconv : String = "-";
                                attribute Ipoint : Boolean = false;
                                attribute mass : Real = 0.7171664482057094;
                                attribute 'σ_mass' : Real = 0.28909372274994966;
                                attribute Cx : Real = 7.859595865011215;
                                attribute 'σ_Cx' : Real = 28.721044428837228;
                                attribute Cy : Real = -57.86468884907663;
                                attribute 'σ_Cy' : Real = 28.23690002309109;
                                attribute Cz : Real = -11.13087204284966;
                                attribute 'σ_Cz' : Real = 29.057750463592832;
                                attribute Ixx : Real = 1.03411822750131;
                                attribute 'σ_Ixx' : Real = 0.37074144170588635;
                                attribute Iyy : Real = 1.0543906151676048;
                                attribute 'σ_Iyy' : Real = 0.3723953238821935;
                                attribute Izz : Real = 1.0422294659697258;
                                attribute 'σ_Izz' : Real = 0.37017423652493897;
                                attribute Ixy : Real = -0.0042345953824020535;
                                attribute 'σ_Ixy' : Real = 0.02351283871158888;
                                attribute Ixz : Real = 0.05645923623199884;
                                attribute 'σ_Ixz' : Real = 0.022566176940390956;
                                attribute Iyz : Real = -0.01745081317211243;
                                attribute 'σ_Iyz' : Real = 0.02209918015384651;
                            }
                            part <'C.1.1.2.1.2.3.5'> 'Part 107' {
                                attribute POIconv : String = "+";
                                attribute Ipoint : Boolean = false;
                                attribute mass : Real = 0.7810161900175735;
                                attribute 'σ_mass' : Real = 0.28909372274994966;
                                attribute Cx : Real = 26.248844899237156;
                                attribute 'σ_Cx' : Real = 28.721044428837228;
                                attribute Cy : Real = 57.523692632094026;
                                attribute 'σ_Cy' : Real = 28.23690002309109;
                                attribute Cz : Real = -44.64739505201578;
                                attribute 'σ_Cz' : Real = 29.057750463592832;
                                attribute Ixx : Real = 0.9088588251040798;
                                attribute 'σ_Ixx' : Real = 0.37074144170588635;
                                attribute Iyy : Real = 0.8972887982764585;
                                attribute 'σ_Iyy' : Real = 0.3723953238821935;
                                attribute Izz : Real = 1.0286008441917176;
                                attribute 'σ_Izz' : Real = 0.37017423652493897;
                                attribute Ixy : Real = 0.008802699271537838;
                                attribute 'σ_Ixy' : Real = 0.02351283871158888;
                                attribute Ixz : Real = 0.03897664736977276;
                                attribute 'σ_Ixz' : Real = 0.022566176940390956;
                                attribute Iyz : Real = 0.004378579248974263;
                                attribute 'σ_Iyz' : Real = 0.02209918015384651;
                            }
                        }
                        part <'C.1.1.2.1.2.4'> 'Subassembly 31' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.2.4.1'> 'Part 108' {
                                attribute POIconv : String = "-";
                                attribute Ipoint : Boolean = false;
                                attribute mass : Real = 0.5589087291043252;
                                attribute 'σ_mass' : Real = 0.28909372274994966;
                                attribute Cx : Real = -11.67716491036117;
                                attribute 'σ_Cx' : Real = 28.721044428837228;
                                attribute Cy : Real = -92.76235578581691;
                                attribute 'σ_Cy' : Real = 28.23690002309109;
                                attribute Cz : Real = 88.77333477139473;
                                attribute 'σ_Cz' : Real = 29.057750463592832;
                                attribute Ixx : Real = 0.737069725504405;
                                attribute 'σ_Ixx' : Real = 0.37074144170588635;
                                attribute Iyy : Real = 0.7012343186114927;
                                attribute 'σ_Iyy' : Real = 0.3723953238821935;
                                attribute Izz : Real = 0.698167848653303;
                                attribute 'σ_Izz' : Real = 0.37017423652493897;
                                attribute Ixy : Real = -0.002877409958384863;
                                attribute 'σ_Ixy' : Real = 0.02351283871158888;
                                attribute Ixz : Real = -0.0066432327710345355;
                                attribute 'σ_Ixz' : Real = 0.022566176940390956;
                                attribute Iyz : Real = 0.0011374349917477645;
                                attribute 'σ_Iyz' : Real = 0.02209918015384651;
                            }
                            part <'C.1.1.2.1.2.4.2'> 'Part 109' {
                                attribute POIconv : String = "+";
                                attribute Ipoint : Boolean = false;
                                attribute mass : Real = 0.4450532393651083;
                                attribute 'σ_mass' : Real = 0.28909372274994966;
                                attribute Cx : Real = 29.549271566793323;
                                attribute 'σ_Cx' : Real = 28.721044428837228;
                                attribute Cy : Real = 79.00358750484884;
                                attribute 'σ_Cy' : Real = 28.23690002309109;
                                attribute Cz : Real = -99.61457783356309;
                                attribute 'σ_Cz' : Real = 29.057750463592832;
                                attribute Ixx : Real = 0.5222635125076712;
                                attribute 'σ_Ixx' : Real = 0.37074144170588635;
                                attribute Iyy : Real = 0.4987335501835786;
                                attribute 'σ_Iyy' : Real = 0.3723953238821935;
                                attribute Izz : Real = 0.5323706972642985;
                                attribute 'σ_Izz' : Real = 0.37017423652493897;
                                attribute Ixy : Real = -0.04973439046222403;
                                attribute 'σ_Ixy' : Real = 0.02351283871158888;
                                attribute Ixz : Real = 0.03416611457543074;
                                attribute 'σ_Ixz' : Real = 0.022566176940390956;
                                attribute Iyz : Real = -0.023478425982874543;
                                attribute 'σ_Iyz' : Real = 0.02209918015384651;
                            }
                            part <'C.1.1.2.1.2.4.3'> 'Part 110' {
                                attribute POIconv : String = "+";
                                attribute Ipoint : Boolean = false;
                                attribute mass : Real = 0.030119509148411452;
                                attribute 'σ_mass' : Real = 0.28909372274994966;
                                attribute Cx : Real = 31.330942641943693;
                                attribute 'σ_Cx' : Real = 28.721044428837228;
                                attribute Cy : Real = 40.80635840073228;
                                attribute 'σ_Cy' : Real = 28.23690002309109;
                                attribute Cz : Real = 92.96931806020439;
                                attribute 'σ_Cz' : Real = 29.057750463592832;
                                attribute Ixx : Real = 0.038950297981389014;
                                attribute 'σ_Ixx' : Real = 0.37074144170588635;
                                attribute Iyy : Real = 0.0348127022016938;
                                attribute 'σ_Iyy' : Real = 0.3723953238821935;
                                attribute Izz : Real = 0.03807755275498147;
                                attribute 'σ_Izz' : Real = 0.37017423652493897;
                                attribute Ixy : Real = -2.4114116855189483e-4;
                                attribute 'σ_Ixy' : Real = 0.02351283871158888;
                                attribute Ixz : Real = -0.0029343003495598333;
                                attribute 'σ_Ixz' : Real = 0.022566176940390956;
                                attribute Iyz : Real = 8.446988898124146e-4;
                                attribute 'σ_Iyz' : Real = 0.02209918015384651;
                            }
                            part <'C.1.1.2.1.2.4.4'> 'Part 111' {
                                attribute POIconv : String = "-";
                                attribute Ipoint : Boolean = false;
                                attribute mass : Real = 0.10221832146658562;
                                attribute 'σ_mass' : Real = 0.28909372274994966;
                                attribute Cx : Real = 25.13614478521049;
                                attribute 'σ_Cx' : Real = 28.721044428837228;
                                attribute Cy : Real = 22.29165304452181;
                                attribute 'σ_Cy' : Real = 28.23690002309109;
                                attribute Cz : Real = 20.215584570541978;
                                attribute 'σ_Cz' : Real = 29.057750463592832;
                                attribute Ixx : Real = 0.1325092216258331;
                                attribute 'σ_Ixx' : Real = 0.37074144170588635;
                                attribute Iyy : Real = 0.123676805384576;
                                attribute 'σ_Iyy' : Real = 0.3723953238821935;
                                attribute Izz : Real = 0.13601064976554533;
                                attribute 'σ_Izz' : Real = 0.37017423652493897;
                                attribute Ixy : Real = -0.002160799402098139;
                                attribute 'σ_Ixy' : Real = 0.02351283871158888;
                                attribute Ixz : Real = -0.006908083565418185;
                                attribute 'σ_Ixz' : Real = 0.022566176940390956;
                                attribute Iyz : Real = 0.003984872657702617;
                                attribute 'σ_Iyz' : Real = 0.02209918015384651;
                            }
                        }
                    }
                    part <'C.1.1.2.1.3'> 'Assembly 9' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.1.3.1'> 'Subassembly 32' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.3.1.1'> 'Part 112' {
                                attribute POIconv : String = "+";
                                attribute Ipoint : Boolean = false;
                                attribute mass : Real = 0.9338561952691525;
                                attribute 'σ_mass' : Real = 0.28909372274994966;
                                attribute Cx : Real = 5.118827288970351;
                                attribute 'σ_Cx' : Real = 28.721044428837228;
                                attribute Cy : Real = 38.082514423877;
                                attribute 'σ_Cy' : Real = 28.23690002309109;
                                attribute Cz : Real = 26.7289356328547;
                                attribute 'σ_Cz' : Real = 29.057750463592832;
                                attribute Ixx : Real = 1.1653744023503134;
                                attribute 'σ_Ixx' : Real = 0.37074144170588635;
                                attribute Iyy : Real = 1.0217089291343224;
                                attribute 'σ_Iyy' : Real = 0.3723953238821935;
                                attribute Izz : Real = 1.1819552403384748;
                                attribute 'σ_Izz' : Real = 0.37017423652493897;
                                attribute Ixy : Real = 0.024492219948517715;
                                attribute 'σ_Ixy' : Real = 0.02351283871158888;
                                attribute Ixz : Real = 0.022118243911945664;
                                attribute 'σ_Ixz' : Real = 0.022566176940390956;
                                attribute Iyz : Real = 0.058857174830539566;
                                attribute 'σ_Iyz' : Real = 0.02209918015384651;
                            }
                            part <'C.1.1.2.1.3.1.2'> 'Part 113' {
                                attribute POIconv : String = "-";
                                attribute Ipoint : Boolean = false;
                                attribute mass : Real = 0.46186563328118063;
                                attribute 'σ_mass' : Real = 0.28909372274994966;
                                attribute Cx : Real = -75.57860091328621;
                                attribute 'σ_Cx' : Real = 28.721044428837228;
                                attribute Cy : Real = -4.03018151409924;
                                attribute 'σ_Cy' : Real = 28.23690002309109;
                                attribute Cz : Real = 53.984742099419236;
                                attribute 'σ_Cz' : Real = 29.057750463592832;
                                attribute Ixx : Real = 0.6544389798744261;
                                attribute 'σ_Ixx' : Real = 0.37074144170588635;
                                attribute Iyy : Real = 0.6051954167904072;
                                attribute 'σ_Iyy' : Real = 0.3723953238821935;
                                attribute Izz : Real = 0.6569215736905387;
                                attribute 'σ_Izz' : Real = 0.37017423652493897;
                                attribute Ixy : Real = 0.008806620127162554;
                                attribute 'σ_Ixy' : Real = 0.02351283871158888;
                                attribute Ixz : Real = 0.05389548984110589;
                                attribute 'σ_Ixz' : Real = 0.022566176940390956;
                                attribute Iyz : Real = 0.007088110613877704;
                                attribute 'σ_Iyz' : Real = 0.02209918015384651;
                            }
                            part <'C.1.1.2.1.3.1.3'> 'Part 114' {
                                attribute POIconv : String = "-";
                                attribute Ipoint : Boolean = false;
                                attribute mass : Real = 0.3358498263717629;
                                attribute 'σ_mass' : Real = 0.28909372274994966;
                                attribute Cx : Real = 48.036784678697586;
                                attribute 'σ_Cx' : Real = 28.721044428837228;
                                attribute Cy : Real = -9.105567447841167;
                                attribute 'σ_Cy' : Real = 28.23690002309109;
                                attribute Cz : Real = 87.98765544779599;
                                attribute 'σ_Cz' : Real = 29.057750463592832;
                                attribute Ixx : Real = 0.4036096597763855;
                                attribute 'σ_Ixx' : Real = 0.37074144170588635;
                                attribute Iyy : Real = 0.30456547608063844;
                                attribute 'σ_Iyy' : Real = 0.3723953238821935;
                                attribute Izz : Real = 0.38373968395260816;
                                attribute 'σ_Izz' : Real = 0.37017423652493897;
                                attribute Ixy : Real = 0.005718439933556093;
                                attribute 'σ_Ixy' : Real = 0.02351283871158888;
                                attribute Ixz : Real = -0.0019330384034318149;
                                attribute 'σ_Ixz' : Real = 0.022566176940390956;
                                attribute Iyz : Real = 0.02271026451536909;
                                attribute 'σ_Iyz' : Real = 0.02209918015384651;
                            }
                            part <'C.1.1.2.1.3.1.4'> 'Part 115' {
                                attribute POIconv : String = "-";
                                attribute Ipoint : Boolean = false;
                                attribute mass : Real = 0.018310213478747756;
                                attribute 'σ_mass' : Real = 0.28909372274994966;
                                attribute Cx : Real = 31.33829841390252;
                                attribute 'σ_Cx' : Real = 28.721044428837228;
                                attribute Cy : Real = 63.64885116927326;
                                attribute 'σ_Cy' : Real = 28.23690002309109;
                                attribute Cz : Real = -59.613018995150924;
                                attribute 'σ_Cz' : Real = 29.057750463592832;
                                attribute Ixx : Real = 0.019225622157582483;
                                attribute 'σ_Ixx' : Real = 0.37074144170588635;
                                attribute Iyy : Real = 0.022425787941668107;
                                attribute 'σ_Iyy' : Real = 0.3723953238821935;
                                attribute Izz : Real = 0.023856757290600834;
                                attribute 'σ_Izz' : Real = 0.37017423652493897;
                                attribute Ixy : Real = 5.787205242036946e-4;
                                attribute 'σ_Ixy' : Real = 0.02351283871158888;
                                attribute Ixz : Real = 0.0012334291663465362;
                                attribute 'σ_Ixz' : Real = 0.022566176940390956;
                                attribute Iyz : Real = -3.3729378829955233e-4;
                                attribute 'σ_Iyz' : Real = 0.02209918015384651;
                            }
                        }
                        part <'C.1.1.2.1.3.2'> 'Subassembly 33' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.3.2.1'> 'Part 116' {
                                attribute POIconv : String = "-";
                                attribute Ipoint : Boolean = false;
                                attribute mass : Real = 0.3936766101690009;
                                attribute 'σ_mass' : Real = 0.28909372274994966;
                                attribute Cx : Real = -67.25974958389997;
                                attribute 'σ_Cx' : Real = 28.721044428837228;
                                attribute Cy : Real = -98.08319783769548;
                                attribute 'σ_Cy' : Real = 28.23690002309109;
                                attribute Cz : Real = 44.33659543283284;
                                attribute 'σ_Cz' : Real = 29.057750463592832;
                                attribute Ixx : Real = 0.5036420194160385;
                                attribute 'σ_Ixx' : Real = 0.37074144170588635;
                                attribute Iyy : Real = 0.4364101412128482;
                                attribute 'σ_Iyy' : Real = 0.3723953238821935;
                                attribute Izz : Real = 0.40619304174458926;
                                attribute 'σ_Izz' : Real = 0.37017423652493897;
                                attribute Ixy : Real = -0.01574896619593659;
                                attribute 'σ_Ixy' : Real = 0.02351283871158888;
                                attribute Ixz : Real = -0.003018634211898349;
                                attribute 'σ_Ixz' : Real = 0.022566176940390956;
                                attribute Iyz : Real = 0.012361048749388657;
                                attribute 'σ_Iyz' : Real = 0.02209918015384651;
                            }
                            part <'C.1.1.2.1.3.2.2'> 'Part 117' {
                                attribute POIconv : String = "-";
                                attribute Ipoint : Boolean = false;
                                attribute mass : Real = 0.5246422383305617;
                                attribute 'σ_mass' : Real = 0.28909372274994966;
                                attribute Cx : Real = 32.32352756895125;
                                attribute 'σ_Cx' : Real = 28.721044428837228;
                                attribute Cy : Real = -46.409074077382684;
                                attribute 'σ_Cy' : Real = 28.23690002309109;
                                attribute Cz : Real = -16.949916956946254;
                                attribute 'σ_Cz' : Real = 29.057750463592832;
                                attribute Ixx : Real = 0.6436906708469579;
                                attribute 'σ_Ixx' : Real = 0.37074144170588635;
                                attribute Iyy : Real = 0.6149535511979446;
                                attribute 'σ_Iyy' : Real = 0.3723953238821935;
                                attribute Izz : Real = 0.7098660760803621;
                                attribute 'σ_Izz' : Real = 0.37017423652493897;
                                attribute Ixy : Real = 0.011890361589308753;
                                attribute 'σ_Ixy' : Real = 0.02351283871158888;
                                attribute Ixz : Real = -0.0021314587259172865;
                                attribute 'σ_Ixz' : Real = 0.022566176940390956;
                                attribute Iyz : Real = 0.0028707870176387803;
                                attribute 'σ_Iyz' : Real = 0.02209918015384651;
                            }
                            part <'C.1.1.2.1.3.2.3'> 'Part 118' {
                                attribute POIconv : String = "-";
                                attribute Ipoint : Boolean = false;
                                attribute mass : Real = 0.7778466038098559;
                                attribute 'σ_mass' : Real = 0.28909372274994966;
                                attribute Cx : Real = 16.84051863849163;
                                attribute 'σ_Cx' : Real = 28.721044428837228;
                                attribute Cy : Real = -31.029005255550146;
                                attribute 'σ_Cy' : Real = 28.23690002309109;
                                attribute Cz : Real = 10.597925912588835;
                                attribute 'σ_Cz' : Real = 29.057750463592832;
                                attribute Ixx : Real = 0.8273860842706021;
                                attribute 'σ_Ixx' : Real = 0.37074144170588635;
                                attribute Iyy : Real = 0.8026428459334166;
                                attribute 'σ_Iyy' : Real = 0.3723953238821935;
                                attribute Izz : Real = 0.8194783115407178;
                                attribute 'σ_Izz' : Real = 0.37017423652493897;
                                attribute Ixy : Real = 0.03416966765977332;
                                attribute 'σ_Ixy' : Real = 0.02351283871158888;
                                attribute Ixz : Real = 0.031207226482758837;
                                attribute 'σ_Ixz' : Real = 0.022566176940390956;
                                attribute Iyz : Real = -0.04057685660210353;
                                attribute 'σ_Iyz' : Real = 0.02209918015384651;
                            }
                        }
                        part <'C.1.1.2.1.3.3'> 'Subassembly 34' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.3.3.1'> 'Part 119' {
                                attribute POIconv : String = "-";
                                attribute Ipoint : Boolean = false;
                                attribute mass : Real = 0.18373120276862756;
                                attribute 'σ_mass' : Real = 0.28909372274994966;
                                attribute Cx : Real = 31.09825341962278;
                                attribute 'σ_Cx' : Real = 28.721044428837228;
                                attribute Cy : Real = -24.085907684639096;
                                attribute 'σ_Cy' : Real = 28.23690002309109;
                                attribute Cz : Real = 57.6162351295352;
                                attribute 'σ_Cz' : Real = 29.057750463592832;
                                attribute Ixx : Real = 0.27372510531737737;
                                attribute 'σ_Ixx' : Real = 0.37074144170588635;
                                attribute Iyy : Real = 0.23628389847206127;
                                attribute 'σ_Iyy' : Real = 0.3723953238821935;
                                attribute Izz : Real = 0.24874276083070115;
                                attribute 'σ_Izz' : Real = 0.37017423652493897;
                                attribute Ixy : Real = 0.01729516478271456;
                                attribute 'σ_Ixy' : Real = 0.02351283871158888;
                                attribute Ixz : Real = -0.006797130441033234;
                                attribute 'σ_Ixz' : Real = 0.022566176940390956;
                                attribute Iyz : Real = 0.00623895865617146;
                                attribute 'σ_Iyz' : Real = 0.02209918015384651;
                            }
                            part <'C.1.1.2.1.3.3.2'> 'Part 120' {
                                attribute POIconv : String = "-";
                                attribute Ipoint : Boolean = false;
                                attribute mass : Real = 0.6625305184298195;
                                attribute 'σ_mass' : Real = 0.28909372274994966;
                                attribute Cx : Real = -35.391599126160145;
                                attribute 'σ_Cx' : Real = 28.721044428837228;
                                attribute Cy : Real = -56.95078456774354;
                                attribute 'σ_Cy' : Real = 28.23690002309109;
                                attribute Cz : Real = 55.88827421888709;
                                attribute 'σ_Cz' : Real = 29.057750463592832;
                                attribute Ixx : Real = 0.6410104854477704;
                                attribute 'σ_Ixx' : Real = 0.37074144170588635;
                                attribute Iyy : Real = 0.7055550495293766;
                                attribute 'σ_Iyy' : Real = 0.3723953238821935;
                                attribute Izz : Real = 0.6513105721243234;
                                attribute 'σ_Izz' : Real = 0.37017423652493897;
                                attribute Ixy : Real = -0.004701371570255442;
                                attribute 'σ_Ixy' : Real = 0.02351283871158888;
                                attribute Ixz : Real = -0.052928650254065304;
                                attribute 'σ_Ixz' : Real = 0.022566176940390956;
                                attribute Iyz : Real = 0.020656573819666957;
                                attribute 'σ_Iyz' : Real = 0.02209918015384651;
                            }
                            part <'C.1.1.2.1.3.3.3'> 'Part 121' {
                                attribute POIconv : String = "-";
                                attribute Ipoint : Boolean = false;
                                attribute mass : Real = 0.5431820213005413;
                                attribute 'σ_mass' : Real = 0.28909372274994966;
                                attribute Cx : Real = 26.398755982518196;
                                attribute 'σ_Cx' : Real = 28.721044428837228;
                                attribute Cy : Real = 91.28393102437258;
                                attribute 'σ_Cy' : Real = 28.23690002309109;
                                attribute Cz : Real = 83.53133285418153;
                                attribute 'σ_Cz' : Real = 29.057750463592832;
                                attribute Ixx : Real = 0.8120921944048798;
                                attribute 'σ_Ixx' : Real = 0.37074144170588635;
                                attribute Iyy : Real = 0.7307946289592773;
                                attribute 'σ_Iyy' : Real = 0.3723953238821935;
                                attribute Izz : Real = 0.7262356898771161;
                                attribute 'σ_Izz' : Real = 0.37017423652493897;
                                attribute Ixy : Real = -0.018511053224840215;
                                attribute 'σ_Ixy' : Real = 0.02351283871158888;
                                attribute Ixz : Real = 0.01200263532458008;
                                attribute 'σ_Ixz' : Real = 0.022566176940390956;
                                attribute Iyz : Real = -0.006901353997963102;
                                attribute 'σ_Iyz' : Real = 0.02209918015384651;
                            }
                        }
                        part <'C.1.1.2.1.3.4'> 'Subassembly 35' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.3.4.1'> 'Part 122' {
                                attribute POIconv : String = "+";
                                attribute Ipoint : Boolean = false;
                                attribute mass : Real = 0.1748610637704842;
                                attribute 'σ_mass' : Real = 0.28909372274994966;
                                attribute Cx : Real = -1.9168300554156303;
                                attribute 'σ_Cx' : Real = 28.721044428837228;
                                attribute Cy : Real = 98.88286697678268;
                                attribute 'σ_Cy' : Real = 28.23690002309109;
                                attribute Cz : Real = 93.15288970246911;
                                attribute 'σ_Cz' : Real = 29.057750463592832;
                                attribute Ixx : Real = 0.2098309765660314;
                                attribute 'σ_Ixx' : Real = 0.37074144170588635;
                                attribute Iyy : Real = 0.20114654134717325;
                                attribute 'σ_Iyy' : Real = 0.3723953238821935;
                                attribute Izz : Real = 0.197896232797806;
                                attribute 'σ_Izz' : Real = 0.37017423652493897;
                                attribute Ixy : Real = -0.0029645845771882505;
                                attribute 'σ_Ixy' : Real = 0.02351283871158888;
                                attribute Ixz : Real = -0.0036342567532666125;
                                attribute 'σ_Ixz' : Real = 0.022566176940390956;
                                attribute Iyz : Real = 0.015297162709185689;
                                attribute 'σ_Iyz' : Real = 0.02209918015384651;
                            }
                            part <'C.1.1.2.1.3.4.2'> 'Part 123' {
                                attribute POIconv : String = "+";
                                attribute Ipoint : Boolean = false;
                                attribute mass : Real = 0.95654023464676;
                                attribute 'σ_mass' : Real = 0.28909372274994966;
                                attribute Cx : Real = -25.246348092332482;
                                attribute 'σ_Cx' : Real = 28.721044428837228;
                                attribute Cy : Real = -78.3324426971376;
                                attribute 'σ_Cy' : Real = 28.23690002309109;
                                attribute Cz : Real = -73.83304671384394;
                                attribute 'σ_Cz' : Real = 29.057750463592832;
                                attribute Ixx : Real = 1.2842653344273014;
                                attribute 'σ_Ixx' : Real = 0.37074144170588635;
                                attribute Iyy : Real = 1.3928357564714327;
                                attribute 'σ_Iyy' : Real = 0.3723953238821935;
                                attribute Izz : Real = 1.3104788193380403;
                                attribute 'σ_Izz' : Real = 0.37017423652493897;
                                attribute Ixy : Real = 0.03837439862975049;
                                attribute 'σ_Ixy' : Real = 0.02351283871158888;
                                attribute Ixz : Real = -0.04813686107031087;
                                attribute 'σ_Ixz' : Real = 0.022566176940390956;
                                attribute Iyz : Real = -0.03632213506196913;
                                attribute 'σ_Iyz' : Real = 0.02209918015384651;
                            }
                        }
                    }
                    part <'C.1.1.2.1.4'> 'Assembly 10' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.1.4.1'> 'Subassembly 36' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.4.1.1'> 'Part 124' {
                                attribute POIconv : String = "-";
                                attribute Ipoint : Boolean = false;
                                attribute mass : Real = 0.23447460628300906;
                                attribute 'σ_mass' : Real = 0.28909372274994966;
                                attribute Cx : Real = 77.25934558548033;
                                attribute 'σ_Cx' : Real = 28.721044428837228;
                                attribute Cy : Real = 19.524044264107943;
                                attribute 'σ_Cy' : Real = 28.23690002309109;
                                attribute Cz : Real = 12.23496524617076;
                                attribute 'σ_Cz' : Real = 29.057750463592832;
                                attribute Ixx : Real = 0.33760943682442096;
                                attribute 'σ_Ixx' : Real = 0.37074144170588635;
                                attribute Iyy : Real = 0.3257122136181345;
                                attribute 'σ_Iyy' : Real = 0.3723953238821935;
                                attribute Izz : Real = 0.3508556112357001;
                                attribute 'σ_Izz' : Real = 0.37017423652493897;
                                attribute Ixy : Real = 0.018267723266434745;
                                attribute 'σ_Ixy' : Real = 0.02351283871158888;
                                attribute Ixz : Real = -0.0025852143004990906;
                                attribute 'σ_Ixz' : Real = 0.022566176940390956;
                                attribute Iyz : Real = 0.003166833910781492;
                                attribute 'σ_Iyz' : Real = 0.02209918015384651;
                            }
                            part <'C.1.1.2.1.4.1.2'> 'Part 125' {
                                attribute POIconv : String = "+";
                                attribute Ipoint : Boolean = false;
                                attribute mass : Real = 0.6192206798119004;
                                attribute 'σ_mass' : Real = 0.28909372274994966;
                                attribute Cx : Real = -86.5062297321856;
                                attribute 'σ_Cx' : Real = 28.721044428837228;
                                attribute Cy : Real = -96.74830525182188;
                                attribute 'σ_Cy' : Real = 28.23690002309109;
                                attribute Cz : Real = -68.38606670498848;
                                attribute 'σ_Cz' : Real = 29.057750463592832;
                                attribute Ixx : Real = 0.9871806816772882;
                                attribute 'σ_Ixx' : Real = 0.37074144170588635;
                                attribute Iyy : Real = 0.9941350619349281;
                                attribute 'σ_Iyy' : Real = 0.3723953238821935;
                                attribute Izz : Real = 0.9835767364973861;
                                attribute 'σ_Izz' : Real = 0.37017423652493897;
                                attribute Ixy : Real = 0.006783720605849883;
                                attribute 'σ_Ixy' : Real = 0.02351283871158888;
                                attribute Ixz : Real = 0.006824846766921822;
                                attribute 'σ_Ixz' : Real = 0.022566176940390956;
                                attribute Iyz : Real = -0.010056441023861532;
                                attribute 'σ_Iyz' : Real = 0.02209918015384651;
                            }
                            part <'C.1.1.2.1.4.1.3'> 'Part 126' {
                                attribute POIconv : String = "-";
                                attribute Ipoint : Boolean = false;
                                attribute mass : Real = 0.33214889976754786;
                                attribute 'σ_mass' : Real = 0.28909372274994966;
                                attribute Cx : Real = -40.611545788124204;
                                attribute 'σ_Cx' : Real = 28.721044428837228;
                                attribute Cy : Real = 56.04165489785373;
                                attribute 'σ_Cy' : Real = 28.23690002309109;
                                attribute Cz : Real = -15.420281514525414;
                                attribute 'σ_Cz' : Real = 29.057750463592832;
                                attribute Ixx : Real = 0.3638069389480099;
                                attribute 'σ_Ixx' : Real = 0.37074144170588635;
                                attribute Iyy : Real = 0.3772242942786602;
                                attribute 'σ_Iyy' : Real = 0.3723953238821935;
                                attribute Izz : Real = 0.37874346984864543;
                                attribute 'σ_Izz' : Real = 0.37017423652493897;
                                attribute Ixy : Real = -0.006927884021614925;
                                attribute 'σ_Ixy' : Real = 0.02351283871158888;
                                attribute Ixz : Real = 0.009380585960091711;
                                attribute 'σ_Ixz' : Real = 0.022566176940390956;
                                attribute Iyz : Real = -0.009317533936621646;
                                attribute 'σ_Iyz' : Real = 0.02209918015384651;
                            }
                        }
                        part <'C.1.1.2.1.4.2'> 'Subassembly 37' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.4.2.1'> 'Part 127' {
                                attribute POIconv : String = "-";
                                attribute Ipoint : Boolean = false;
                                attribute mass : Real = 0.4957759951716289;
                                attribute 'σ_mass' : Real = 0.28909372274994966;
                                attribute Cx : Real = 18.431154219433665;
                                attribute 'σ_Cx' : Real = 28.721044428837228;
                                attribute Cy : Real = -82.50533048994839;
                                attribute 'σ_Cy' : Real = 28.23690002309109;
                                attribute Cz : Real = 98.84459828026593;
                                attribute 'σ_Cz' : Real = 29.057750463592832;
                                attribute Ixx : Real = 0.5286776004907918;
                                attribute 'σ_Ixx' : Real = 0.37074144170588635;
                                attribute Iyy : Real = 0.5708044860358918;
                                attribute 'σ_Iyy' : Real = 0.3723953238821935;
                                attribute Izz : Real = 0.52383640923802;
                                attribute 'σ_Izz' : Real = 0.37017423652493897;
                                attribute Ixy : Real = 0.017712193363592185;
                                attribute 'σ_Ixy' : Real = 0.02351283871158888;
                                attribute Ixz : Real = -0.0035164365329158434;
                                attribute 'σ_Ixz' : Real = 0.022566176940390956;
                                attribute Iyz : Real = -0.007319028275059267;
                                attribute 'σ_Iyz' : Real = 0.02209918015384651;
                            }
                            part <'C.1.1.2.1.4.2.2'> 'Part 128' {
                                attribute POIconv : String = "-";
                                attribute Ipoint : Boolean = false;
                                attribute mass : Real = 0.8807608322163578;
                                attribute 'σ_mass' : Real = 0.28909372274994966;
                                attribute Cx : Real = -37.91659162379801;
                                attribute 'σ_Cx' : Real = 28.721044428837228;
                                attribute Cy : Real = -96.924460073933;
                                attribute 'σ_Cy' : Real = 28.23690002309109;
                                attribute Cz : Real = 29.28264937363565;
                                attribute 'σ_Cz' : Real = 29.057750463592832;
                                attribute Ixx : Real = 1.1063320662331158;
                                attribute 'σ_Ixx' : Real = 0.37074144170588635;
                                attribute Iyy : Real = 1.2682195369159506;
                                attribute 'σ_Iyy' : Real = 0.3723953238821935;
                                attribute Izz : Real = 1.049335223667783;
                                attribute 'σ_Izz' : Real = 0.37017423652493897;
                                attribute Ixy : Real = -0.08539073804645332;
                                attribute 'σ_Ixy' : Real = 0.02351283871158888;
                                attribute Ixz : Real = 0.0179739801162003;
                                attribute 'σ_Ixz' : Real = 0.022566176940390956;
                                attribute Iyz : Real = -0.003457029164869484;
                                attribute 'σ_Iyz' : Real = 0.02209918015384651;
                            }
                            part <'C.1.1.2.1.4.2.3'> 'Part 129' {
                                attribute POIconv : String = "-";
                                attribute Ipoint : Boolean = false;
                                attribute mass : Real = 0.4885202861928847;
                                attribute 'σ_mass' : Real = 0.28909372274994966;
                                attribute Cx : Real = 74.1569550242275;
                                attribute 'σ_Cx' : Real = 28.721044428837228;
                                attribute Cy : Real = -0.19180597737431526;
                                attribute 'σ_Cy' : Real = 28.23690002309109;
                                attribute Cz : Real = 54.23494102433324;
                                attribute 'σ_Cz' : Real = 29.057750463592832;
                                attribute Ixx : Real = 0.7329805623354415;
                                attribute 'σ_Ixx' : Real = 0.37074144170588635;
                                attribute Iyy : Real = 0.6990801407418776;
                                attribute 'σ_Iyy' : Real = 0.3723953238821935;
                                attribute Izz : Real = 0.6730097009794579;
                                attribute 'σ_Izz' : Real = 0.37017423652493897;
                                attribute Ixy : Real = 0.01009572963695184;
                                attribute 'σ_Ixy' : Real = 0.02351283871158888;
                                attribute Ixz : Real = 0.014573420691217233;
                                attribute 'σ_Ixz' : Real = 0.022566176940390956;
                                attribute Iyz : Real = -0.016796732980520805;
                                attribute 'σ_Iyz' : Real = 0.02209918015384651;
                            }
                        }
                        part <'C.1.1.2.1.4.3'> 'Subassembly 38' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.4.3.1'> 'Part 130' {
                                attribute POIconv : String = "+";
                                attribute Ipoint : Boolean = false;
                                attribute mass : Real = 0.14198284141719342;
                                attribute 'σ_mass' : Real = 0.28909372274994966;
                                attribute Cx : Real = -73.916393565014;
                                attribute 'σ_Cx' : Real = 28.721044428837228;
                                attribute Cy : Real = 23.420857964083552;
                                attribute 'σ_Cy' : Real = 28.23690002309109;
                                attribute Cz : Real = -68.08523307554424;
                                attribute 'σ_Cz' : Real = 29.057750463592832;
                                attribute Ixx : Real = 0.17459145689449226;
                                attribute 'σ_Ixx' : Real = 0.37074144170588635;
                                attribute Iyy : Real = 0.18512921711189126;
                                attribute 'σ_Iyy' : Real = 0.3723953238821935;
                                attribute Izz : Real = 0.2117745645151967;
                                attribute 'σ_Izz' : Real = 0.37017423652493897;
                                attribute Ixy : Real = -7.834183456654027e-4;
                                attribute 'σ_Ixy' : Real = 0.02351283871158888;
                                attribute Ixz : Real = 0.002452268902502458;
                                attribute 'σ_Ixz' : Real = 0.022566176940390956;
                                attribute Iyz : Real = 0.01859493967813753;
                                attribute 'σ_Iyz' : Real = 0.02209918015384651;
                            }
                            part <'C.1.1.2.1.4.3.2'> 'Part 131' {
                                attribute POIconv : String = "-";
                                attribute Ipoint : Boolean = false;
                                attribute mass : Real = 0.02294431808940135;
                                attribute 'σ_mass' : Real = 0.28909372274994966;
                                attribute Cx : Real = -32.0907271001488;
                                attribute 'σ_Cx' : Real = 28.721044428837228;
                                attribute Cy : Real = 38.18034525029361;
                                attribute 'σ_Cy' : Real = 28.23690002309109;
                                attribute Cz : Real = -81.63100318051875;
                                attribute 'σ_Cz' : Real = 29.057750463592832;
                                attribute Ixx : Real = 0.023836702726453995;
                                attribute 'σ_Ixx' : Real = 0.37074144170588635;
                                attribute Iyy : Real = 0.025088736877533106;
                                attribute 'σ_Iyy' : Real = 0.3723953238821935;
                                attribute Izz : Real = 0.02798837960848096;
                                attribute 'σ_Izz' : Real = 0.37017423652493897;
                                attribute Ixy : Real = -0.0032552824928376786;
                                attribute 'σ_Ixy' : Real = 0.02351283871158888;
                                attribute Ixz : Real = 6.857683075510088e-4;
                                attribute 'σ_Ixz' : Real = 0.022566176940390956;
                                attribute Iyz : Real = 4.502117066058381e-4;
                                attribute 'σ_Iyz' : Real = 0.02209918015384651;
                            }
                        }
                    }
                    part <'C.1.1.2.1.5'> 'Assembly 11' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.1.5.1'> 'Subassembly 39' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.5.1.1'> 'Part 132' {
                                attribute POIconv : String = "-";
                                attribute Ipoint : Boolean = false;
                                attribute mass : Real = 0.5447481498254929;
                                attribute 'σ_mass' : Real = 0.28909372274994966;
                                attribute Cx : Real = -20.864103361964226;
                                attribute 'σ_Cx' : Real = 28.721044428837228;
                                attribute Cy : Real = -81.62685362622142;
                                attribute 'σ_Cy' : Real = 28.23690002309109;
                                attribute Cz : Real = 17.97395357862115;
                                attribute 'σ_Cz' : Real = 29.057750463592832;
                                attribute Ixx : Real = 0.5130627845459527;
                                attribute 'σ_Ixx' : Real = 0.37074144170588635;
                                attribute Iyy : Real = 0.4968297851749982;
                                attribute 'σ_Iyy' : Real = 0.3723953238821935;
                                attribute Izz : Real = 0.5109684194588667;
                                attribute 'σ_Izz' : Real = 0.37017423652493897;
                                attribute Ixy : Real = 0.0036725636275820503;
                                attribute 'σ_Ixy' : Real = 0.02351283871158888;
                                attribute Ixz : Real = -0.006936378657597641;
                                attribute 'σ_Ixz' : Real = 0.022566176940390956;
                                attribute Iyz : Real = 0.01882163310990817;
                                attribute 'σ_Iyz' : Real = 0.02209918015384651;
                            }
                            part <'C.1.1.2.1.5.1.2'> 'Part 133' {
                                attribute POIconv : String = "-";
                                attribute Ipoint : Boolean = false;
                                attribute mass : Real = 0.8436234026858583;
                                attribute 'σ_mass' : Real = 0.28909372274994966;
                                attribute Cx : Real = -49.32384677231312;
                                attribute 'σ_Cx' : Real = 28.721044428837228;
                                attribute Cy : Real = 18.329235026612878;
                                attribute 'σ_Cy' : Real = 28.23690002309109;
                                attribute Cz : Real = 36.198614398017526;
                                attribute 'σ_Cz' : Real = 29.057750463592832;
                                attribute Ixx : Real = 1.38693099467527;
                                attribute 'σ_Ixx' : Real = 0.37074144170588635;
                                attribute Iyy : Real = 1.3063913980778492;
                                attribute 'σ_Iyy' : Real = 0.3723953238821935;
                                attribute Izz : Real = 1.3178038998415318;
                                attribute 'σ_Izz' : Real = 0.37017423652493897;
                                attribute Ixy : Real = -0.015861692037110478;
                                attribute 'σ_Ixy' : Real = 0.02351283871158888;
                                attribute Ixz : Real = 0.02828794807666528;
                                attribute 'σ_Ixz' : Real = 0.022566176940390956;
                                attribute Iyz : Real = -0.00411327201991964;
                                attribute 'σ_Iyz' : Real = 0.02209918015384651;
                            }
                            part <'C.1.1.2.1.5.1.3'> 'Part 134' {
                                attribute POIconv : String = "+";
                                attribute Ipoint : Boolean = false;
                                attribute mass : Real = 0.5824006713996641;
                                attribute 'σ_mass' : Real = 0.28909372274994966;
                                attribute Cx : Real = 93.24663882143795;
                                attribute 'σ_Cx' : Real = 28.721044428837228;
                                attribute Cy : Real = 76.3129263650626;
                                attribute 'σ_Cy' : Real = 28.23690002309109;
                                attribute Cz : Real = 61.39633618295193;
                                attribute 'σ_Cz' : Real = 29.057750463592832;
                                attribute Ixx : Real = 0.7129259852741276;
                                attribute 'σ_Ixx' : Real = 0.37074144170588635;
                                attribute Iyy : Real = 0.686126297392601;
                                attribute 'σ_Iyy' : Real = 0.3723953238821935;
                                attribute Izz : Real = 0.6654475053164781;
                                attribute 'σ_Izz' : Real = 0.37017423652493897;
                                attribute Ixy : Real = 0.010834347812575203;
                                attribute 'σ_Ixy' : Real = 0.02351283871158888;
                                attribute Ixz : Real = 0.03531242626553843;
                                attribute 'σ_Ixz' : Real = 0.022566176940390956;
                                attribute Iyz : Real = 0.0061909824000929;
                                attribute 'σ_Iyz' : Real = 0.02209918015384651;
                            }
                            part <'C.1.1.2.1.5.1.4'> 'Part 135' {
                                attribute POIconv : String = "+";
                                attribute Ipoint : Boolean = false;
                                attribute mass : Real = 0.12478426721296274;
                                attribute 'σ_mass' : Real = 0.28909372274994966;
                                attribute Cx : Real = -24.885624833405018;
                                attribute 'σ_Cx' : Real = 28.721044428837228;
                                attribute Cy : Real = 69.08309417776763;
                                attribute 'σ_Cy' : Real = 28.23690002309109;
                                attribute Cz : Real = 33.07829308323562;
                                attribute 'σ_Cz' : Real = 29.057750463592832;
                                attribute Ixx : Real = 0.16729162841915973;
                                attribute 'σ_Ixx' : Real = 0.37074144170588635;
                                attribute Iyy : Real = 0.1675720632074804;
                                attribute 'σ_Iyy' : Real = 0.3723953238821935;
                                attribute Izz : Real = 0.1788596220331902;
                                attribute 'σ_Izz' : Real = 0.37017423652493897;
                                attribute Ixy : Real = 0.0061222076255589685;
                                attribute 'σ_Ixy' : Real = 0.02351283871158888;
                                attribute Ixz : Real = -6.39257326523658e-4;
                                attribute 'σ_Ixz' : Real = 0.022566176940390956;
                                attribute Iyz : Real = 0.012940473403577082;
                                attribute 'σ_Iyz' : Real = 0.02209918015384651;
                            }
                            part <'C.1.1.2.1.5.1.5'> 'Part 136' {
                                attribute POIconv : String = "-";
                                attribute Ipoint : Boolean = false;
                                attribute mass : Real = 0.7526343445971142;
                                attribute 'σ_mass' : Real = 0.28909372274994966;
                                attribute Cx : Real = -89.76666345261037;
                                attribute 'σ_Cx' : Real = 28.721044428837228;
                                attribute Cy : Real = -19.528738548979163;
                                attribute 'σ_Cy' : Real = 28.23690002309109;
                                attribute Cz : Real = -20.769359869882464;
                                attribute 'σ_Cz' : Real = 29.057750463592832;
                                attribute Ixx : Real = 0.9786911379695393;
                                attribute 'σ_Ixx' : Real = 0.37074144170588635;
                                attribute Iyy : Real = 0.9700725852833165;
                                attribute 'σ_Iyy' : Real = 0.3723953238821935;
                                attribute Izz : Real = 0.9060240286801441;
                                attribute 'σ_Izz' : Real = 0.37017423652493897;
                                attribute Ixy : Real = 0.002023714339072712;
                                attribute 'σ_Ixy' : Real = 0.02351283871158888;
                                attribute Ixz : Real = -3.9750999514207643e-4;
                                attribute 'σ_Ixz' : Real = 0.022566176940390956;
                                attribute Iyz : Real = 0.00885074351613383;
                                attribute 'σ_Iyz' : Real = 0.02209918015384651;
                            }
                        }
                        part <'C.1.1.2.1.5.2'> 'Subassembly 40' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.5.2.1'> 'Part 137' {
                                attribute POIconv : String = "+";
                                attribute Ipoint : Boolean = false;
                                attribute mass : Real = 0.676165806948673;
                                attribute 'σ_mass' : Real = 0.28909372274994966;
                                attribute Cx : Real = -96.10035391524434;
                                attribute 'σ_Cx' : Real = 28.721044428837228;
                                attribute Cy : Real = -69.41496604122221;
                                attribute 'σ_Cy' : Real = 28.23690002309109;
                                attribute Cz : Real = -94.27793025970459;
                                attribute 'σ_Cz' : Real = 29.057750463592832;
                                attribute Ixx : Real = 0.8177669569200914;
                                attribute 'σ_Ixx' : Real = 0.37074144170588635;
                                attribute Iyy : Real = 0.7299320788650162;
                                attribute 'σ_Iyy' : Real = 0.3723953238821935;
                                attribute Izz : Real = 0.8097335357735644;
                                attribute 'σ_Izz' : Real = 0.37017423652493897;
                                attribute Ixy : Real = 0.01811276072234147;
                                attribute 'σ_Ixy' : Real = 0.02351283871158888;
                                attribute Ixz : Real = -0.05779361816424772;
                                attribute 'σ_Ixz' : Real = 0.022566176940390956;
                                attribute Iyz : Real = 0.04648571447315491;
                                attribute 'σ_Iyz' : Real = 0.02209918015384651;
                            }
                            part <'C.1.1.2.1.5.2.2'> 'Part 138' {
                                attribute POIconv : String = "-";
                                attribute Ipoint : Boolean = false;
                                attribute mass : Real = 0.8123143940349109;
                                attribute 'σ_mass' : Real = 0.28909372274994966;
                                attribute Cx : Real = -49.23978759907186;
                                attribute 'σ_Cx' : Real = 28.721044428837228;
                                attribute Cy : Real = 22.621416673064232;
                                attribute 'σ_Cy' : Real = 28.23690002309109;
                                attribute Cz : Real = 40.08059962652624;
                                attribute 'σ_Cz' : Real = 29.057750463592832;
                                attribute Ixx : Real = 1.002210221059507;
                                attribute 'σ_Ixx' : Real = 0.37074144170588635;
                                attribute Iyy : Real = 1.185394183821374;
                                attribute 'σ_Iyy' : Real = 0.3723953238821935;
                                attribute Izz : Real = 0.9463297037965218;
                                attribute 'σ_Izz' : Real = 0.37017423652493897;
                                attribute Ixy : Real = -0.022432198261390094;
                                attribute 'σ_Ixy' : Real = 0.02351283871158888;
                                attribute Ixz : Real = 0.034175143590491466;
                                attribute 'σ_Ixz' : Real = 0.022566176940390956;
                                attribute Iyz : Real = 0.08665344471318208;
                                attribute 'σ_Iyz' : Real = 0.02209918015384651;
                            }
                            part <'C.1.1.2.1.5.2.3'> 'Part 139' {
                                attribute POIconv : String = "-";
                                attribute Ipoint : Boolean = false;
                                attribute mass : Real = 0.12062828322360292;
                                attribute 'σ_mass' : Real = 0.28909372274994966;
                                attribute Cx : Real = 30.05693545565009;
                                attribute 'σ_Cx' : Real = 28.721044428837228;
                                attribute Cy : Real = -91.9261603616178;
                                attribute 'σ_Cy' : Real = 28.23690002309109;
                                attribute Cz : Real = -53.16067193634808;
                                attribute 'σ_Cz' : Real = 29.057750463592832;
                                attribute Ixx : Real = 0.15840495688468167;
                                attribute 'σ_Ixx' : Real = 0.37074144170588635;
                                attribute Iyy : Real = 0.15415726107422356;
                                attribute 'σ_Iyy' : Real = 0.3723953238821935;
                                attribute Izz : Real = 0.1506746933151752;
                                attribute 'σ_Izz' : Real = 0.37017423652493897;
                                attribute Ixy : Real = 0.006711086624961781;
                                attribute 'σ_Ixy' : Real = 0.02351283871158888;
                                attribute Ixz : Real = -0.0015860072164172753;
                                attribute 'σ_Ixz' : Real = 0.022566176940390956;
                                attribute Iyz : Real = -7.317874406657901e-4;
                                attribute 'σ_Iyz' : Real = 0.02209918015384651;
                            }
                        }
                        part <'C.1.1.2.1.5.3'> 'Subassembly 41' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.5.3.1'> 'Part 140' {
                                attribute POIconv : String = "-";
                                attribute Ipoint : Boolean = false;
                                attribute mass : Real = 0.28459705574368127;
                                attribute 'σ_mass' : Real = 0.28909372274994966;
                                attribute Cx : Real = -83.23765029199421;
                                attribute 'σ_Cx' : Real = 28.721044428837228;
                                attribute Cy : Real = 6.243040785193443;
                                attribute 'σ_Cy' : Real = 28.23690002309109;
                                attribute Cz : Real = -6.131899217143655;
                                attribute 'σ_Cz' : Real = 29.057750463592832;
                                attribute Ixx : Real = 0.3174809909585794;
                                attribute 'σ_Ixx' : Real = 0.37074144170588635;
                                attribute Iyy : Real = 0.36332572703877697;
                                attribute 'σ_Iyy' : Real = 0.3723953238821935;
                                attribute Izz : Real = 0.36544653798551574;
                                attribute 'σ_Izz' : Real = 0.37017423652493897;
                                attribute Ixy : Real = -0.021020534893919716;
                                attribute 'σ_Ixy' : Real = 0.02351283871158888;
                                attribute Ixz : Real = 0.0011902640754227955;
                                attribute 'σ_Ixz' : Real = 0.022566176940390956;
                                attribute Iyz : Real = 3.0644695781537024e-4;
                                attribute 'σ_Iyz' : Real = 0.02209918015384651;
                            }
                            part <'C.1.1.2.1.5.3.2'> 'Part 141' {
                                attribute POIconv : String = "+";
                                attribute Ipoint : Boolean = false;
                                attribute mass : Real = 0.5458731079851277;
                                attribute 'σ_mass' : Real = 0.28909372274994966;
                                attribute Cx : Real = -81.45713596604764;
                                attribute 'σ_Cx' : Real = 28.721044428837228;
                                attribute Cy : Real = -7.000693446025252;
                                attribute 'σ_Cy' : Real = 28.23690002309109;
                                attribute Cz : Real = -96.07520098797977;
                                attribute 'σ_Cz' : Real = 29.057750463592832;
                                attribute Ixx : Real = 0.5347265581717263;
                                attribute 'σ_Ixx' : Real = 0.37074144170588635;
                                attribute Iyy : Real = 0.5734655753935646;
                                attribute 'σ_Iyy' : Real = 0.3723953238821935;
                                attribute Izz : Real = 0.5902595852370592;
                                attribute 'σ_Izz' : Real = 0.37017423652493897;
                                attribute Ixy : Real = -0.02793345944694969;
                                attribute 'σ_Ixy' : Real = 0.02351283871158888;
                                attribute Ixz : Real = 0.027203295076605523;
                                attribute 'σ_Ixz' : Real = 0.022566176940390956;
                                attribute Iyz : Real = 0.0036293523578296983;
                                attribute 'σ_Iyz' : Real = 0.02209918015384651;
                            }
                            part <'C.1.1.2.1.5.3.3'> 'Part 142' {
                                attribute POIconv : String = "-";
                                attribute Ipoint : Boolean = false;
                                attribute mass : Real = 0.1344736803707201;
                                attribute 'σ_mass' : Real = 0.28909372274994966;
                                attribute Cx : Real = 10.61953529715538;
                                attribute 'σ_Cx' : Real = 28.721044428837228;
                                attribute Cy : Real = 91.78987140767276;
                                attribute 'σ_Cy' : Real = 28.23690002309109;
                                attribute Cz : Real = -69.49640740640461;
                                attribute 'σ_Cz' : Real = 29.057750463592832;
                                attribute Ixx : Real = 0.1994522258616676;
                                attribute 'σ_Ixx' : Real = 0.37074144170588635;
                                attribute Iyy : Real = 0.1967005418142774;
                                attribute 'σ_Iyy' : Real = 0.3723953238821935;
                                attribute Izz : Real = 0.1966584182224298;
                                attribute 'σ_Izz' : Real = 0.37017423652493897;
                                attribute Ixy : Real = 0.0025516026135663145;
                                attribute 'σ_Ixy' : Real = 0.02351283871158888;
                                attribute Ixz : Real = 0.0011009687983479684;
                                attribute 'σ_Ixz' : Real = 0.022566176940390956;
                                attribute Iyz : Real = 3.185896142718945e-4;
                                attribute 'σ_Iyz' : Real = 0.02209918015384651;
                            }
                        }
                        part <'C.1.1.2.1.5.4'> 'Subassembly 42' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.5.4.1'> 'Part 143' {
                                attribute POIconv : String = "+";
                                attribute Ipoint : Boolean = false;
                                attribute mass : Real = 0.1215258111958392;
                                attribute 'σ_mass' : Real = 0.28909372274994966;
                                attribute Cx : Real = 97.89935210719705;
                                attribute 'σ_Cx' : Real = 28.721044428837228;
                                attribute Cy : Real = -14.352465933188796;
                                attribute 'σ_Cy' : Real = 28.23690002309109;
                                attribute Cz : Real = 42.845899472013116;
                                attribute 'σ_Cz' : Real = 29.057750463592832;
                                attribute Ixx : Real = 0.17301150346399724;
                                attribute 'σ_Ixx' : Real = 0.37074144170588635;
                                attribute Iyy : Real = 0.15823515097252172;
                                attribute 'σ_Iyy' : Real = 0.3723953238821935;
                                attribute Izz : Real = 0.17622942245687723;
                                attribute 'σ_Izz' : Real = 0.37017423652493897;
                                attribute Ixy : Real = 0.006047759901812523;
                                attribute 'σ_Ixy' : Real = 0.02351283871158888;
                                attribute Ixz : Real = 0.008413166574839984;
                                attribute 'σ_Ixz' : Real = 0.022566176940390956;
                                attribute Iyz : Real = -4.807438877178667e-4;
                                attribute 'σ_Iyz' : Real = 0.02209918015384651;
                            }
                            part <'C.1.1.2.1.5.4.2'> 'Part 144' {
                                attribute POIconv : String = "+";
                                attribute Ipoint : Boolean = false;
                                attribute mass : Real = 0.46269242569990454;
                                attribute 'σ_mass' : Real = 0.28909372274994966;
                                attribute Cx : Real = -2.2517085541039705;
                                attribute 'σ_Cx' : Real = 28.721044428837228;
                                attribute Cy : Real = 83.73118420131505;
                                attribute 'σ_Cy' : Real = 28.23690002309109;
                                attribute Cz : Real = -98.01948610693216;
                                attribute 'σ_Cz' : Real = 29.057750463592832;
                                attribute Ixx : Real = 0.6048215949955417;
                                attribute 'σ_Ixx' : Real = 0.37074144170588635;
                                attribute Iyy : Real = 0.7201245139841406;
                                attribute 'σ_Iyy' : Real = 0.3723953238821935;
                                attribute Izz : Real = 0.5765976279600344;
                                attribute 'σ_Izz' : Real = 0.37017423652493897;
                                attribute Ixy : Real = -0.06448649363053159;
                                attribute 'σ_Ixy' : Real = 0.02351283871158888;
                                attribute Ixz : Real = 0.007168666867494928;
                                attribute 'σ_Ixz' : Real = 0.022566176940390956;
                                attribute Iyz : Real = 0.0162296272098285;
                                attribute 'σ_Iyz' : Real = 0.02209918015384651;
                            }
                            part <'C.1.1.2.1.5.4.3'> 'Part 145' {
                                attribute POIconv : String = "+";
                                attribute Ipoint : Boolean = false;
                                attribute mass : Real = 0.9827399011156521;
                                attribute 'σ_mass' : Real = 0.28909372274994966;
                                attribute Cx : Real = 66.33293624036014;
                                attribute 'σ_Cx' : Real = 28.721044428837228;
                                attribute Cy : Real = 49.1757424082607;
                                attribute 'σ_Cy' : Real = 28.23690002309109;
                                attribute Cz : Real = -18.6045931186527;
                                attribute 'σ_Cz' : Real = 29.057750463592832;
                                attribute Ixx : Real = 1.3108250003809785;
                                attribute 'σ_Ixx' : Real = 0.37074144170588635;
                                attribute Iyy : Real = 1.2985415627352457;
                                attribute 'σ_Iyy' : Real = 0.3723953238821935;
                                attribute Izz : Real = 1.0950475129815074;
                                attribute 'σ_Izz' : Real = 0.37017423652493897;
                                attribute Ixy : Real = -0.04401540679121507;
                                attribute 'σ_Ixy' : Real = 0.02351283871158888;
                                attribute Ixz : Real = -0.07174685322028279;
                                attribute 'σ_Ixz' : Real = 0.022566176940390956;
                                attribute Iyz : Real = 0.05532002807269491;
                                attribute 'σ_Iyz' : Real = 0.02209918015384651;
                            }
                            part <'C.1.1.2.1.5.4.4'> 'Part 146' {
                                attribute POIconv : String = "-";
                                attribute Ipoint : Boolean = false;
                                attribute mass : Real = 0.8762005920649972;
                                attribute 'σ_mass' : Real = 0.28909372274994966;
                                attribute Cx : Real = -55.63594405539334;
                                attribute 'σ_Cx' : Real = 28.721044428837228;
                                attribute Cy : Real = -45.388418808579445;
                                attribute 'σ_Cy' : Real = 28.23690002309109;
                                attribute Cz : Real = 27.493249252438545;
                                attribute 'σ_Cz' : Real = 29.057750463592832;
                                attribute Ixx : Real = 1.17859494960956;
                                attribute 'σ_Ixx' : Real = 0.37074144170588635;
                                attribute Iyy : Real = 1.1898543637982602;
                                attribute 'σ_Iyy' : Real = 0.3723953238821935;
                                attribute Izz : Real = 0.9244969492842944;
                                attribute 'σ_Izz' : Real = 0.37017423652493897;
                                attribute Ixy : Real = -0.004802690682821149;
                                attribute 'σ_Ixy' : Real = 0.02351283871158888;
                                attribute Ixz : Real = 0.033619872224326;
                                attribute 'σ_Ixz' : Real = 0.022566176940390956;
                                attribute Iyz : Real = -0.023429283271321405;
                                attribute 'σ_Iyz' : Real = 0.02209918015384651;
                            }
                            part <'C.1.1.2.1.5.4.5'> 'Part 147' {
                                attribute POIconv : String = "+";
                                attribute Ipoint : Boolean = false;
                                attribute mass : Real = 0.7790842246743851;
                                attribute 'σ_mass' : Real = 0.28909372274994966;
                                attribute Cx : Real = -5.9667938854545355;
                                attribute 'σ_Cx' : Real = 28.721044428837228;
                                attribute Cy : Real = -21.262207766994834;
                                attribute 'σ_Cy' : Real = 28.23690002309109;
                                attribute Cz : Real = -6.58764666877687;
                                attribute 'σ_Cz' : Real = 29.057750463592832;
                                attribute Ixx : Real = 0.9049289085296087;
                                attribute 'σ_Ixx' : Real = 0.37074144170588635;
                                attribute Iyy : Real = 1.0021354911993983;
                                attribute 'σ_Iyy' : Real = 0.3723953238821935;
                                attribute Izz : Real = 0.9534793197752769;
                                attribute 'σ_Izz' : Real = 0.37017423652493897;
                                attribute Ixy : Real = -0.046207166276300594;
                                attribute 'σ_Ixy' : Real = 0.02351283871158888;
                                attribute Ixz : Real = -0.08452388087665226;
                                attribute 'σ_Ixz' : Real = 0.022566176940390956;
                                attribute Iyz : Real = 0.06762880194057005;
                                attribute 'σ_Iyz' : Real = 0.02209918015384651;
                            }
                        }
                        part <'C.1.1.2.1.5.5'> 'Subassembly 43' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.1.5.5.1'> 'Part 148' {
                                attribute POIconv : String = "+";
                                attribute Ipoint : Boolean = false;
                                attribute mass : Real = 0.5692882913739886;
                                attribute 'σ_mass' : Real = 0.28909372274994966;
                                attribute Cx : Real = -20.47927901148796;
                                attribute 'σ_Cx' : Real = 28.721044428837228;
                                attribute Cy : Real = -33.217661594972014;
                                attribute 'σ_Cy' : Real = 28.23690002309109;
                                attribute Cz : Real = 8.835651725530624;
                                attribute 'σ_Cz' : Real = 29.057750463592832;
                                attribute Ixx : Real = 0.8289207536336094;
                                attribute 'σ_Ixx' : Real = 0.37074144170588635;
                                attribute Iyy : Real = 0.7676713468109841;
                                attribute 'σ_Iyy' : Real = 0.3723953238821935;
                                attribute Izz : Real = 0.8125309094102543;
                                attribute 'σ_Izz' : Real = 0.37017423652493897;
                                attribute Ixy : Real = 5.303710081927901e-4;
                                attribute 'σ_Ixy' : Real = 0.02351283871158888;
                                attribute Ixz : Real = 0.009410466876182872;
                                attribute 'σ_Ixz' : Real = 0.022566176940390956;
                                attribute Iyz : Real = 0.03702571528161821;
                                attribute 'σ_Iyz' : Real = 0.02209918015384651;
                            }
                            part <'C.1.1.2.1.5.5.2'> 'Part 149' {
                                attribute POIconv : String = "-";
                                attribute Ipoint : Boolean = false;
                                attribute mass : Real = 0.15183776629413478;
                                attribute 'σ_mass' : Real = 0.28909372274994966;
                                attribute Cx : Real = 59.654495073482394;
                                attribute 'σ_Cx' : Real = 28.721044428837228;
                                attribute Cy : Real = 49.16452025063336;
                                attribute 'σ_Cy' : Real = 28.23690002309109;
                                attribute Cz : Real = -8.414956089109182;
                                attribute 'σ_Cz' : Real = 29.057750463592832;
                                attribute Ixx : Real = 0.165857578928367;
                                attribute 'σ_Ixx' : Real = 0.37074144170588635;
                                attribute Iyy : Real = 0.17216267449049777;
                                attribute 'σ_Iyy' : Real = 0.3723953238821935;
                                attribute Izz : Real = 0.16724703343679237;
                                attribute 'σ_Izz' : Real = 0.37017423652493897;
                                attribute Ixy : Real = -0.00197736672212002;
                                attribute 'σ_Ixy' : Real = 0.02351283871158888;
                                attribute Ixz : Real = 0.0058231361076871374;
                                attribute 'σ_Ixz' : Real = 0.022566176940390956;
                                attribute Iyz : Real = 0.0018797894763217964;
                                attribute 'σ_Iyz' : Real = 0.02209918015384651;
                            }
                            part <'C.1.1.2.1.5.5.3'> 'Part 150' {
                                attribute POIconv : String = "-";
                                attribute Ipoint : Boolean = false;
                                attribute mass : Real = 0.10770200214954093;
                                attribute 'σ_mass' : Real = 0.28909372274994966;
                                attribute Cx : Real = 74.13820647634566;
                                attribute 'σ_Cx' : Real = 28.721044428837228;
                                attribute Cy : Real = -30.705874180421233;
                                attribute 'σ_Cy' : Real = 28.23690002309109;
                                attribute Cz : Real = 4.817138891667128;
                                attribute 'σ_Cz' : Real = 29.057750463592832;
                                attribute Ixx : Real = 0.1257832376891619;
                                attribute 'σ_Ixx' : Real = 0.37074144170588635;
                                attribute Iyy : Real = 0.10392978416812212;
                                attribute 'σ_Iyy' : Real = 0.3723953238821935;
                                attribute Izz : Real = 0.13898286923139067;
                                attribute 'σ_Izz' : Real = 0.37017423652493897;
                                attribute Ixy : Real = -0.003402490667846773;
                                attribute 'σ_Ixy' : Real = 0.02351283871158888;
                                attribute Ixz : Real = 0.0012548029673312864;
                                attribute 'σ_Ixz' : Real = 0.022566176940390956;
                                attribute Iyz : Real = -7.626846859778377e-6;
                                attribute 'σ_Iyz' : Real = 0.02209918015384651;
                            }
                            part <'C.1.1.2.1.5.5.4'> 'Part 151' {
                                attribute POIconv : String = "-";
                                attribute Ipoint : Boolean = false;
                                attribute mass : Real = 0.9767942562880926;
                                attribute 'σ_mass' : Real = 0.28909372274994966;
                                attribute Cx : Real = -53.13462843187153;
                                attribute 'σ_Cx' : Real = 28.721044428837228;
                                attribute Cy : Real = 18.97773602977395;
                                attribute 'σ_Cy' : Real = 28.23690002309109;
                                attribute Cz : Real = 98.64025609567761;
                                attribute 'σ_Cz' : Real = 29.057750463592832;
                                attribute Ixx : Real = 1.4181757016777667;
                                attribute 'σ_Ixx' : Real = 0.37074144170588635;
                                attribute Iyy : Real = 1.304351102648269;
                                attribute 'σ_Iyy' : Real = 0.3723953238821935;
                                attribute Izz : Real = 1.3441982823391134;
                                attribute 'σ_Izz' : Real = 0.37017423652493897;
                                attribute Ixy : Real = 0.027490749776944545;
                                attribute 'σ_Ixy' : Real = 0.02351283871158888;
                                attribute Ixz : Real = -0.07202193601768515;
                                attribute 'σ_Ixz' : Real = 0.022566176940390956;
                                attribute Iyz : Real = -0.03568700747841831;
                                attribute 'σ_Iyz' : Real = 0.02209918015384651;
                            }
                            part <'C.1.1.2.1.5.5.5'> 'Part 152' {
                                attribute POIconv : String = "-";
                                attribute Ipoint : Boolean = false;
                                attribute mass : Real = 0.6024173960543703;
                                attribute 'σ_mass' : Real = 0.28909372274994966;
                                attribute Cx : Real = -56.167668756097555;
                                attribute 'σ_Cx' : Real = 28.721044428837228;
                                attribute Cy : Real = -81.73653865233064;
                                attribute 'σ_Cy' : Real = 28.23690002309109;
                                attribute Cz : Real = 65.05627376027405;
                                attribute 'σ_Cz' : Real = 29.057750463592832;
                                attribute Ixx : Real = 0.7724924516764912;
                                attribute 'σ_Ixx' : Real = 0.37074144170588635;
                                attribute Iyy : Real = 0.8379278897473506;
                                attribute 'σ_Iyy' : Real = 0.3723953238821935;
                                attribute Izz : Real = 0.7378951037295188;
                                attribute 'σ_Izz' : Real = 0.37017423652493897;
                                attribute Ixy : Real = 0.032745472532650435;
                                attribute 'σ_Ixy' : Real = 0.02351283871158888;
                                attribute Ixz : Real = -0.021583451067481694;
                                attribute 'σ_Ixz' : Real = 0.022566176940390956;
                                attribute Iyz : Real = -0.01001994014271302;
                                attribute 'σ_Iyz' : Real = 0.02209918015384651;
                            }
                        }
                    }
                }
                part <'C.1.1.2.2'> 'Subsystem 4' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.2.2.1'> 'Assembly 12' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.2.1.1'> 'Subassembly 44' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.2.1.1.1'> 'Part 153' {
                                attribute POIconv : String = "-";
                                attribute Ipoint : Boolean = false;
                                attribute mass : Real = 0.855321117463056;
                                attribute 'σ_mass' : Real = 0.28909372274994966;
                                attribute Cx : Real = 4.351499816402793;
                                attribute 'σ_Cx' : Real = 28.721044428837228;
                                attribute Cy : Real = -21.02312254719436;
                                attribute 'σ_Cy' : Real = 28.23690002309109;
                                attribute Cz : Real = 6.591932894662023;
                                attribute 'σ_Cz' : Real = 29.057750463592832;
                                attribute Ixx : Real = 1.011890819436567;
                                attribute 'σ_Ixx' : Real = 0.37074144170588635;
                                attribute Iyy : Real = 1.1037062744217299;
                                attribute 'σ_Iyy' : Real = 0.3723953238821935;
                                attribute Izz : Real = 1.0899136050558529;
                                attribute 'σ_Izz' : Real = 0.37017423652493897;
                                attribute Ixy : Real = 0.03067171311202662;
                                attribute 'σ_Ixy' : Real = 0.02351283871158888;
                                attribute Ixz : Real = 0.02717709442391499;
                                attribute 'σ_Ixz' : Real = 0.022566176940390956;
                                attribute Iyz : Real = 0.01112129199620427;
                                attribute 'σ_Iyz' : Real = 0.02209918015384651;
                            }
                            part <'C.1.1.2.2.1.1.2'> 'Part 154' {
                                attribute POIconv : String = "+";
                                attribute Ipoint : Boolean = false;
                                attribute mass : Real = 0.08018356888229028;
                                attribute 'σ_mass' : Real = 0.28909372274994966;
                                attribute Cx : Real = 55.72422328405082;
                                attribute 'σ_Cx' : Real = 28.721044428837228;
                                attribute Cy : Real = -63.476700987666845;
                                attribute 'σ_Cy' : Real = 28.23690002309109;
                                attribute Cz : Real = 21.198144974187016;
                                attribute 'σ_Cz' : Real = 29.057750463592832;
                                attribute Ixx : Real = 0.09829198843261945;
                                attribute 'σ_Ixx' : Real = 0.37074144170588635;
                                attribute Iyy : Real = 0.09654515079313099;
                                attribute 'σ_Iyy' : Real = 0.3723953238821935;
                                attribute Izz : Real = 0.0966067730546954;
                                attribute 'σ_Izz' : Real = 0.37017423652493897;
                                attribute Ixy : Real = 9.798259919753046e-4;
                                attribute 'σ_Ixy' : Real = 0.02351283871158888;
                                attribute Ixz : Real = 2.4115810899414248e-4;
                                attribute 'σ_Ixz' : Real = 0.022566176940390956;
                                attribute Iyz : Real = 7.37659657377281e-5;
                                attribute 'σ_Iyz' : Real = 0.02209918015384651;
                            }
                            part <'C.1.1.2.2.1.1.3'> 'Part 155' {
                                attribute POIconv : String = "+";
                                attribute Ipoint : Boolean = false;
                                attribute mass : Real = 0.3022511094980873;
                                attribute 'σ_mass' : Real = 0.28909372274994966;
                                attribute Cx : Real = 75.32320339232683;
                                attribute 'σ_Cx' : Real = 28.721044428837228;
                                attribute Cy : Real = 81.75194882787764;
                                attribute 'σ_Cy' : Real = 28.23690002309109;
                                attribute Cz : Real = 27.09015137515962;
                                attribute 'σ_Cz' : Real = 29.057750463592832;
                                attribute Ixx : Real = 0.33478560117777884;
                                attribute 'σ_Ixx' : Real = 0.37074144170588635;
                                attribute Iyy : Real = 0.3329397819957529;
                                attribute 'σ_Iyy' : Real = 0.3723953238821935;
                                attribute Izz : Real = 0.3270648789313383;
                                attribute 'σ_Izz' : Real = 0.37017423652493897;
                                attribute Ixy : Real = 0.01622390100726502;
                                attribute 'σ_Ixy' : Real = 0.02351283871158888;
                                attribute Ixz : Real = -0.015992914831490568;
                                attribute 'σ_Ixz' : Real = 0.022566176940390956;
                                attribute Iyz : Real = -0.01936987097497332;
                                attribute 'σ_Iyz' : Real = 0.02209918015384651;
                            }
                            part <'C.1.1.2.2.1.1.4'> 'Part 156' {
                                attribute POIconv : String = "+";
                                attribute Ipoint : Boolean = false;
                                attribute mass : Real = 0.6322654617959633;
                                attribute 'σ_mass' : Real = 0.28909372274994966;
                                attribute Cx : Real = 7.3610767256468534;
                                attribute 'σ_Cx' : Real = 28.721044428837228;
                                attribute Cy : Real = 41.338973538950086;
                                attribute 'σ_Cy' : Real = 28.23690002309109;
                                attribute Cz : Real = 63.55626191943884;
                                attribute 'σ_Cz' : Real = 29.057750463592832;
                                attribute Ixx : Real = 0.9551482203657099;
                                attribute 'σ_Ixx' : Real = 0.37074144170588635;
                                attribute Iyy : Real = 0.9194819283207218;
                                attribute 'σ_Iyy' : Real = 0.3723953238821935;
                                attribute Izz : Real = 0.8733881917209926;
                                attribute 'σ_Izz' : Real = 0.37017423652493897;
                                attribute Ixy : Real = 0.04531404116053733;
                                attribute 'σ_Ixy' : Real = 0.02351283871158888;
                                attribute Ixz : Real = 0.004886040855269214;
                                attribute 'σ_Ixz' : Real = 0.022566176940390956;
                                attribute Iyz : Real = -0.029527678514451056;
                                attribute 'σ_Iyz' : Real = 0.02209918015384651;
                            }
                        }
                        part <'C.1.1.2.2.1.2'> 'Subassembly 45' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.2.1.2.1'> 'Part 157' {
                                attribute POIconv : String = "+";
                                attribute Ipoint : Boolean = false;
                                attribute mass : Real = 0.6295002899167593;
                                attribute 'σ_mass' : Real = 0.28909372274994966;
                                attribute Cx : Real = -25.61848503537476;
                                attribute 'σ_Cx' : Real = 28.721044428837228;
                                attribute Cy : Real = -57.095806021243334;
                                attribute 'σ_Cy' : Real = 28.23690002309109;
                                attribute Cz : Real = -84.21276365406811;
                                attribute 'σ_Cz' : Real = 29.057750463592832;
                                attribute Ixx : Real = 0.6434653361214111;
                                attribute 'σ_Ixx' : Real = 0.37074144170588635;
                                attribute Iyy : Real = 0.6757857073193699;
                                attribute 'σ_Iyy' : Real = 0.3723953238821935;
                                attribute Izz : Real = 0.7229691868410921;
                                attribute 'σ_Izz' : Real = 0.37017423652493897;
                                attribute Ixy : Real = 0.006136141931393743;
                                attribute 'σ_Ixy' : Real = 0.02351283871158888;
                                attribute Ixz : Real = -0.0016994229790750132;
                                attribute 'σ_Ixz' : Real = 0.022566176940390956;
                                attribute Iyz : Real = -0.0033163206767449814;
                                attribute 'σ_Iyz' : Real = 0.02209918015384651;
                            }
                            part <'C.1.1.2.2.1.2.2'> 'Part 158' {
                                attribute POIconv : String = "-";
                                attribute Ipoint : Boolean = false;
                                attribute mass : Real = 0.7332497966079973;
                                attribute 'σ_mass' : Real = 0.28909372274994966;
                                attribute Cx : Real = 77.08858493715525;
                                attribute 'σ_Cx' : Real = 28.721044428837228;
                                attribute Cy : Real = -36.88400159589946;
                                attribute 'σ_Cy' : Real = 28.23690002309109;
                                attribute Cz : Real = 91.61950079724193;
                                attribute 'σ_Cz' : Real = 29.057750463592832;
                                attribute Ixx : Real = 0.9606364971161523;
                                attribute 'σ_Ixx' : Real = 0.37074144170588635;
                                attribute Iyy : Real = 0.9855901543380022;
                                attribute 'σ_Iyy' : Real = 0.3723953238821935;
                                attribute Izz : Real = 0.9440147050071717;
                                attribute 'σ_Izz' : Real = 0.37017423652493897;
                                attribute Ixy : Real = -0.028827491222627472;
                                attribute 'σ_Ixy' : Real = 0.02351283871158888;
                                attribute Ixz : Real = 0.03276269160907726;
                                attribute 'σ_Ixz' : Real = 0.022566176940390956;
                                attribute Iyz : Real = 0.03920061223880837;
                                attribute 'σ_Iyz' : Real = 0.02209918015384651;
                            }
                            part <'C.1.1.2.2.1.2.3'> 'Part 159' {
                                attribute POIconv : String = "+";
                                attribute Ipoint : Boolean = false;
                                attribute mass : Real = 0.3508497709115036;
                                attribute 'σ_mass' : Real = 0.28909372274994966;
                                attribute Cx : Real = -91.8515557423234;
                                attribute 'σ_Cx' : Real = 28.721044428837228;
                                attribute Cy : Real = 45.420784410089254;
                                attribute 'σ_Cy' : Real = 28.23690002309109;
                                attribute Cz : Real = 94.70796925015748;
                                attribute 'σ_Cz' : Real = 29.057750463592832;
                                attribute Ixx : Real = 0.4205162186672067;
                                attribute 'σ_Ixx' : Real = 0.37074144170588635;
                                attribute Iyy : Real = 0.5004571198168236;
                                attribute 'σ_Iyy' : Real = 0.3723953238821935;
                                attribute Izz : Real = 0.43971269939499696;
                                attribute 'σ_Izz' : Real = 0.37017423652493897;
                                attribute Ixy : Real = -0.007283636028104069;
                                attribute 'σ_Ixy' : Real = 0.02351283871158888;
                                attribute Ixz : Real = -0.018455258131757347;
                                attribute 'σ_Ixz' : Real = 0.022566176940390956;
                                attribute Iyz : Real = -0.03375045589190957;
                                attribute 'σ_Iyz' : Real = 0.02209918015384651;
                            }
                            part <'C.1.1.2.2.1.2.4'> 'Part 160' {
                                attribute POIconv : String = "+";
                                attribute Ipoint : Boolean = false;
                                attribute mass : Real = 0.1311549131362699;
                                attribute 'σ_mass' : Real = 0.28909372274994966;
                                attribute Cx : Real = -99.81856071390212;
                                attribute 'σ_Cx' : Real = 28.721044428837228;
                                attribute Cy : Real = 36.38377725146711;
                                attribute 'σ_Cy' : Real = 28.23690002309109;
                                attribute Cz : Real = 23.7374025862664;
                                attribute 'σ_Cz' : Real = 29.057750463592832;
                                attribute Ixx : Real = 0.14938146417337916;
                                attribute 'σ_Ixx' : Real = 0.37074144170588635;
                                attribute Iyy : Real = 0.15153397534380042;
                                attribute 'σ_Iyy' : Real = 0.3723953238821935;
                                attribute Izz : Real = 0.154632344761327;
                                attribute 'σ_Izz' : Real = 0.37017423652493897;
                                attribute Ixy : Real = -0.0027815909208092644;
                                attribute 'σ_Ixy' : Real = 0.02351283871158888;
                                attribute Ixz : Real = -0.002273090261887583;
                                attribute 'σ_Ixz' : Real = 0.022566176940390956;
                                attribute Iyz : Real = 6.452655050746567e-4;
                                attribute 'σ_Iyz' : Real = 0.02209918015384651;
                            }
                            part <'C.1.1.2.2.1.2.5'> 'Part 161' {
                                attribute POIconv : String = "-";
                                attribute Ipoint : Boolean = false;
                                attribute mass : Real = 0.24676580228842795;
                                attribute 'σ_mass' : Real = 0.28909372274994966;
                                attribute Cx : Real = 64.69208640046418;
                                attribute 'σ_Cx' : Real = 28.721044428837228;
                                attribute Cy : Real = -85.01289207488298;
                                attribute 'σ_Cy' : Real = 28.23690002309109;
                                attribute Cz : Real = 31.298457086086273;
                                attribute 'σ_Cz' : Real = 29.057750463592832;
                                attribute Ixx : Real = 0.31763448575623865;
                                attribute 'σ_Ixx' : Real = 0.37074144170588635;
                                attribute Iyy : Real = 0.26658696509313023;
                                attribute 'σ_Iyy' : Real = 0.3723953238821935;
                                attribute Izz : Real = 0.28184354054357186;
                                attribute 'σ_Izz' : Real = 0.37017423652493897;
                                attribute Ixy : Real = -0.025203932874431536;
                                attribute 'σ_Ixy' : Real = 0.02351283871158888;
                                attribute Ixz : Real = -6.307231815927926e-4;
                                attribute 'σ_Ixz' : Real = 0.022566176940390956;
                                attribute Iyz : Real = -7.151757905495217e-5;
                                attribute 'σ_Iyz' : Real = 0.02209918015384651;
                            }
                        }
                        part <'C.1.1.2.2.1.3'> 'Subassembly 46' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.2.1.3.1'> 'Part 162' {
                                attribute POIconv : String = "+";
                                attribute Ipoint : Boolean = false;
                                attribute mass : Real = 0.7893546829856932;
                                attribute 'σ_mass' : Real = 0.28909372274994966;
                                attribute Cx : Real = -67.3292264342308;
                                attribute 'σ_Cx' : Real = 28.721044428837228;
                                attribute Cy : Real = -73.68204486556351;
                                attribute 'σ_Cy' : Real = 28.23690002309109;
                                attribute Cz : Real = -38.91388191841543;
                                attribute 'σ_Cz' : Real = 29.057750463592832;
                                attribute Ixx : Real = 1.1290150077386103;
                                attribute 'σ_Ixx' : Real = 0.37074144170588635;
                                attribute Iyy : Real = 1.1553110575148235;
                                attribute 'σ_Iyy' : Real = 0.3723953238821935;
                                attribute Izz : Real = 1.1540887704207425;
                                attribute 'σ_Izz' : Real = 0.37017423652493897;
                                attribute Ixy : Real = 0.03496088578509725;
                                attribute 'σ_Ixy' : Real = 0.02351283871158888;
                                attribute Ixz : Real = -0.06512104541504529;
                                attribute 'σ_Ixz' : Real = 0.022566176940390956;
                                attribute Iyz : Real = 0.0332753571194644;
                                attribute 'σ_Iyz' : Real = 0.02209918015384651;
                            }
                            part <'C.1.1.2.2.1.3.2'> 'Part 163' {
                                attribute POIconv : String = "+";
                                attribute Ipoint : Boolean = false;
                                attribute mass : Real = 0.34623989950399847;
                                attribute 'σ_mass' : Real = 0.28909372274994966;
                                attribute Cx : Real = -43.06602762080729;
                                attribute 'σ_Cx' : Real = 28.721044428837228;
                                attribute Cy : Real = 1.5229502692818642;
                                attribute 'σ_Cy' : Real = 28.23690002309109;
                                attribute Cz : Real = 96.34249876253307;
                                attribute 'σ_Cz' : Real = 29.057750463592832;
                                attribute Ixx : Real = 0.44940755420150236;
                                attribute 'σ_Ixx' : Real = 0.37074144170588635;
                                attribute Iyy : Real = 0.4369300211826027;
                                attribute 'σ_Iyy' : Real = 0.3723953238821935;
                                attribute Izz : Real = 0.46562037221866565;
                                attribute 'σ_Izz' : Real = 0.37017423652493897;
                                attribute Ixy : Real = -0.00170280583917383;
                                attribute 'σ_Ixy' : Real = 0.02351283871158888;
                                attribute Ixz : Real = 0.02977670813782962;
                                attribute 'σ_Ixz' : Real = 0.022566176940390956;
                                attribute Iyz : Real = 0.044653474482573605;
                                attribute 'σ_Iyz' : Real = 0.02209918015384651;
                            }
                            part <'C.1.1.2.2.1.3.3'> 'Part 164' {
                                attribute POIconv : String = "+";
                                attribute Ipoint : Boolean = false;
                                attribute mass : Real = 0.6073562870700844;
                                attribute 'σ_mass' : Real = 0.28909372274994966;
                                attribute Cx : Real = -12.623134488239884;
                                attribute 'σ_Cx' : Real = 28.721044428837228;
                                attribute Cy : Real = 89.40444383770227;
                                attribute 'σ_Cy' : Real = 28.23690002309109;
                                attribute Cz : Real = -6.745311804115772;
                                attribute 'σ_Cz' : Real = 29.057750463592832;
                                attribute Ixx : Real = 0.7477489793465344;
                                attribute 'σ_Ixx' : Real = 0.37074144170588635;
                                attribute Iyy : Real = 0.7959935845449397;
                                attribute 'σ_Iyy' : Real = 0.3723953238821935;
                                attribute Izz : Real = 0.78254186501959;
                                attribute 'σ_Izz' : Real = 0.37017423652493897;
                                attribute Ixy : Real = -0.03885328169766915;
                                attribute 'σ_Ixy' : Real = 0.02351283871158888;
                                attribute Ixz : Real = -0.0012848464781238028;
                                attribute 'σ_Ixz' : Real = 0.022566176940390956;
                                attribute Iyz : Real = -0.041375048005681744;
                                attribute 'σ_Iyz' : Real = 0.02209918015384651;
                            }
                        }
                        part <'C.1.1.2.2.1.4'> 'Subassembly 47' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.2.1.4.1'> 'Part 165' {
                                attribute POIconv : String = "+";
                                attribute Ipoint : Boolean = false;
                                attribute mass : Real = 0.3922002762623597;
                                attribute 'σ_mass' : Real = 0.28909372274994966;
                                attribute Cx : Real = 41.76503103226423;
                                attribute 'σ_Cx' : Real = 28.721044428837228;
                                attribute Cy : Real = 16.801129328086972;
                                attribute 'σ_Cy' : Real = 28.23690002309109;
                                attribute Cz : Real = -31.626209104433656;
                                attribute 'σ_Cz' : Real = 29.057750463592832;
                                attribute Ixx : Real = 0.48126984569039655;
                                attribute 'σ_Ixx' : Real = 0.37074144170588635;
                                attribute Iyy : Real = 0.5040004115610209;
                                attribute 'σ_Iyy' : Real = 0.3723953238821935;
                                attribute Izz : Real = 0.49089795328071667;
                                attribute 'σ_Izz' : Real = 0.37017423652493897;
                                attribute Ixy : Real = -0.048019304466833994;
                                attribute 'σ_Ixy' : Real = 0.02351283871158888;
                                attribute Ixz : Real = -0.003057873010357374;
                                attribute 'σ_Ixz' : Real = 0.022566176940390956;
                                attribute Iyz : Real = 0.03230530719502631;
                                attribute 'σ_Iyz' : Real = 0.02209918015384651;
                            }
                            part <'C.1.1.2.2.1.4.2'> 'Part 166' {
                                attribute POIconv : String = "+";
                                attribute Ipoint : Boolean = false;
                                attribute mass : Real = 0.36562424327223564;
                                attribute 'σ_mass' : Real = 0.28909372274994966;
                                attribute Cx : Real = 5.3220359608531;
                                attribute 'σ_Cx' : Real = 28.721044428837228;
                                attribute Cy : Real = -41.46459153853357;
                                attribute 'σ_Cy' : Real = 28.23690002309109;
                                attribute Cz : Real = 65.6319173052907;
                                attribute 'σ_Cz' : Real = 29.057750463592832;
                                attribute Ixx : Real = 0.5162617026691243;
                                attribute 'σ_Ixx' : Real = 0.37074144170588635;
                                attribute Iyy : Real = 0.4954593465074545;
                                attribute 'σ_Iyy' : Real = 0.3723953238821935;
                                attribute Izz : Real = 0.5326384598125916;
                                attribute 'σ_Izz' : Real = 0.37017423652493897;
                                attribute Ixy : Real = 0.030207636725343538;
                                attribute 'σ_Ixy' : Real = 0.02351283871158888;
                                attribute Ixz : Real = 0.02205165776763099;
                                attribute 'σ_Ixz' : Real = 0.022566176940390956;
                                attribute Iyz : Real = -0.03535328358763729;
                                attribute 'σ_Iyz' : Real = 0.02209918015384651;
                            }
                            part <'C.1.1.2.2.1.4.3'> 'Part 167' {
                                attribute POIconv : String = "-";
                                attribute Ipoint : Boolean = false;
                                attribute mass : Real = 0.19489581103413367;
                                attribute 'σ_mass' : Real = 0.28909372274994966;
                                attribute Cx : Real = -73.25983932241797;
                                attribute 'σ_Cx' : Real = 28.721044428837228;
                                attribute Cy : Real = -26.92969162017107;
                                attribute 'σ_Cy' : Real = 28.23690002309109;
                                attribute Cz : Real = -48.997609969228506;
                                attribute 'σ_Cz' : Real = 29.057750463592832;
                                attribute Ixx : Real = 0.2217614715819434;
                                attribute 'σ_Ixx' : Real = 0.37074144170588635;
                                attribute Iyy : Real = 0.24654102146115023;
                                attribute 'σ_Iyy' : Real = 0.3723953238821935;
                                attribute Izz : Real = 0.23082892828115417;
                                attribute 'σ_Izz' : Real = 0.37017423652493897;
                                attribute Ixy : Real = -0.02575661379570556;
                                attribute 'σ_Ixy' : Real = 0.02351283871158888;
                                attribute Ixz : Real = -7.370291618240341e-4;
                                attribute 'σ_Ixz' : Real = 0.022566176940390956;
                                attribute Iyz : Real = -0.003283593917601211;
                                attribute 'σ_Iyz' : Real = 0.02209918015384651;
                            }
                            part <'C.1.1.2.2.1.4.4'> 'Part 168' {
                                attribute POIconv : String = "+";
                                attribute Ipoint : Boolean = false;
                                attribute mass : Real = 0.28059754030313344;
                                attribute 'σ_mass' : Real = 0.28909372274994966;
                                attribute Cx : Real = -43.049339298158884;
                                attribute 'σ_Cx' : Real = 28.721044428837228;
                                attribute Cy : Real = 26.16354515776038;
                                attribute 'σ_Cy' : Real = 28.23690002309109;
                                attribute Cz : Real = 93.12769616954029;
                                attribute 'σ_Cz' : Real = 29.057750463592832;
                                attribute Ixx : Real = 0.308688770596357;
                                attribute 'σ_Ixx' : Real = 0.37074144170588635;
                                attribute Iyy : Real = 0.30325470210694705;
                                attribute 'σ_Iyy' : Real = 0.3723953238821935;
                                attribute Izz : Real = 0.3512915592998523;
                                attribute 'σ_Izz' : Real = 0.37017423652493897;
                                attribute Ixy : Real = 1.2055425453756205e-4;
                                attribute 'σ_Ixy' : Real = 0.02351283871158888;
                                attribute Ixz : Real = 0.018464009269710403;
                                attribute 'σ_Ixz' : Real = 0.022566176940390956;
                                attribute Iyz : Real = 0.01283015502173616;
                                attribute 'σ_Iyz' : Real = 0.02209918015384651;
                            }
                            part <'C.1.1.2.2.1.4.5'> 'Part 169' {
                                attribute POIconv : String = "+";
                                attribute Ipoint : Boolean = false;
                                attribute mass : Real = 0.510693000448402;
                                attribute 'σ_mass' : Real = 0.28909372274994966;
                                attribute Cx : Real = 81.95249321870506;
                                attribute 'σ_Cx' : Real = 28.721044428837228;
                                attribute Cy : Real = 68.96228790283203;
                                attribute 'σ_Cy' : Real = 28.23690002309109;
                                attribute Cz : Real = -14.606244023889303;
                                attribute 'σ_Cz' : Real = 29.057750463592832;
                                attribute Ixx : Real = 0.5349014972267188;
                                attribute 'σ_Ixx' : Real = 0.37074144170588635;
                                attribute Iyy : Real = 0.524934917587324;
                                attribute 'σ_Iyy' : Real = 0.3723953238821935;
                                attribute Izz : Real = 0.5736673343665503;
                                attribute 'σ_Izz' : Real = 0.37017423652493897;
                                attribute Ixy : Real = -0.04917564918169298;
                                attribute 'σ_Ixy' : Real = 0.02351283871158888;
                                attribute Ixz : Real = -0.024640099051106902;
                                attribute 'σ_Ixz' : Real = 0.022566176940390956;
                                attribute Iyz : Real = 0.011977660643177224;
                                attribute 'σ_Iyz' : Real = 0.02209918015384651;
                            }
                        }
                    }
                    part <'C.1.1.2.2.2'> 'Assembly 13' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.2.2.1'> 'Subassembly 48' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.2.2.1.1'> 'Part 170' {
                                attribute POIconv : String = "+";
                                attribute Ipoint : Boolean = false;
                                attribute mass : Real = 0.6996860573282465;
                                attribute 'σ_mass' : Real = 0.28909372274994966;
                                attribute Cx : Real = -1.7720005940645933;
                                attribute 'σ_Cx' : Real = 28.721044428837228;
                                attribute Cy : Real = -67.52090468071401;
                                attribute 'σ_Cy' : Real = 28.23690002309109;
                                attribute Cz : Real = 16.659361915662885;
                                attribute 'σ_Cz' : Real = 29.057750463592832;
                                attribute Ixx : Real = 0.7565597034536904;
                                attribute 'σ_Ixx' : Real = 0.37074144170588635;
                                attribute Iyy : Real = 0.7140389968962108;
                                attribute 'σ_Iyy' : Real = 0.3723953238821935;
                                attribute Izz : Real = 0.7799959383165427;
                                attribute 'σ_Izz' : Real = 0.37017423652493897;
                                attribute Ixy : Real = -0.041547433095870986;
                                attribute 'σ_Ixy' : Real = 0.02351283871158888;
                                attribute Ixz : Real = -0.01745733488467227;
                                attribute 'σ_Ixz' : Real = 0.022566176940390956;
                                attribute Iyz : Real = -0.04193598402791303;
                                attribute 'σ_Iyz' : Real = 0.02209918015384651;
                            }
                            part <'C.1.1.2.2.2.1.2'> 'Part 171' {
                                attribute POIconv : String = "-";
                                attribute Ipoint : Boolean = false;
                                attribute mass : Real = 0.6787785719020758;
                                attribute 'σ_mass' : Real = 0.28909372274994966;
                                attribute Cx : Real = -65.46351229771972;
                                attribute 'σ_Cx' : Real = 28.721044428837228;
                                attribute Cy : Real = 62.76944437995553;
                                attribute 'σ_Cy' : Real = 28.23690002309109;
                                attribute Cz : Real = -18.304060399532318;
                                attribute 'σ_Cz' : Real = 29.057750463592832;
                                attribute Ixx : Real = 0.7822071559843139;
                                attribute 'σ_Ixx' : Real = 0.37074144170588635;
                                attribute Iyy : Real = 0.7778822248011155;
                                attribute 'σ_Iyy' : Real = 0.3723953238821935;
                                attribute Izz : Real = 0.978182922344661;
                                attribute 'σ_Izz' : Real = 0.37017423652493897;
                                attribute Ixy : Real = 0.014097647102195519;
                                attribute 'σ_Ixy' : Real = 0.02351283871158888;
                                attribute Ixz : Real = -0.01694636423436308;
                                attribute 'σ_Ixz' : Real = 0.022566176940390956;
                                attribute Iyz : Real = 0.01500608161680842;
                                attribute 'σ_Iyz' : Real = 0.02209918015384651;
                            }
                        }
                        part <'C.1.1.2.2.2.2'> 'Subassembly 49' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.2.2.2.1'> 'Part 172' {
                                attribute POIconv : String = "+";
                                attribute Ipoint : Boolean = false;
                                attribute mass : Real = 0.4198192962212488;
                                attribute 'σ_mass' : Real = 0.28909372274994966;
                                attribute Cx : Real = -37.14067074470222;
                                attribute 'σ_Cx' : Real = 28.721044428837228;
                                attribute Cy : Real = 14.053925639018416;
                                attribute 'σ_Cy' : Real = 28.23690002309109;
                                attribute Cz : Real = -85.41102516464889;
                                attribute 'σ_Cz' : Real = 29.057750463592832;
                                attribute Ixx : Real = 0.4565478244430911;
                                attribute 'σ_Ixx' : Real = 0.37074144170588635;
                                attribute Iyy : Real = 0.43155697305090707;
                                attribute 'σ_Iyy' : Real = 0.3723953238821935;
                                attribute Izz : Real = 0.44063510654598226;
                                attribute 'σ_Izz' : Real = 0.37017423652493897;
                                attribute Ixy : Real = -0.01574009883870208;
                                attribute 'σ_Ixy' : Real = 0.02351283871158888;
                                attribute Ixz : Real = -0.02596286629234972;
                                attribute 'σ_Ixz' : Real = 0.022566176940390956;
                                attribute Iyz : Real = -0.005362394374839528;
                                attribute 'σ_Iyz' : Real = 0.02209918015384651;
                            }
                            part <'C.1.1.2.2.2.2.2'> 'Part 173' {
                                attribute POIconv : String = "+";
                                attribute Ipoint : Boolean = false;
                                attribute mass : Real = 0.7348289012997411;
                                attribute 'σ_mass' : Real = 0.28909372274994966;
                                attribute Cx : Real = -10.253697354346514;
                                attribute 'σ_Cx' : Real = 28.721044428837228;
                                attribute Cy : Real = 62.32720548287034;
                                attribute 'σ_Cy' : Real = 28.23690002309109;
                                attribute Cz : Real = 63.26927565969527;
                                attribute 'σ_Cz' : Real = 29.057750463592832;
                                attribute Ixx : Real = 0.9086654377186083;
                                attribute 'σ_Ixx' : Real = 0.37074144170588635;
                                attribute Iyy : Real = 0.817470985763932;
                                attribute 'σ_Iyy' : Real = 0.3723953238821935;
                                attribute Izz : Real = 0.9042395640767662;
                                attribute 'σ_Izz' : Real = 0.37017423652493897;
                                attribute Ixy : Real = 0.04881666259776883;
                                attribute 'σ_Ixy' : Real = 0.02351283871158888;
                                attribute Ixz : Real = -0.00671583145843677;
                                attribute 'σ_Ixz' : Real = 0.022566176940390956;
                                attribute Iyz : Real = -0.0737893775556489;
                                attribute 'σ_Iyz' : Real = 0.02209918015384651;
                            }
                            part <'C.1.1.2.2.2.2.3'> 'Part 174' {
                                attribute POIconv : String = "-";
                                attribute Ipoint : Boolean = false;
                                attribute mass : Real = 0.26073586418759076;
                                attribute 'σ_mass' : Real = 0.28909372274994966;
                                attribute Cx : Real = 34.56955854780972;
                                attribute 'σ_Cx' : Real = 28.721044428837228;
                                attribute Cy : Real = 72.76789420284331;
                                attribute 'σ_Cy' : Real = 28.23690002309109;
                                attribute Cz : Real = -52.1450235042721;
                                attribute 'σ_Cz' : Real = 29.057750463592832;
                                attribute Ixx : Real = 0.3281893917850688;
                                attribute 'σ_Ixx' : Real = 0.37074144170588635;
                                attribute Iyy : Real = 0.31658153701329195;
                                attribute 'σ_Iyy' : Real = 0.3723953238821935;
                                attribute Izz : Real = 0.35617066525768576;
                                attribute 'σ_Izz' : Real = 0.37017423652493897;
                                attribute Ixy : Real = 0.023748535612479228;
                                attribute 'σ_Ixy' : Real = 0.02351283871158888;
                                attribute Ixz : Real = 0.008651694245284846;
                                attribute 'σ_Ixz' : Real = 0.022566176940390956;
                                attribute Iyz : Real = -0.0021481332233297193;
                                attribute 'σ_Iyz' : Real = 0.02209918015384651;
                            }
                        }
                    }
                    part <'C.1.1.2.2.3'> 'Assembly 14' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.2.3.1'> 'Subassembly 50' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.2.3.1.1'> 'Part 175' {
                                attribute POIconv : String = "+";
                                attribute Ipoint : Boolean = false;
                                attribute mass : Real = 0.3818557383387815;
                                attribute 'σ_mass' : Real = 0.28909372274994966;
                                attribute Cx : Real = 78.52229713462293;
                                attribute 'σ_Cx' : Real = 28.721044428837228;
                                attribute Cy : Real = 21.36943400837481;
                                attribute 'σ_Cy' : Real = 28.23690002309109;
                                attribute Cz : Real = -9.543733717873693;
                                attribute 'σ_Cz' : Real = 29.057750463592832;
                                attribute Ixx : Real = 0.5319513754691908;
                                attribute 'σ_Ixx' : Real = 0.37074144170588635;
                                attribute Iyy : Real = 0.5483133823325838;
                                attribute 'σ_Iyy' : Real = 0.3723953238821935;
                                attribute Izz : Real = 0.4872504616722236;
                                attribute 'σ_Izz' : Real = 0.37017423652493897;
                                attribute Ixy : Real = -0.008903521278638978;
                                attribute 'σ_Ixy' : Real = 0.02351283871158888;
                                attribute Ixz : Real = 0.018111536032810044;
                                attribute 'σ_Ixz' : Real = 0.022566176940390956;
                                attribute Iyz : Real = -0.008122788963804048;
                                attribute 'σ_Iyz' : Real = 0.02209918015384651;
                            }
                            part <'C.1.1.2.2.3.1.2'> 'Part 176' {
                                attribute POIconv : String = "-";
                                attribute Ipoint : Boolean = false;
                                attribute mass : Real = 0.34342165624699555;
                                attribute 'σ_mass' : Real = 0.28909372274994966;
                                attribute Cx : Real = 41.91951500251889;
                                attribute 'σ_Cx' : Real = 28.721044428837228;
                                attribute Cy : Real = 2.2042570635676384;
                                attribute 'σ_Cy' : Real = 28.23690002309109;
                                attribute Cz : Real = 22.982495417818427;
                                attribute 'σ_Cz' : Real = 29.057750463592832;
                                attribute Ixx : Real = 0.40729414914632167;
                                attribute 'σ_Ixx' : Real = 0.37074144170588635;
                                attribute Iyy : Real = 0.47263102522078565;
                                attribute 'σ_Iyy' : Real = 0.3723953238821935;
                                attribute Izz : Real = 0.47056312665341976;
                                attribute 'σ_Izz' : Real = 0.37017423652493897;
                                attribute Ixy : Real = -0.006881955584817899;
                                attribute 'σ_Ixy' : Real = 0.02351283871158888;
                                attribute Ixz : Real = -0.006839163063818052;
                                attribute 'σ_Ixz' : Real = 0.022566176940390956;
                                attribute Iyz : Real = -0.009270036525564025;
                                attribute 'σ_Iyz' : Real = 0.02209918015384651;
                            }
                            part <'C.1.1.2.2.3.1.3'> 'Part 177' {
                                attribute POIconv : String = "+";
                                attribute Ipoint : Boolean = false;
                                attribute mass : Real = 0.6777255211237352;
                                attribute 'σ_mass' : Real = 0.28909372274994966;
                                attribute Cx : Real = 83.33116816356778;
                                attribute 'σ_Cx' : Real = 28.721044428837228;
                                attribute Cy : Real = -21.35280929505825;
                                attribute 'σ_Cy' : Real = 28.23690002309109;
                                attribute Cz : Real = 15.441287821158767;
                                attribute 'σ_Cz' : Real = 29.057750463592832;
                                attribute Ixx : Real = 0.9386723776818713;
                                attribute 'σ_Ixx' : Real = 0.37074144170588635;
                                attribute Iyy : Real = 0.7963311692494339;
                                attribute 'σ_Iyy' : Real = 0.3723953238821935;
                                attribute Izz : Real = 0.7530448965205254;
                                attribute 'σ_Izz' : Real = 0.37017423652493897;
                                attribute Ixy : Real = -0.052695440524780354;
                                attribute 'σ_Ixy' : Real = 0.02351283871158888;
                                attribute Ixz : Real = 0.0012846230703561275;
                                attribute 'σ_Ixz' : Real = 0.022566176940390956;
                                attribute Iyz : Real = 0.05640080099556968;
                                attribute 'σ_Iyz' : Real = 0.02209918015384651;
                            }
                            part <'C.1.1.2.2.3.1.4'> 'Part 178' {
                                attribute POIconv : String = "-";
                                attribute Ipoint : Boolean = false;
                                attribute mass : Real = 0.38699206047155893;
                                attribute 'σ_mass' : Real = 0.28909372274994966;
                                attribute Cx : Real = -26.587445428594947;
                                attribute 'σ_Cx' : Real = 28.721044428837228;
                                attribute Cy : Real = -33.18620836362243;
                                attribute 'σ_Cy' : Real = 28.23690002309109;
                                attribute Cz : Real = -60.725729214027524;
                                attribute 'σ_Cz' : Real = 29.057750463592832;
                                attribute Ixx : Real = 0.4727235236998924;
                                attribute 'σ_Ixx' : Real = 0.37074144170588635;
                                attribute Iyy : Real = 0.5222823067161467;
                                attribute 'σ_Iyy' : Real = 0.3723953238821935;
                                attribute Izz : Real = 0.48139932215659925;
                                attribute 'σ_Izz' : Real = 0.37017423652493897;
                                attribute Ixy : Real = 0.025724385298106316;
                                attribute 'σ_Ixy' : Real = 0.02351283871158888;
                                attribute Ixz : Real = -0.011550567601656537;
                                attribute 'σ_Ixz' : Real = 0.022566176940390956;
                                attribute Iyz : Real = -0.0023495446656244673;
                                attribute 'σ_Iyz' : Real = 0.02209918015384651;
                            }
                        }
                        part <'C.1.1.2.2.3.2'> 'Subassembly 51' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.2.3.2.1'> 'Part 179' {
                                attribute POIconv : String = "-";
                                attribute Ipoint : Boolean = false;
                                attribute mass : Real = 0.921826909518335;
                                attribute 'σ_mass' : Real = 0.28909372274994966;
                                attribute Cx : Real = -51.94877693429589;
                                attribute 'σ_Cx' : Real = 28.721044428837228;
                                attribute Cy : Real = -91.24262607656419;
                                attribute 'σ_Cy' : Real = 28.23690002309109;
                                attribute Cz : Real = 46.45874951966107;
                                attribute 'σ_Cz' : Real = 29.057750463592832;
                                attribute Ixx : Real = 1.1651781250013817;
                                attribute 'σ_Ixx' : Real = 0.37074144170588635;
                                attribute Iyy : Real = 1.26555224577138;
                                attribute 'σ_Iyy' : Real = 0.3723953238821935;
                                attribute Izz : Real = 1.0835543969554178;
                                attribute 'σ_Izz' : Real = 0.37017423652493897;
                                attribute Ixy : Real = -0.015265954075495313;
                                attribute 'σ_Ixy' : Real = 0.02351283871158888;
                                attribute Ixz : Real = 0.09962482356939162;
                                attribute 'σ_Ixz' : Real = 0.022566176940390956;
                                attribute Iyz : Real = -0.07392358763382721;
                                attribute 'σ_Iyz' : Real = 0.02209918015384651;
                            }
                            part <'C.1.1.2.2.3.2.2'> 'Part 180' {
                                attribute POIconv : String = "+";
                                attribute Ipoint : Boolean = false;
                                attribute mass : Real = 0.8862786426742095;
                                attribute 'σ_mass' : Real = 0.28909372274994966;
                                attribute Cx : Real = 54.19662734493613;
                                attribute 'σ_Cx' : Real = 28.721044428837228;
                                attribute Cy : Real = -68.70926516130567;
                                attribute 'σ_Cy' : Real = 28.23690002309109;
                                attribute Cz : Real = -41.655086586251855;
                                attribute 'σ_Cz' : Real = 29.057750463592832;
                                attribute Ixx : Real = 1.0921190348871317;
                                attribute 'σ_Ixx' : Real = 0.37074144170588635;
                                attribute Iyy : Real = 1.1557262504995385;
                                attribute 'σ_Iyy' : Real = 0.3723953238821935;
                                attribute Izz : Real = 1.131124092215032;
                                attribute 'σ_Izz' : Real = 0.37017423652493897;
                                attribute Ixy : Real = 0.1221352198976941;
                                attribute 'σ_Ixy' : Real = 0.02351283871158888;
                                attribute Ixz : Real = -0.05467236166137991;
                                attribute 'σ_Ixz' : Real = 0.022566176940390956;
                                attribute Iyz : Real = -0.05448487207736866;
                                attribute 'σ_Iyz' : Real = 0.02209918015384651;
                            }
                            part <'C.1.1.2.2.3.2.3'> 'Part 181' {
                                attribute POIconv : String = "+";
                                attribute Ipoint : Boolean = false;
                                attribute mass : Real = 0.3094832809737418;
                                attribute 'σ_mass' : Real = 0.28909372274994966;
                                attribute Cx : Real = 65.61011811718345;
                                attribute 'σ_Cx' : Real = 28.721044428837228;
                                attribute Cy : Real = -31.50172927416861;
                                attribute 'σ_Cy' : Real = 28.23690002309109;
                                attribute Cz : Real = 38.402926130220294;
                                attribute 'σ_Cz' : Real = 29.057750463592832;
                                attribute Ixx : Real = 0.4233542535556114;
                                attribute 'σ_Ixx' : Real = 0.37074144170588635;
                                attribute Iyy : Real = 0.43254369374762774;
                                attribute 'σ_Iyy' : Real = 0.3723953238821935;
                                attribute Izz : Real = 0.3669955389625493;
                                attribute 'σ_Izz' : Real = 0.37017423652493897;
                                attribute Ixy : Real = 0.008415277523069996;
                                attribute 'σ_Ixy' : Real = 0.02351283871158888;
                                attribute Ixz : Real = 0.014774548870305677;
                                attribute 'σ_Ixz' : Real = 0.022566176940390956;
                                attribute Iyz : Real = -0.010480292298601068;
                                attribute 'σ_Iyz' : Real = 0.02209918015384651;
                            }
                            part <'C.1.1.2.2.3.2.4'> 'Part 182' {
                                attribute POIconv : String = "+";
                                attribute Ipoint : Boolean = false;
                                attribute mass : Real = 0.22355187601805665;
                                attribute 'σ_mass' : Real = 0.28909372274994966;
                                attribute Cx : Real = -42.93162287212908;
                                attribute 'σ_Cx' : Real = 28.721044428837228;
                                attribute Cy : Real = -96.18664039298892;
                                attribute 'σ_Cy' : Real = 28.23690002309109;
                                attribute Cz : Real = -82.45789795182645;
                                attribute 'σ_Cz' : Real = 29.057750463592832;
                                attribute Ixx : Real = 0.3079912211934493;
                                attribute 'σ_Ixx' : Real = 0.37074144170588635;
                                attribute Iyy : Real = 0.35107218112298116;
                                attribute 'σ_Iyy' : Real = 0.3723953238821935;
                                attribute Izz : Real = 0.3078917453193108;
                                attribute 'σ_Izz' : Real = 0.37017423652493897;
                                attribute Ixy : Real = -0.02019461563142872;
                                attribute 'σ_Ixy' : Real = 0.02351283871158888;
                                attribute Ixz : Real = 0.005513813084381957;
                                attribute 'σ_Ixz' : Real = 0.022566176940390956;
                                attribute Iyz : Real = 0.006168232857509408;
                                attribute 'σ_Iyz' : Real = 0.02209918015384651;
                            }
                            part <'C.1.1.2.2.3.2.5'> 'Part 183' {
                                attribute POIconv : String = "+";
                                attribute Ipoint : Boolean = false;
                                attribute mass : Real = 0.9242441020437981;
                                attribute 'σ_mass' : Real = 0.28909372274994966;
                                attribute Cx : Real = -5.231239879503846;
                                attribute 'σ_Cx' : Real = 28.721044428837228;
                                attribute Cy : Real = -64.01164601556957;
                                attribute 'σ_Cy' : Real = 28.23690002309109;
                                attribute Cz : Real = 3.6815470084547997;
                                attribute 'σ_Cz' : Real = 29.057750463592832;
                                attribute Ixx : Real = 1.0950805614993238;
                                attribute 'σ_Ixx' : Real = 0.37074144170588635;
                                attribute Iyy : Real = 1.1707770162630593;
                                attribute 'σ_Iyy' : Real = 0.3723953238821935;
                                attribute Izz : Real = 1.0120576525062939;
                                attribute 'σ_Izz' : Real = 0.37017423652493897;
                                attribute Ixy : Real = -0.010934337522805072;
                                attribute 'σ_Ixy' : Real = 0.02351283871158888;
                                attribute Ixz : Real = -0.08165481635000502;
                                attribute 'σ_Ixz' : Real = 0.022566176940390956;
                                attribute Iyz : Real = 0.0296555379743003;
                                attribute 'σ_Iyz' : Real = 0.02209918015384651;
                            }
                        }
                        part <'C.1.1.2.2.3.3'> 'Subassembly 52' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.2.3.3.1'> 'Part 184' {
                                attribute POIconv : String = "-";
                                attribute Ipoint : Boolean = false;
                                attribute mass : Real = 0.04803869580011815;
                                attribute 'σ_mass' : Real = 0.28909372274994966;
                                attribute Cx : Real = 66.72488856129348;
                                attribute 'σ_Cx' : Real = 28.721044428837228;
                                attribute Cy : Real = -10.92528160661459;
                                attribute 'σ_Cy' : Real = 28.23690002309109;
                                attribute Cz : Real = -51.6026321798563;
                                attribute 'σ_Cz' : Real = 29.057750463592832;
                                attribute Ixx : Real = 0.06142990296864371;
                                attribute 'σ_Ixx' : Real = 0.37074144170588635;
                                attribute Iyy : Real = 0.06211455597531635;
                                attribute 'σ_Iyy' : Real = 0.3723953238821935;
                                attribute Izz : Real = 0.066987543236277175;
                                attribute 'σ_Izz' : Real = 0.37017423652493897;
                                attribute Ixy : Real = -0.0033889768570873873;
                                attribute 'σ_Ixy' : Real = 0.02351283871158888;
                                attribute Ixz : Real = 1.2456251773068552e-4;
                                attribute 'σ_Ixz' : Real = 0.022566176940390956;
                                attribute Iyz : Real = 0.002252160035002961;
                                attribute 'σ_Iyz' : Real = 0.02209918015384651;
                            }
                            part <'C.1.1.2.2.3.3.2'> 'Part 185' {
                                attribute POIconv : String = "-";
                                attribute Ipoint : Boolean = false;
                                attribute mass : Real = 0.8562299040998332;
                                attribute 'σ_mass' : Real = 0.28909372274994966;
                                attribute Cx : Real = -50.343500170856714;
                                attribute 'σ_Cx' : Real = 28.721044428837228;
                                attribute Cy : Real = -33.38116309605539;
                                attribute 'σ_Cy' : Real = 28.23690002309109;
                                attribute Cz : Real = 80.38007272407413;
                                attribute 'σ_Cz' : Real = 29.057750463592832;
                                attribute Ixx : Real = 1.0210523919141257;
                                attribute 'σ_Ixx' : Real = 0.37074144170588635;
                                attribute Iyy : Real = 1.0426604759076454;
                                attribute 'σ_Iyy' : Real = 0.3723953238821935;
                                attribute Izz : Real = 0.825067983737281;
                                attribute 'σ_Izz' : Real = 0.37017423652493897;
                                attribute Ixy : Real = 0.002357001642284754;
                                attribute 'σ_Ixy' : Real = 0.02351283871158888;
                                attribute Ixz : Real = -0.0052327181802938934;
                                attribute 'σ_Ixz' : Real = 0.022566176940390956;
                                attribute Iyz : Real = -0.0066476320400703625;
                                attribute 'σ_Iyz' : Real = 0.02209918015384651;
                            }
                        }
                        part <'C.1.1.2.2.3.4'> 'Subassembly 53' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.2.3.4.1'> 'Part 186' {
                                attribute POIconv : String = "-";
                                attribute Ipoint : Boolean = false;
                                attribute mass : Real = 0.3002359834588133;
                                attribute 'σ_mass' : Real = 0.28909372274994966;
                                attribute Cx : Real = 25.597803201526403;
                                attribute 'σ_Cx' : Real = 28.721044428837228;
                                attribute Cy : Real = 30.103622004389763;
                                attribute 'σ_Cy' : Real = 28.23690002309109;
                                attribute Cz : Real = -57.109012082219124;
                                attribute 'σ_Cz' : Real = 29.057750463592832;
                                attribute Ixx : Real = 0.36829728687696506;
                                attribute 'σ_Ixx' : Real = 0.37074144170588635;
                                attribute Iyy : Real = 0.42310058052205446;
                                attribute 'σ_Iyy' : Real = 0.3723953238821935;
                                attribute Izz : Real = 0.35415201145191993;
                                attribute 'σ_Izz' : Real = 0.37017423652493897;
                                attribute Ixy : Real = 0.03080669356825065;
                                attribute 'σ_Ixy' : Real = 0.02351283871158888;
                                attribute Ixz : Real = -0.011446127957038359;
                                attribute 'σ_Ixz' : Real = 0.022566176940390956;
                                attribute Iyz : Real = -0.009596556081073104;
                                attribute 'σ_Iyz' : Real = 0.02209918015384651;
                            }
                            part <'C.1.1.2.2.3.4.2'> 'Part 187' {
                                attribute POIconv : String = "+";
                                attribute Ipoint : Boolean = false;
                                attribute mass : Real = 0.3281037449145224;
                                attribute 'σ_mass' : Real = 0.28909372274994966;
                                attribute Cx : Real = -14.040295174345374;
                                attribute 'σ_Cx' : Real = 28.721044428837228;
                                attribute Cy : Real = 14.488649740815163;
                                attribute 'σ_Cy' : Real = 28.23690002309109;
                                attribute Cz : Real = -18.506762851029634;
                                attribute 'σ_Cz' : Real = 29.057750463592832;
                                attribute Ixx : Real = 0.4284691494171979;
                                attribute 'σ_Ixx' : Real = 0.37074144170588635;
                                attribute Iyy : Real = 0.41935830629330473;
                                attribute 'σ_Iyy' : Real = 0.3723953238821935;
                                attribute Izz : Real = 0.392214819135819;
                                attribute 'σ_Izz' : Real = 0.37017423652493897;
                                attribute Ixy : Real = 0.006701085850058464;
                                attribute 'σ_Ixy' : Real = 0.02351283871158888;
                                attribute Ixz : Real = 0.016201924786676227;
                                attribute 'σ_Ixz' : Real = 0.022566176940390956;
                                attribute Iyz : Real = 0.023212845009562173;
                                attribute 'σ_Iyz' : Real = 0.02209918015384651;
                            }
                            part <'C.1.1.2.2.3.4.3'> 'Part 188' {
                                attribute POIconv : String = "+";
                                attribute Ipoint : Boolean = false;
                                attribute mass : Real = 0.8658656481034123;
                                attribute 'σ_mass' : Real = 0.28909372274994966;
                                attribute Cx : Real = -64.91963169537485;
                                attribute 'σ_Cx' : Real = 28.721044428837228;
                                attribute Cy : Real = -43.292079120874405;
                                attribute 'σ_Cy' : Real = 28.23690002309109;
                                attribute Cz : Real = -27.12198505178094;
                                attribute 'σ_Cz' : Real = 29.057750463592832;
                                attribute Ixx : Real = 1.077036074914798;
                                attribute 'σ_Ixx' : Real = 0.37074144170588635;
                                attribute Iyy : Real = 1.1624130034062254;
                                attribute 'σ_Iyy' : Real = 0.3723953238821935;
                                attribute Izz : Real = 1.0652868370570392;
                                attribute 'σ_Izz' : Real = 0.37017423652493897;
                                attribute Ixy : Real = -0.13159559804711357;
                                attribute 'σ_Ixy' : Real = 0.02351283871158888;
                                attribute Ixz : Real = -0.047983866772825394;
                                attribute 'σ_Ixz' : Real = 0.022566176940390956;
                                attribute Iyz : Real = -0.041762921962672866;
                                attribute 'σ_Iyz' : Real = 0.02209918015384651;
                            }
                        }
                        part <'C.1.1.2.2.3.5'> 'Subassembly 54' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.2.3.5.1'> 'Part 189' {
                                attribute POIconv : String = "-";
                                attribute Ipoint : Boolean = false;
                                attribute mass : Real = 0.47780262160301207;
                                attribute 'σ_mass' : Real = 0.28909372274994966;
                                attribute Cx : Real = -73.00108168274164;
                                attribute 'σ_Cx' : Real = 28.721044428837228;
                                attribute Cy : Real = -31.360478466376662;
                                attribute 'σ_Cy' : Real = 28.23690002309109;
                                attribute Cz : Real = 95.72706767357886;
                                attribute 'σ_Cz' : Real = 29.057750463592832;
                                attribute Ixx : Real = 0.5265216427943255;
                                attribute 'σ_Ixx' : Real = 0.37074144170588635;
                                attribute Iyy : Real = 0.5261432335377831;
                                attribute 'σ_Iyy' : Real = 0.3723953238821935;
                                attribute Izz : Real = 0.5543274632164974;
                                attribute 'σ_Izz' : Real = 0.37017423652493897;
                                attribute Ixy : Real = 0.02960063515569681;
                                attribute 'σ_Ixy' : Real = 0.02351283871158888;
                                attribute Ixz : Real = -1.2168005271508214e-4;
                                attribute 'σ_Ixz' : Real = 0.022566176940390956;
                                attribute Iyz : Real = 1.6350315055952514e-4;
                                attribute 'σ_Iyz' : Real = 0.02209918015384651;
                            }
                            part <'C.1.1.2.2.3.5.2'> 'Part 190' {
                                attribute POIconv : String = "+";
                                attribute Ipoint : Boolean = false;
                                attribute mass : Real = 0.05314318692218512;
                                attribute 'σ_mass' : Real = 0.28909372274994966;
                                attribute Cx : Real = -44.827170949429274;
                                attribute 'σ_Cx' : Real = 28.721044428837228;
                                attribute Cy : Real = -76.82795417495072;
                                attribute 'σ_Cy' : Real = 28.23690002309109;
                                attribute Cz : Real = 99.72366993315518;
                                attribute 'σ_Cz' : Real = 29.057750463592832;
                                attribute Ixx : Real = 0.06773992825147897;
                                attribute 'σ_Ixx' : Real = 0.37074144170588635;
                                attribute Iyy : Real = 0.07836658136671154;
                                attribute 'σ_Iyy' : Real = 0.3723953238821935;
                                attribute Izz : Real = 0.06488608151294459;
                                attribute 'σ_Izz' : Real = 0.37017423652493897;
                                attribute Ixy : Real = 0.005263767600881721;
                                attribute 'σ_Ixy' : Real = 0.02351283871158888;
                                attribute Ixz : Real = 0.004183776910756587;
                                attribute 'σ_Ixz' : Real = 0.022566176940390956;
                                attribute Iyz : Real = -0.00301476035404252;
                                attribute 'σ_Iyz' : Real = 0.02209918015384651;
                            }
                        }
                    }
                }
                part <'C.1.1.2.3'> 'Subsystem 5' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.2.3.1'> 'Assembly 15' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.3.1.1'> 'Subassembly 55' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.1.1.1'> 'Part 191' {
                                attribute POIconv : String = "-";
                                attribute Ipoint : Boolean = false;
                                attribute mass : Real = 0.2017568920047488;
                                attribute 'σ_mass' : Real = 0.28909372274994966;
                                attribute Cx : Real = 68.65355842746794;
                                attribute 'σ_Cx' : Real = 28.721044428837228;
                                attribute Cy : Real = 0.6748892366886139;
                                attribute 'σ_Cy' : Real = 28.23690002309109;
                                attribute Cz : Real = 67.41321492008865;
                                attribute 'σ_Cz' : Real = 29.057750463592832;
                                attribute Ixx : Real = 0.24496460754134886;
                                attribute 'σ_Ixx' : Real = 0.37074144170588635;
                                attribute Iyy : Real = 0.25679066894576086;
                                attribute 'σ_Iyy' : Real = 0.3723953238821935;
                                attribute Izz : Real = 0.19759319167786243;
                                attribute 'σ_Izz' : Real = 0.37017423652493897;
                                attribute Ixy : Real = -0.006378790443042046;
                                attribute 'σ_Ixy' : Real = 0.02351283871158888;
                                attribute Ixz : Real = -0.011015689262780133;
                                attribute 'σ_Ixz' : Real = 0.022566176940390956;
                                attribute Iyz : Real = 0.014957847660477037;
                                attribute 'σ_Iyz' : Real = 0.02209918015384651;
                            }
                            part <'C.1.1.2.3.1.1.2'> 'Part 192' {
                                attribute POIconv : String = "+";
                                attribute Ipoint : Boolean = false;
                                attribute mass : Real = 0.19057214169902728;
                                attribute 'σ_mass' : Real = 0.28909372274994966;
                                attribute Cx : Real = 62.64283275231719;
                                attribute 'σ_Cx' : Real = 28.721044428837228;
                                attribute Cy : Real = -57.9179001506418;
                                attribute 'σ_Cy' : Real = 28.23690002309109;
                                attribute Cz : Real = 96.48704556748271;
                                attribute 'σ_Cz' : Real = 29.057750463592832;
                                attribute Ixx : Real = 0.21287893065200106;
                                attribute 'σ_Ixx' : Real = 0.37074144170588635;
                                attribute Iyy : Real = 0.20975969055237606;
                                attribute 'σ_Iyy' : Real = 0.3723953238821935;
                                attribute Izz : Real = 0.2293773328263036;
                                attribute 'σ_Izz' : Real = 0.37017423652493897;
                                attribute Ixy : Real = -0.015535023367661199;
                                attribute 'σ_Ixy' : Real = 0.02351283871158888;
                                attribute Ixz : Real = -0.0036337337007628936;
                                attribute 'σ_Ixz' : Real = 0.022566176940390956;
                                attribute Iyz : Real = -0.0188370907797132;
                                attribute 'σ_Iyz' : Real = 0.02209918015384651;
                            }
                            part <'C.1.1.2.3.1.1.3'> 'Part 193' {
                                attribute POIconv : String = "-";
                                attribute Ipoint : Boolean = false;
                                attribute mass : Real = 0.5426606895879377;
                                attribute 'σ_mass' : Real = 0.28909372274994966;
                                attribute Cx : Real = 80.8619745541364;
                                attribute 'σ_Cx' : Real = 28.721044428837228;
                                attribute Cy : Real = 8.39486550539732;
                                attribute 'σ_Cy' : Real = 28.23690002309109;
                                attribute Cz : Real = 6.17535631172359;
                                attribute 'σ_Cz' : Real = 29.057750463592832;
                                attribute Ixx : Real = 0.8269090735238956;
                                attribute 'σ_Ixx' : Real = 0.37074144170588635;
                                attribute Iyy : Real = 0.7506516924279656;
                                attribute 'σ_Iyy' : Real = 0.3723953238821935;
                                attribute Izz : Real = 0.7343245518450107;
                                attribute 'σ_Izz' : Real = 0.37017423652493897;
                                attribute Ixy : Real = 0.07182772582190096;
                                attribute 'σ_Ixy' : Real = 0.02351283871158888;
                                attribute Ixz : Real = -0.05154987776560595;
                                attribute 'σ_Ixz' : Real = 0.022566176940390956;
                                attribute Iyz : Real = -0.024594550556900477;
                                attribute 'σ_Iyz' : Real = 0.02209918015384651;
                            }
                            part <'C.1.1.2.3.1.1.4'> 'Part 194' {
                                attribute POIconv : String = "-";
                                attribute Ipoint : Boolean = false;
                                attribute mass : Real = 0.2217793539171107;
                                attribute 'σ_mass' : Real = 0.28909372274994966;
                                attribute Cx : Real = 17.347895121201873;
                                attribute 'σ_Cx' : Real = 28.721044428837228;
                                attribute Cy : Real = -26.311938371509314;
                                attribute 'σ_Cy' : Real = 28.23690002309109;
                                attribute Cz : Real = -75.32026804983616;
                                attribute 'σ_Cz' : Real = 29.057750463592832;
                                attribute Ixx : Real = 0.2942299446199009;
                                attribute 'σ_Ixx' : Real = 0.37074144170588635;
                                attribute Iyy : Real = 0.31046253632181203;
                                attribute 'σ_Iyy' : Real = 0.3723953238821935;
                                attribute Izz : Real = 0.2813837037222907;
                                attribute 'σ_Izz' : Real = 0.37017423652493897;
                                attribute Ixy : Real = 0.006218850816250379;
                                attribute 'σ_Ixy' : Real = 0.02351283871158888;
                                attribute Ixz : Real = -0.02413819180300856;
                                attribute 'σ_Ixz' : Real = 0.022566176940390956;
                                attribute Iyz : Real = 0.012351308300200899;
                                attribute 'σ_Iyz' : Real = 0.02209918015384651;
                            }
                            part <'C.1.1.2.3.1.1.5'> 'Part 195' {
                                attribute POIconv : String = "+";
                                attribute Ipoint : Boolean = false;
                                attribute mass : Real = 0.6768042528231163;
                                attribute 'σ_mass' : Real = 0.28909372274994966;
                                attribute Cx : Real = 29.585199523717165;
                                attribute 'σ_Cx' : Real = 28.721044428837228;
                                attribute Cy : Real = -34.10200816579163;
                                attribute 'σ_Cy' : Real = 28.23690002309109;
                                attribute Cz : Real = 44.80167152360082;
                                attribute 'σ_Cz' : Real = 29.057750463592832;
                                attribute Ixx : Real = 0.7392883402225693;
                                attribute 'σ_Ixx' : Real = 0.37074144170588635;
                                attribute Iyy : Real = 0.8312327009620615;
                                attribute 'σ_Iyy' : Real = 0.3723953238821935;
                                attribute Izz : Real = 0.8362273992383054;
                                attribute 'σ_Izz' : Real = 0.37017423652493897;
                                attribute Ixy : Real = 0.02514644397238257;
                                attribute 'σ_Ixy' : Real = 0.02351283871158888;
                                attribute Ixz : Real = 0.01741511537849129;
                                attribute 'σ_Ixz' : Real = 0.022566176940390956;
                                attribute Iyz : Real = 0.020945190167058127;
                                attribute 'σ_Iyz' : Real = 0.02209918015384651;
                            }
                        }
                        part <'C.1.1.2.3.1.2'> 'Subassembly 56' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.1.2.1'> 'Part 196' {
                                attribute POIconv : String = "+";
                                attribute Ipoint : Boolean = false;
                                attribute mass : Real = 0.03308807502221316;
                                attribute 'σ_mass' : Real = 0.28909372274994966;
                                attribute Cx : Real = 28.40084624476731;
                                attribute 'σ_Cx' : Real = 28.721044428837228;
                                attribute Cy : Real = -24.667787086218596;
                                attribute 'σ_Cy' : Real = 28.23690002309109;
                                attribute Cz : Real = 28.634455800056458;
                                attribute 'σ_Cz' : Real = 29.057750463592832;
                                attribute Ixx : Real = 0.03507778863209477;
                                attribute 'σ_Ixx' : Real = 0.37074144170588635;
                                attribute Iyy : Real = 0.039794912554532526;
                                attribute 'σ_Iyy' : Real = 0.3723953238821935;
                                attribute Izz : Real = 0.041501837097676686;
                                attribute 'σ_Izz' : Real = 0.37017423652493897;
                                attribute Ixy : Real = 5.716764811712153e-4;
                                attribute 'σ_Ixy' : Real = 0.02351283871158888;
                                attribute Ixz : Real = 1.0225247334140415e-4;
                                attribute 'σ_Ixz' : Real = 0.022566176940390956;
                                attribute Iyz : Real = -7.3559638454395216e-06;
                                attribute 'σ_Iyz' : Real = 0.02209918015384651;
                            }
                            part <'C.1.1.2.3.1.2.2'> 'Part 197' {
                                attribute POIconv : String = "+";
                                attribute Ipoint : Boolean = false;
                                attribute mass : Real = 0.44275650366465563;
                                attribute 'σ_mass' : Real = 0.28909372274994966;
                                attribute Cx : Real = -14.455753704532981;
                                attribute 'σ_Cx' : Real = 28.721044428837228;
                                attribute Cy : Real = -11.410603346303105;
                                attribute 'σ_Cy' : Real = 28.23690002309109;
                                attribute Cz : Real = -10.451269242912531;
                                attribute 'σ_Cz' : Real = 29.057750463592832;
                                attribute Ixx : Real = 0.47554547574018785;
                                attribute 'σ_Ixx' : Real = 0.37074144170588635;
                                attribute Iyy : Real = 0.4739426683714093;
                                attribute 'σ_Iyy' : Real = 0.3723953238821935;
                                attribute Izz : Real = 0.4059268710803595;
                                attribute 'σ_Izz' : Real = 0.37017423652493897;
                                attribute Ixy : Real = 0.0028811845819153334;
                                attribute 'σ_Ixy' : Real = 0.02351283871158888;
                                attribute Ixz : Real = -0.010076932861846102;
                                attribute 'σ_Ixz' : Real = 0.022566176940390956;
                                attribute Iyz : Real = -0.019369151282463012;
                                attribute 'σ_Iyz' : Real = 0.02209918015384651;
                            }
                        }
                        part <'C.1.1.2.3.1.3'> 'Subassembly 57' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.1.3.1'> 'Part 198' {
                                attribute POIconv : String = "+";
                                attribute Ipoint : Boolean = false;
                                attribute mass : Real = 0.5433124298229813;
                                attribute 'σ_mass' : Real = 0.28909372274994966;
                                attribute Cx : Real = 91.01874330081046;
                                attribute 'σ_Cx' : Real = 28.721044428837228;
                                attribute Cy : Real = -27.00051823630929;
                                attribute 'σ_Cy' : Real = 28.23690002309109;
                                attribute Cz : Real = 34.61931757628918;
                                attribute 'σ_Cz' : Real = 29.057750463592832;
                                attribute Ixx : Real = 0.7382956422295451;
                                attribute 'σ_Ixx' : Real = 0.37074144170588635;
                                attribute Iyy : Real = 0.7107770884193192;
                                attribute 'σ_Iyy' : Real = 0.3723953238821935;
                                attribute Izz : Real = 0.8113776701219594;
                                attribute 'σ_Izz' : Real = 0.37017423652493897;
                                attribute Ixy : Real = 0.01318499833317646;
                                attribute 'σ_Ixy' : Real = 0.02351283871158888;
                                attribute Ixz : Real = -0.02182231900762043;
                                attribute 'σ_Ixz' : Real = 0.022566176940390956;
                                attribute Iyz : Real = -0.006105077178933551;
                                attribute 'σ_Iyz' : Real = 0.02209918015384651;
                            }
                            part <'C.1.1.2.3.1.3.2'> 'Part 199' {
                                attribute POIconv : String = "+";
                                attribute Ipoint : Boolean = false;
                                attribute mass : Real = 0.34429813690832817;
                                attribute 'σ_mass' : Real = 0.28909372274994966;
                                attribute Cx : Real = 86.92097919993103;
                                attribute 'σ_Cx' : Real = 28.721044428837228;
                                attribute Cy : Real = -4.746119165793061;
                                attribute 'σ_Cy' : Real = 28.23690002309109;
                                attribute Cz : Real = 56.174975261092186;
                                attribute 'σ_Cz' : Real = 29.057750463592832;
                                attribute Ixx : Real = 0.41979101797520396;
                                attribute 'σ_Ixx' : Real = 0.37074144170588635;
                                attribute Iyy : Real = 0.3710750195989728;
                                attribute 'σ_Iyy' : Real = 0.3723953238821935;
                                attribute Izz : Real = 0.41846541440958507;
                                attribute 'σ_Izz' : Real = 0.37017423652493897;
                                attribute Ixy : Real = -0.036823989763189055;
                                attribute 'σ_Ixy' : Real = 0.02351283871158888;
                                attribute Ixz : Real = -0.007268370627463555;
                                attribute 'σ_Ixz' : Real = 0.022566176940390956;
                                attribute Iyz : Real = 0.015092720033780762;
                                attribute 'σ_Iyz' : Real = 0.02209918015384651;
                            }
                            part <'C.1.1.2.3.1.3.3'> 'Part 200' {
                                attribute POIconv : String = "-";
                                attribute Ipoint : Boolean = false;
                                attribute mass : Real = 0.7634404668330681;
                                attribute 'σ_mass' : Real = 0.28909372274994966;
                                attribute Cx : Real = -62.20163619145751;
                                attribute 'σ_Cx' : Real = 28.721044428837228;
                                attribute Cy : Real = 31.335248751565814;
                                attribute 'σ_Cy' : Real = 28.23690002309109;
                                attribute Cz : Real = 45.288399839773774;
                                attribute 'σ_Cz' : Real = 29.057750463592832;
                                attribute Ixx : Real = 0.7506995817795064;
                                attribute 'σ_Ixx' : Real = 0.37074144170588635;
                                attribute Iyy : Real = 0.7634941794798735;
                                attribute 'σ_Iyy' : Real = 0.3723953238821935;
                                attribute Izz : Real = 0.7933615100188953;
                                attribute 'σ_Izz' : Real = 0.37017423652493897;
                                attribute Ixy : Real = -0.022147348672817348;
                                attribute 'σ_Ixy' : Real = 0.02351283871158888;
                                attribute Ixz : Real = -0.002487193942590132;
                                attribute 'σ_Ixz' : Real = 0.022566176940390956;
                                attribute Iyz : Real = -0.005297538129773369;
                                attribute 'σ_Iyz' : Real = 0.02209918015384651;
                            }
                            part <'C.1.1.2.3.1.3.4'> 'Part 201' {
                                attribute POIconv : String = "-";
                                attribute Ipoint : Boolean = false;
                                attribute mass : Real = 0.13778229261725208;
                                attribute 'σ_mass' : Real = 0.28909372274994966;
                                attribute Cx : Real = -63.09048677794635;
                                attribute 'σ_Cx' : Real = 28.721044428837228;
                                attribute Cy : Real = -85.07544659078121;
                                attribute 'σ_Cy' : Real = 28.23690002309109;
                                attribute Cz : Real = 99.00784189812839;
                                attribute 'σ_Cz' : Real = 29.057750463592832;
                                attribute Ixx : Real = 0.17923436663313697;
                                attribute 'σ_Ixx' : Real = 0.37074144170588635;
                                attribute Iyy : Real = 0.18238904714735232;
                                attribute 'σ_Iyy' : Real = 0.3723953238821935;
                                attribute Izz : Real = 0.16877397682766557;
                                attribute 'σ_Izz' : Real = 0.37017423652493897;
                                attribute Ixy : Real = -0.005829413648427368;
                                attribute 'σ_Ixy' : Real = 0.02351283871158888;
                                attribute Ixz : Real = 8.768979596522473e-5;
                                attribute 'σ_Ixz' : Real = 0.022566176940390956;
                                attribute Iyz : Real = 0.013625494200226625;
                                attribute 'σ_Iyz' : Real = 0.02209918015384651;
                            }
                        }
                        part <'C.1.1.2.3.1.4'> 'Subassembly 58' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.1.4.1'> 'Part 202' {
                                attribute POIconv : String = "+";
                                attribute Ipoint : Boolean = false;
                                attribute mass : Real = 0.07755370915262029;
                                attribute 'σ_mass' : Real = 0.28909372274994966;
                                attribute Cx : Real = -5.862633092328906;
                                attribute 'σ_Cx' : Real = 28.721044428837228;
                                attribute Cy : Real = 72.41359152831137;
                                attribute 'σ_Cy' : Real = 28.23690002309109;
                                attribute Cz : Real = -66.02655639871955;
                                attribute 'σ_Cz' : Real = 29.057750463592832;
                                attribute Ixx : Real = 0.10696283434151345;
                                attribute 'σ_Ixx' : Real = 0.37074144170588635;
                                attribute Iyy : Real = 0.11241554872105647;
                                attribute 'σ_Iyy' : Real = 0.3723953238821935;
                                attribute Izz : Real = 0.10620296057443154;
                                attribute 'σ_Izz' : Real = 0.37017423652493897;
                                attribute Ixy : Real = -0.007846729545288353;
                                attribute 'σ_Ixy' : Real = 0.02351283871158888;
                                attribute Ixz : Real = -0.005205180699407828;
                                attribute 'σ_Ixz' : Real = 0.022566176940390956;
                                attribute Iyz : Real = -0.007361154328928053;
                                attribute 'σ_Iyz' : Real = 0.02209918015384651;
                            }
                            part <'C.1.1.2.3.1.4.2'> 'Part 203' {
                                attribute POIconv : String = "-";
                                attribute Ipoint : Boolean = false;
                                attribute mass : Real = 0.10513522690092214;
                                attribute 'σ_mass' : Real = 0.28909372274994966;
                                attribute Cx : Real = 57.00324783101678;
                                attribute 'σ_Cx' : Real = 28.721044428837228;
                                attribute Cy : Real = 47.535066306591034;
                                attribute 'σ_Cy' : Real = 28.23690002309109;
                                attribute Cz : Real = -16.182217560708523;
                                attribute 'σ_Cz' : Real = 29.057750463592832;
                                attribute Ixx : Real = 0.13551568426536068;
                                attribute 'σ_Ixx' : Real = 0.37074144170588635;
                                attribute Iyy : Real = 0.13368519737671267;
                                attribute 'σ_Iyy' : Real = 0.3723953238821935;
                                attribute Izz : Real = 0.11999905947091685;
                                attribute 'σ_Izz' : Real = 0.37017423652493897;
                                attribute Ixy : Real = -0.004373116928128338;
                                attribute 'σ_Ixy' : Real = 0.02351283871158888;
                                attribute Ixz : Real = -0.008104542666268142;
                                attribute 'σ_Ixz' : Real = 0.022566176940390956;
                                attribute Iyz : Real = -0.004497123293024494;
                                attribute 'σ_Iyz' : Real = 0.02209918015384651;
                            }
                            part <'C.1.1.2.3.1.4.3'> 'Part 204' {
                                attribute POIconv : String = "+";
                                attribute Ipoint : Boolean = false;
                                attribute mass : Real = 0.25733619152544995;
                                attribute 'σ_mass' : Real = 0.28909372274994966;
                                attribute Cx : Real = 7.374726561829448;
                                attribute 'σ_Cx' : Real = 28.721044428837228;
                                attribute Cy : Real = 80.04060229286551;
                                attribute 'σ_Cy' : Real = 28.23690002309109;
                                attribute Cz : Real = 92.05705286003649;
                                attribute 'σ_Cz' : Real = 29.057750463592832;
                                attribute Ixx : Real = 0.2771713747403308;
                                attribute 'σ_Ixx' : Real = 0.37074144170588635;
                                attribute Iyy : Real = 0.33526471192253005;
                                attribute 'σ_Iyy' : Real = 0.3723953238821935;
                                attribute Izz : Real = 0.34104150255091464;
                                attribute 'σ_Izz' : Real = 0.37017423652493897;
                                attribute Ixy : Real = -0.025175789319774364;
                                attribute 'σ_Ixy' : Real = 0.02351283871158888;
                                attribute Ixz : Real = -0.015170073867423271;
                                attribute 'σ_Ixz' : Real = 0.022566176940390956;
                                attribute Iyz : Real = 0.005649570345318704;
                                attribute 'σ_Iyz' : Real = 0.02209918015384651;
                            }
                            part <'C.1.1.2.3.1.4.4'> 'Part 205' {
                                attribute POIconv : String = "-";
                                attribute Ipoint : Boolean = false;
                                attribute mass : Real = 0.6430239959149622;
                                attribute 'σ_mass' : Real = 0.28909372274994966;
                                attribute Cx : Real = -40.56690093129873;
                                attribute 'σ_Cx' : Real = 28.721044428837228;
                                attribute Cy : Real = 69.87919686362147;
                                attribute 'σ_Cy' : Real = 28.23690002309109;
                                attribute Cz : Real = -7.449634652584791;
                                attribute 'σ_Cz' : Real = 29.057750463592832;
                                attribute Ixx : Real = 0.7825312164095768;
                                attribute 'σ_Ixx' : Real = 0.37074144170588635;
                                attribute Iyy : Real = 0.7553746232066285;
                                attribute 'σ_Iyy' : Real = 0.3723953238821935;
                                attribute Izz : Real = 0.8028865719582547;
                                attribute 'σ_Izz' : Real = 0.37017423652493897;
                                attribute Ixy : Real = -0.011248901337559134;
                                attribute 'σ_Ixy' : Real = 0.02351283871158888;
                                attribute Ixz : Real = 0.009332727233953871;
                                attribute 'σ_Ixz' : Real = 0.022566176940390956;
                                attribute Iyz : Real = -0.020336001319640418;
                                attribute 'σ_Iyz' : Real = 0.02209918015384651;
                            }
                            part <'C.1.1.2.3.1.4.5'> 'Part 206' {
                                attribute POIconv : String = "-";
                                attribute Ipoint : Boolean = false;
                                attribute mass : Real = 0.5342970893140883;
                                attribute 'σ_mass' : Real = 0.28909372274994966;
                                attribute Cx : Real = 2.947690337896347;
                                attribute 'σ_Cx' : Real = 28.721044428837228;
                                attribute Cy : Real = 74.7065988369286;
                                attribute 'σ_Cy' : Real = 28.23690002309109;
                                attribute Cz : Real = 79.68378127552569;
                                attribute 'σ_Cz' : Real = 29.057750463592832;
                                attribute Ixx : Real = 0.6129229295080617;
                                attribute 'σ_Ixx' : Real = 0.37074144170588635;
                                attribute Iyy : Real = 0.6611321472380082;
                                attribute 'σ_Iyy' : Real = 0.3723953238821935;
                                attribute Izz : Real = 0.6752065583022;
                                attribute 'σ_Izz' : Real = 0.37017423652493897;
                                attribute Ixy : Real = 0.02353989303576627;
                                attribute 'σ_Ixy' : Real = 0.02351283871158888;
                                attribute Ixz : Real = 0.008023090549977647;
                                attribute 'σ_Ixz' : Real = 0.022566176940390956;
                                attribute Iyz : Real = 0.013821623675489572;
                                attribute 'σ_Iyz' : Real = 0.02209918015384651;
                            }
                        }
                        part <'C.1.1.2.3.1.5'> 'Subassembly 59' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.1.5.1'> 'Part 207' {
                                attribute POIconv : String = "+";
                                attribute Ipoint : Boolean = false;
                                attribute mass : Real = 0.9916431890237145;
                                attribute 'σ_mass' : Real = 0.28909372274994966;
                                attribute Cx : Real = -55.29658221639693;
                                attribute 'σ_Cx' : Real = 28.721044428837228;
                                attribute Cy : Real = -62.59580650366843;
                                attribute 'σ_Cy' : Real = 28.23690002309109;
                                attribute Cz : Real = -10.22542673163116;
                                attribute 'σ_Cz' : Real = 29.057750463592832;
                                attribute Ixx : Real = 1.3052119954712176;
                                attribute 'σ_Ixx' : Real = 0.37074144170588635;
                                attribute Iyy : Real = 1.298355961276188;
                                attribute 'σ_Iyy' : Real = 0.3723953238821935;
                                attribute Izz : Real = 1.1960568089899328;
                                attribute 'σ_Izz' : Real = 0.37017423652493897;
                                attribute Ixy : Real = -0.0026266695130579085;
                                attribute 'σ_Ixy' : Real = 0.02351283871158888;
                                attribute Ixz : Real = 0.010798719757647375;
                                attribute 'σ_Ixz' : Real = 0.022566176940390956;
                                attribute Iyz : Real = -0.02861200530929836;
                                attribute 'σ_Iyz' : Real = 0.02209918015384651;
                            }
                            part <'C.1.1.2.3.1.5.2'> 'Part 208' {
                                attribute POIconv : String = "-";
                                attribute Ipoint : Boolean = false;
                                attribute mass : Real = 0.06942617495777086;
                                attribute 'σ_mass' : Real = 0.28909372274994966;
                                attribute Cx : Real = 91.56149867922068;
                                attribute 'σ_Cx' : Real = 28.721044428837228;
                                attribute Cy : Real = 63.96658178418875;
                                attribute 'σ_Cy' : Real = 28.23690002309109;
                                attribute Cz : Real = -60.67341645248234;
                                attribute 'σ_Cz' : Real = 29.057750463592832;
                                attribute Ixx : Real = 0.07283614190677053;
                                attribute 'σ_Ixx' : Real = 0.37074144170588635;
                                attribute Iyy : Real = 0.0762629662462501;
                                attribute 'σ_Iyy' : Real = 0.3723953238821935;
                                attribute Izz : Real = 0.08098728686827261;
                                attribute 'σ_Izz' : Real = 0.37017423652493897;
                                attribute Ixy : Real = 0.00983192775955202;
                                attribute 'σ_Ixy' : Real = 0.02351283871158888;
                                attribute Ixz : Real = -0.0019387864821624144;
                                attribute 'σ_Ixz' : Real = 0.022566176940390956;
                                attribute Iyz : Real = 0.001152984632487434;
                                attribute 'σ_Iyz' : Real = 0.02209918015384651;
                            }
                        }
                    }
                    part <'C.1.1.2.3.2'> 'Assembly 16' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.3.2.1'> 'Subassembly 60' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.2.1.1'> 'Part 209' {
                                attribute POIconv : String = "+";
                                attribute Ipoint : Boolean = false;
                                attribute mass : Real = 0.13887204244593157;
                                attribute 'σ_mass' : Real = 0.28909372274994966;
                                attribute Cx : Real = 89.26507718861103;
                                attribute 'σ_Cx' : Real = 28.721044428837228;
                                attribute Cy : Real = 36.58494339324534;
                                attribute 'σ_Cy' : Real = 28.23690002309109;
                                attribute Cz : Real = -79.73456969484687;
                                attribute 'σ_Cz' : Real = 29.057750463592832;
                                attribute Ixx : Real = 0.14514116367016228;
                                attribute 'σ_Ixx' : Real = 0.37074144170588635;
                                attribute Iyy : Real = 0.14596382733371122;
                                attribute 'σ_Iyy' : Real = 0.3723953238821935;
                                attribute Izz : Real = 0.14465895499196033;
                                attribute 'σ_Izz' : Real = 0.37017423652493897;
                                attribute Ixy : Real = 0.005346107723156964;
                                attribute 'σ_Ixy' : Real = 0.02351283871158888;
                                attribute Ixz : Real = 0.0015761853435010964;
                                attribute 'σ_Ixz' : Real = 0.022566176940390956;
                                attribute Iyz : Real = -0.0037011263911777134;
                                attribute 'σ_Iyz' : Real = 0.02209918015384651;
                            }
                            part <'C.1.1.2.3.2.1.2'> 'Part 210' {
                                attribute POIconv : String = "+";
                                attribute Ipoint : Boolean = false;
                                attribute mass : Real = 0.697480263418518;
                                attribute 'σ_mass' : Real = 0.28909372274994966;
                                attribute Cx : Real = 2.2660118993371725;
                                attribute 'σ_Cx' : Real = 28.721044428837228;
                                attribute Cy : Real = -53.27062103897333;
                                attribute 'σ_Cy' : Real = 28.23690002309109;
                                attribute Cz : Real = -49.074615351855755;
                                attribute 'σ_Cz' : Real = 29.057750463592832;
                                attribute Ixx : Real = 0.9396640060114518;
                                attribute 'σ_Ixx' : Real = 0.37074144170588635;
                                attribute Iyy : Real = 0.8412246628530119;
                                attribute 'σ_Iyy' : Real = 0.3723953238821935;
                                attribute Izz : Real = 0.962606489559149;
                                attribute 'σ_Izz' : Real = 0.37017423652493897;
                                attribute Ixy : Real = 0.020095831167865057;
                                attribute 'σ_Ixy' : Real = 0.02351283871158888;
                                attribute Ixz : Real = -0.07976675379093173;
                                attribute 'σ_Ixz' : Real = 0.022566176940390956;
                                attribute Iyz : Real = 0.029116783923820194;
                                attribute 'σ_Iyz' : Real = 0.02209918015384651;
                            }
                        }
                        part <'C.1.1.2.3.2.2'> 'Subassembly 61' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.2.2.1'> 'Part 211' {
                                attribute POIconv : String = "+";
                                attribute Ipoint : Boolean = false;
                                attribute mass : Real = 0.7717454422237352;
                                attribute 'σ_mass' : Real = 0.28909372274994966;
                                attribute Cx : Real = -87.09769323468208;
                                attribute 'σ_Cx' : Real = 28.721044428837228;
                                attribute Cy : Real = 57.12637607939541;
                                attribute 'σ_Cy' : Real = 28.23690002309109;
                                attribute Cz : Real = -47.994602378457785;
                                attribute 'σ_Cz' : Real = 29.057750463592832;
                                attribute Ixx : Real = 1.021487361083056;
                                attribute 'σ_Ixx' : Real = 0.37074144170588635;
                                attribute Iyy : Real = 1.0702934663447334;
                                attribute 'σ_Iyy' : Real = 0.3723953238821935;
                                attribute Izz : Real = 1.1697831672251717;
                                attribute 'σ_Izz' : Real = 0.37017423652493897;
                                attribute Ixy : Real = -0.04207693301034161;
                                attribute 'σ_Ixy' : Real = 0.02351283871158888;
                                attribute Ixz : Real = 0.04459838752703561;
                                attribute 'σ_Ixz' : Real = 0.022566176940390956;
                                attribute Iyz : Real = 0.10953832114419812;
                                attribute 'σ_Iyz' : Real = 0.02209918015384651;
                            }
                            part <'C.1.1.2.3.2.2.2'> 'Part 212' {
                                attribute POIconv : String = "+";
                                attribute Ipoint : Boolean = false;
                                attribute mass : Real = 0.11227221190836281;
                                attribute 'σ_mass' : Real = 0.28909372274994966;
                                attribute Cx : Real = -99.41370082087815;
                                attribute 'σ_Cx' : Real = 28.721044428837228;
                                attribute Cy : Real = 97.38592957146466;
                                attribute 'σ_Cy' : Real = 28.23690002309109;
                                attribute Cz : Real = -29.90108672529459;
                                attribute 'σ_Cz' : Real = 29.057750463592832;
                                attribute Ixx : Real = 0.15903547245720948;
                                attribute 'σ_Ixx' : Real = 0.37074144170588635;
                                attribute Iyy : Real = 0.14521923226222264;
                                attribute 'σ_Iyy' : Real = 0.3723953238821935;
                                attribute Izz : Real = 0.14012225356268734;
                                attribute 'σ_Izz' : Real = 0.37017423652493897;
                                attribute Ixy : Real = 0.004382316501913142;
                                attribute 'σ_Ixy' : Real = 0.02351283871158888;
                                attribute Ixz : Real = 0.002159721094211143;
                                attribute 'σ_Ixz' : Real = 0.022566176940390956;
                                attribute Iyz : Real = -0.0019180314823680834;
                                attribute 'σ_Iyz' : Real = 0.02209918015384651;
                            }
                            part <'C.1.1.2.3.2.2.3'> 'Part 213' {
                                attribute POIconv : String = "+";
                                attribute Ipoint : Boolean = false;
                                attribute mass : Real = 0.1452233827507589;
                                attribute 'σ_mass' : Real = 0.28909372274994966;
                                attribute Cx : Real = 69.70235966145992;
                                attribute 'σ_Cx' : Real = 28.721044428837228;
                                attribute Cy : Real = -99.04682179912925;
                                attribute 'σ_Cy' : Real = 28.23690002309109;
                                attribute Cz : Real = -4.038118151947856;
                                attribute 'σ_Cz' : Real = 29.057750463592832;
                                attribute Ixx : Real = 0.16467064719103577;
                                attribute 'σ_Ixx' : Real = 0.37074144170588635;
                                attribute Iyy : Real = 0.16516332636656902;
                                attribute 'σ_Iyy' : Real = 0.3723953238821935;
                                attribute Izz : Real = 0.16574756405439617;
                                attribute 'σ_Izz' : Real = 0.37017423652493897;
                                attribute Ixy : Real = 6.73015669809325e-5;
                                attribute 'σ_Ixy' : Real = 0.02351283871158888;
                                attribute Ixz : Real = 8.064859573860474e-4;
                                attribute 'σ_Ixz' : Real = 0.022566176940390956;
                                attribute Iyz : Real = 9.45429883206804e-5;
                                attribute 'σ_Iyz' : Real = 0.02209918015384651;
                            }
                        }
                        part <'C.1.1.2.3.2.3'> 'Subassembly 62' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.2.3.1'> 'Part 214' {
                                attribute POIconv : String = "-";
                                attribute Ipoint : Boolean = false;
                                attribute mass : Real = 0.9044022637305316;
                                attribute 'σ_mass' : Real = 0.28909372274994966;
                                attribute Cx : Real = -73.1652638874948;
                                attribute 'σ_Cx' : Real = 28.721044428837228;
                                attribute Cy : Real = 47.319724690169096;
                                attribute 'σ_Cy' : Real = 28.23690002309109;
                                attribute Cz : Real = -9.99916298314929;
                                attribute 'σ_Cz' : Real = 29.057750463592832;
                                attribute Ixx : Real = 0.9492325947565305;
                                attribute 'σ_Ixx' : Real = 0.37074144170588635;
                                attribute Iyy : Real = 0.9360320524630835;
                                attribute 'σ_Iyy' : Real = 0.3723953238821935;
                                attribute Izz : Real = 0.8839911821577315;
                                attribute 'σ_Izz' : Real = 0.37017423652493897;
                                attribute Ixy : Real = 0.009948496644084932;
                                attribute 'σ_Ixy' : Real = 0.02351283871158888;
                                attribute Ixz : Real = 0.019967147101891583;
                                attribute 'σ_Ixz' : Real = 0.022566176940390956;
                                attribute Iyz : Real = -0.025267237121970227;
                                attribute 'σ_Iyz' : Real = 0.02209918015384651;
                            }
                            part <'C.1.1.2.3.2.3.2'> 'Part 215' {
                                attribute POIconv : String = "-";
                                attribute Ipoint : Boolean = false;
                                attribute mass : Real = 0.2961221624750178;
                                attribute 'σ_mass' : Real = 0.28909372274994966;
                                attribute Cx : Real = 57.75272874161601;
                                attribute 'σ_Cx' : Real = 28.721044428837228;
                                attribute Cy : Real = 23.951233038678765;
                                attribute 'σ_Cy' : Real = 28.23690002309109;
                                attribute Cz : Real = 2.959229564294219;
                                attribute 'σ_Cz' : Real = 29.057750463592832;
                                attribute Ixx : Real = 0.3626336955522084;
                                attribute 'σ_Ixx' : Real = 0.37074144170588635;
                                attribute Iyy : Real = 0.3879335935391537;
                                attribute 'σ_Iyy' : Real = 0.3723953238821935;
                                attribute Izz : Real = 0.3270495279040912;
                                attribute 'σ_Izz' : Real = 0.37017423652493897;
                                attribute Ixy : Real = 0.013342437011175195;
                                attribute 'σ_Ixy' : Real = 0.02351283871158888;
                                attribute Ixz : Real = 0.020906812089557816;
                                attribute 'σ_Ixz' : Real = 0.022566176940390956;
                                attribute Iyz : Real = -0.027296757254632677;
                                attribute 'σ_Iyz' : Real = 0.02209918015384651;
                            }
                            part <'C.1.1.2.3.2.3.3'> 'Part 216' {
                                attribute POIconv : String = "+";
                                attribute Ipoint : Boolean = false;
                                attribute mass : Real = 0.22443272114475257;
                                attribute 'σ_mass' : Real = 0.28909372274994966;
                                attribute Cx : Real = -4.827612871304154;
                                attribute 'σ_Cx' : Real = 28.721044428837228;
                                attribute Cy : Real = 99.99984567984939;
                                attribute 'σ_Cy' : Real = 28.23690002309109;
                                attribute Cz : Real = -53.286241833120584;
                                attribute 'σ_Cz' : Real = 29.057750463592832;
                                attribute Ixx : Real = 0.26050450990952745;
                                attribute 'σ_Ixx' : Real = 0.37074144170588635;
                                attribute Iyy : Real = 0.28602244937862803;
                                attribute 'σ_Iyy' : Real = 0.3723953238821935;
                                attribute Izz : Real = 0.2639115457422525;
                                attribute 'σ_Izz' : Real = 0.37017423652493897;
                                attribute Ixy : Real = 0.02205493497426421;
                                attribute 'σ_Ixy' : Real = 0.02351283871158888;
                                attribute Ixz : Real = -0.004006234463396817;
                                attribute 'σ_Ixz' : Real = 0.022566176940390956;
                                attribute Iyz : Real = 0.005434384403010348;
                                attribute 'σ_Iyz' : Real = 0.02209918015384651;
                            }
                            part <'C.1.1.2.3.2.3.4'> 'Part 217' {
                                attribute POIconv : String = "+";
                                attribute Ipoint : Boolean = false;
                                attribute mass : Real = 0.3628422315439675;
                                attribute 'σ_mass' : Real = 0.28909372274994966;
                                attribute Cx : Real = -91.83305935002863;
                                attribute 'σ_Cx' : Real = 28.721044428837228;
                                attribute Cy : Real = 73.45646698959172;
                                attribute 'σ_Cy' : Real = 28.23690002309109;
                                attribute Cz : Real = 86.74204144626856;
                                attribute 'σ_Cz' : Real = 29.057750463592832;
                                attribute Ixx : Real = 0.4874537378145461;
                                attribute 'σ_Ixx' : Real = 0.37074144170588635;
                                attribute Iyy : Real = 0.48705138601994724;
                                attribute 'σ_Iyy' : Real = 0.3723953238821935;
                                attribute Izz : Real = 0.44344065095010604;
                                attribute 'σ_Izz' : Real = 0.37017423652493897;
                                attribute Ixy : Real = -0.0049053120278111425;
                                attribute 'σ_Ixy' : Real = 0.02351283871158888;
                                attribute Ixz : Real = 0.0156571873612094;
                                attribute 'σ_Ixz' : Real = 0.022566176940390956;
                                attribute Iyz : Real = -0.016236185597347543;
                                attribute 'σ_Iyz' : Real = 0.02209918015384651;
                            }
                            part <'C.1.1.2.3.2.3.5'> 'Part 218' {
                                attribute POIconv : String = "-";
                                attribute Ipoint : Boolean = false;
                                attribute mass : Real = 0.5219580342152622;
                                attribute 'σ_mass' : Real = 0.28909372274994966;
                                attribute Cx : Real = -86.63846324197948;
                                attribute 'σ_Cx' : Real = 28.721044428837228;
                                attribute Cy : Real = 29.20695743523538;
                                attribute 'σ_Cy' : Real = 28.23690002309109;
                                attribute Cz : Real = 84.14441836066544;
                                attribute 'σ_Cz' : Real = 29.057750463592832;
                                attribute Ixx : Real = 0.7293026154351471;
                                attribute 'σ_Ixx' : Real = 0.37074144170588635;
                                attribute Iyy : Real = 0.735436075843346;
                                attribute 'σ_Iyy' : Real = 0.3723953238821935;
                                attribute Izz : Real = 0.7321682560002494;
                                attribute 'σ_Izz' : Real = 0.37017423652493897;
                                attribute Ixy : Real = -0.009181125230816344;
                                attribute 'σ_Ixy' : Real = 0.02351283871158888;
                                attribute Ixz : Real = -0.006440108924525716;
                                attribute 'σ_Ixz' : Real = 0.022566176940390956;
                                attribute Iyz : Real = -0.006741881939528966;
                                attribute 'σ_Iyz' : Real = 0.02209918015384651;
                            }
                        }
                        part <'C.1.1.2.3.2.4'> 'Subassembly 63' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.2.4.1'> 'Part 219' {
                                attribute POIconv : String = "+";
                                attribute Ipoint : Boolean = false;
                                attribute mass : Real = 0.9988584387758747;
                                attribute 'σ_mass' : Real = 0.28909372274994966;
                                attribute Cx : Real = -42.60098938830197;
                                attribute 'σ_Cx' : Real = 28.721044428837228;
                                attribute Cy : Real = -68.97324780002236;
                                attribute 'σ_Cy' : Real = 28.23690002309109;
                                attribute Cz : Real = 10.626331716775894;
                                attribute 'σ_Cz' : Real = 29.057750463592832;
                                attribute Ixx : Real = 1.3874784053624771;
                                attribute 'σ_Ixx' : Real = 0.37074144170588635;
                                attribute Iyy : Real = 1.307586360478764;
                                attribute 'σ_Iyy' : Real = 0.3723953238821935;
                                attribute Izz : Real = 1.256634479098342;
                                attribute 'σ_Izz' : Real = 0.37017423652493897;
                                attribute Ixy : Real = -0.13110482560099634;
                                attribute 'σ_Ixy' : Real = 0.02351283871158888;
                                attribute Ixz : Real = 0.04625486455079787;
                                attribute 'σ_Ixz' : Real = 0.022566176940390956;
                                attribute Iyz : Real = 0.016983430869299314;
                                attribute 'σ_Iyz' : Real = 0.02209918015384651;
                            }
                            part <'C.1.1.2.3.2.4.2'> 'Part 220' {
                                attribute POIconv : String = "+";
                                attribute Ipoint : Boolean = false;
                                attribute mass : Real = 0.5840093918405473;
                                attribute 'σ_mass' : Real = 0.28909372274994966;
                                attribute Cx : Real = 46.205307403579354;
                                attribute 'σ_Cx' : Real = 28.721044428837228;
                                attribute Cy : Real = -58.744016010314226;
                                attribute 'σ_Cy' : Real = 28.23690002309109;
                                attribute Cz : Real = 47.29798976331949;
                                attribute 'σ_Cz' : Real = 29.057750463592832;
                                attribute Ixx : Real = 0.7925765243026777;
                                attribute 'σ_Ixx' : Real = 0.37074144170588635;
                                attribute Iyy : Real = 0.837003196750336;
                                attribute 'σ_Iyy' : Real = 0.3723953238821935;
                                attribute Izz : Real = 0.7932874879269525;
                                attribute 'σ_Izz' : Real = 0.37017423652493897;
                                attribute Ixy : Real = -0.036248160328857026;
                                attribute 'σ_Ixy' : Real = 0.02351283871158888;
                                attribute Ixz : Real = -0.043563745725989436;
                                attribute 'σ_Ixz' : Real = 0.022566176940390956;
                                attribute Iyz : Real = -0.04072657822490108;
                                attribute 'σ_Iyz' : Real = 0.02209918015384651;
                            }
                            part <'C.1.1.2.3.2.4.3'> 'Part 221' {
                                attribute POIconv : String = "+";
                                attribute Ipoint : Boolean = false;
                                attribute mass : Real = 0.9989164593699388;
                                attribute 'σ_mass' : Real = 0.28909372274994966;
                                attribute Cx : Real = 90.2907453943044;
                                attribute 'σ_Cx' : Real = 28.721044428837228;
                                attribute Cy : Real = 46.59674004651606;
                                attribute 'σ_Cy' : Real = 28.23690002309109;
                                attribute Cz : Real = 69.82713281176984;
                                attribute 'σ_Cz' : Real = 29.057750463592832;
                                attribute Ixx : Real = 1.1095701631112358;
                                attribute 'σ_Ixx' : Real = 0.37074144170588635;
                                attribute Iyy : Real = 1.1100416041463839;
                                attribute 'σ_Iyy' : Real = 0.3723953238821935;
                                attribute Izz : Real = 1.112370446975694;
                                attribute 'σ_Izz' : Real = 0.37017423652493897;
                                attribute Ixy : Real = -0.017234259898404644;
                                attribute 'σ_Ixy' : Real = 0.02351283871158888;
                                attribute Ixz : Real = 0.018538264519253334;
                                attribute 'σ_Ixz' : Real = 0.022566176940390956;
                                attribute Iyz : Real = 0.01709519954696141;
                                attribute 'σ_Iyz' : Real = 0.02209918015384651;
                            }
                        }
                    }
                    part <'C.1.1.2.3.3'> 'Assembly 17' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.3.3.1'> 'Subassembly 64' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.3.1.1'> 'Part 222' {
                                attribute POIconv : String = "+";
                                attribute Ipoint : Boolean = false;
                                attribute mass : Real = 0.6981337218536064;
                                attribute 'σ_mass' : Real = 0.28909372274994966;
                                attribute Cx : Real = 67.63584432192147;
                                attribute 'σ_Cx' : Real = 28.721044428837228;
                                attribute Cy : Real = 73.54285116307437;
                                attribute 'σ_Cy' : Real = 28.23690002309109;
                                attribute Cz : Real = -92.03836084343493;
                                attribute 'σ_Cz' : Real = 29.057750463592832;
                                attribute Ixx : Real = 0.8445897074929012;
                                attribute 'σ_Ixx' : Real = 0.37074144170588635;
                                attribute Iyy : Real = 0.8524050803617161;
                                attribute 'σ_Iyy' : Real = 0.3723953238821935;
                                attribute Izz : Real = 0.8139248541718875;
                                attribute 'σ_Izz' : Real = 0.37017423652493897;
                                attribute Ixy : Real = -0.013188904285200972;
                                attribute 'σ_Ixy' : Real = 0.02351283871158888;
                                attribute Ixz : Real = 0.0015370608965754537;
                                attribute 'σ_Ixz' : Real = 0.022566176940390956;
                                attribute Iyz : Real = -0.06759867719942336;
                                attribute 'σ_Iyz' : Real = 0.02209918015384651;
                            }
                            part <'C.1.1.2.3.3.1.2'> 'Part 223' {
                                attribute POIconv : String = "+";
                                attribute Ipoint : Boolean = false;
                                attribute mass : Real = 0.9647084078663029;
                                attribute 'σ_mass' : Real = 0.28909372274994966;
                                attribute Cx : Real = 78.57757876627147;
                                attribute 'σ_Cx' : Real = 28.721044428837228;
                                attribute Cy : Real = -56.53379508294165;
                                attribute 'σ_Cy' : Real = 28.23690002309109;
                                attribute Cz : Real = 92.2572017647326;
                                attribute 'σ_Cz' : Real = 29.057750463592832;
                                attribute Ixx : Real = 1.119175687159004;
                                attribute 'σ_Ixx' : Real = 0.37074144170588635;
                                attribute Iyy : Real = 1.2611308568725628;
                                attribute 'σ_Iyy' : Real = 0.3723953238821935;
                                attribute Izz : Real = 1.0751581449878107;
                                attribute 'σ_Izz' : Real = 0.37017423652493897;
                                attribute Ixy : Real = -0.03904206589218167;
                                attribute 'σ_Ixy' : Real = 0.02351283871158888;
                                attribute Ixz : Real = 0.027826538221908642;
                                attribute 'σ_Ixz' : Real = 0.022566176940390956;
                                attribute Iyz : Real = 0.07962088554850537;
                                attribute 'σ_Iyz' : Real = 0.02209918015384651;
                            }
                            part <'C.1.1.2.3.3.1.3'> 'Part 224' {
                                attribute POIconv : String = "-";
                                attribute Ipoint : Boolean = false;
                                attribute mass : Real = 0.9123147654340137;
                                attribute 'σ_mass' : Real = 0.28909372274994966;
                                attribute Cx : Real = 25.994484685361385;
                                attribute 'σ_Cx' : Real = 28.721044428837228;
                                attribute Cy : Real = -59.17880036868155;
                                attribute 'σ_Cy' : Real = 28.23690002309109;
                                attribute Cz : Real = 75.86501985788345;
                                attribute 'σ_Cz' : Real = 29.057750463592832;
                                attribute Ixx : Real = 0.9567876611695977;
                                attribute 'σ_Ixx' : Real = 0.37074144170588635;
                                attribute Iyy : Real = 0.9558885021706184;
                                attribute 'σ_Iyy' : Real = 0.3723953238821935;
                                attribute Izz : Real = 0.8850765849763327;
                                attribute 'σ_Izz' : Real = 0.37017423652493897;
                                attribute Ixy : Real = 0.0030148245862326043;
                                attribute 'σ_Ixy' : Real = 0.02351283871158888;
                                attribute Ixz : Real = 0.03158207208613933;
                                attribute 'σ_Ixz' : Real = 0.022566176940390956;
                                attribute Iyz : Real = 0.01556459289111984;
                                attribute 'σ_Iyz' : Real = 0.02209918015384651;
                            }
                            part <'C.1.1.2.3.3.1.4'> 'Part 225' {
                                attribute POIconv : String = "+";
                                attribute Ipoint : Boolean = false;
                                attribute mass : Real = 0.9164974176930264;
                                attribute 'σ_mass' : Real = 0.28909372274994966;
                                attribute Cx : Real = 34.91646875627339;
                                attribute 'σ_Cx' : Real = 28.721044428837228;
                                attribute Cy : Real = 90.33616781234741;
                                attribute 'σ_Cy' : Real = 28.23690002309109;
                                attribute Cz : Real = 72.14552643708885;
                                attribute 'σ_Cz' : Real = 29.057750463592832;
                                attribute Ixx : Real = 1.1165697394666352;
                                attribute 'σ_Ixx' : Real = 0.37074144170588635;
                                attribute Iyy : Real = 1.1605305403015118;
                                attribute 'σ_Iyy' : Real = 0.3723953238821935;
                                attribute Izz : Real = 1.2445897060531552;
                                attribute 'σ_Izz' : Real = 0.37017423652493897;
                                attribute Ixy : Real = 0.05241478792559159;
                                attribute 'σ_Ixy' : Real = 0.02351283871158888;
                                attribute Ixz : Real = 0.07428953166550448;
                                attribute 'σ_Ixz' : Real = 0.022566176940390956;
                                attribute Iyz : Real = -0.11462705715255231;
                                attribute 'σ_Iyz' : Real = 0.02209918015384651;
                            }
                        }
                        part <'C.1.1.2.3.3.2'> 'Subassembly 65' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.3.2.1'> 'Part 226' {
                                attribute POIconv : String = "-";
                                attribute Ipoint : Boolean = false;
                                attribute mass : Real = 0.9521157774229069;
                                attribute 'σ_mass' : Real = 0.28909372274994966;
                                attribute Cx : Real = 27.95442072674632;
                                attribute 'σ_Cx' : Real = 28.721044428837228;
                                attribute Cy : Real = -17.813743744045496;
                                attribute 'σ_Cy' : Real = 28.23690002309109;
                                attribute Cz : Real = -96.69689703732729;
                                attribute 'σ_Cz' : Real = 29.057750463592832;
                                attribute Ixx : Real = 1.371600012959723;
                                attribute 'σ_Ixx' : Real = 0.37074144170588635;
                                attribute Iyy : Real = 1.2419443960559506;
                                attribute 'σ_Iyy' : Real = 0.3723953238821935;
                                attribute Izz : Real = 1.342665845706661;
                                attribute 'σ_Izz' : Real = 0.37017423652493897;
                                attribute Ixy : Real = -0.07520682467824574;
                                attribute 'σ_Ixy' : Real = 0.02351283871158888;
                                attribute Ixz : Real = -0.007326237124911683;
                                attribute 'σ_Ixz' : Real = 0.022566176940390956;
                                attribute Iyz : Real = 0.04274520311737465;
                                attribute 'σ_Iyz' : Real = 0.02209918015384651;
                            }
                            part <'C.1.1.2.3.3.2.2'> 'Part 227' {
                                attribute POIconv : String = "+";
                                attribute Ipoint : Boolean = false;
                                attribute mass : Real = 0.9317316875497345;
                                attribute 'σ_mass' : Real = 0.28909372274994966;
                                attribute Cx : Real = -51.0455621406436;
                                attribute 'σ_Cx' : Real = 28.721044428837228;
                                attribute Cy : Real = -4.449240770190954;
                                attribute 'σ_Cy' : Real = 28.23690002309109;
                                attribute Cz : Real = -37.096175737679005;
                                attribute 'σ_Cz' : Real = 29.057750463592832;
                                attribute Ixx : Real = 1.2477798228030526;
                                attribute 'σ_Ixx' : Real = 0.37074144170588635;
                                attribute Iyy : Real = 1.1724668222578458;
                                attribute 'σ_Iyy' : Real = 0.3723953238821935;
                                attribute Izz : Real = 1.2328642761254631;
                                attribute 'σ_Izz' : Real = 0.37017423652493897;
                                attribute Ixy : Real = 0.020919445093805503;
                                attribute 'σ_Ixy' : Real = 0.02351283871158888;
                                attribute Ixz : Real = 0.032715710235393367;
                                attribute 'σ_Ixz' : Real = 0.022566176940390956;
                                attribute Iyz : Real = 0.07338760775987871;
                                attribute 'σ_Iyz' : Real = 0.02209918015384651;
                            }
                            part <'C.1.1.2.3.3.2.3'> 'Part 228' {
                                attribute POIconv : String = "-";
                                attribute Ipoint : Boolean = false;
                                attribute mass : Real = 0.6940943061190191;
                                attribute 'σ_mass' : Real = 0.28909372274994966;
                                attribute Cx : Real = -54.334507742896676;
                                attribute 'σ_Cx' : Real = 28.721044428837228;
                                attribute Cy : Real = 87.44880226440728;
                                attribute 'σ_Cy' : Real = 28.23690002309109;
                                attribute Cz : Real = -52.77128373272717;
                                attribute 'σ_Cz' : Real = 29.057750463592832;
                                attribute Ixx : Real = 0.7778768636204603;
                                attribute 'σ_Ixx' : Real = 0.37074144170588635;
                                attribute Iyy : Real = 0.8285365676523015;
                                attribute 'σ_Iyy' : Real = 0.3723953238821935;
                                attribute Izz : Real = 0.786388175813045;
                                attribute 'σ_Izz' : Real = 0.37017423652493897;
                                attribute Ixy : Real = 0.042779019462823;
                                attribute 'σ_Ixy' : Real = 0.02351283871158888;
                                attribute Ixz : Real = 0.05916467742656986;
                                attribute 'σ_Ixz' : Real = 0.022566176940390956;
                                attribute Iyz : Real = -0.040436065287044694;
                                attribute 'σ_Iyz' : Real = 0.02209918015384651;
                            }
                            part <'C.1.1.2.3.3.2.4'> 'Part 229' {
                                attribute POIconv : String = "-";
                                attribute Ipoint : Boolean = false;
                                attribute mass : Real = 0.6398391010495834;
                                attribute 'σ_mass' : Real = 0.28909372274994966;
                                attribute Cx : Real = 98.3718675095588;
                                attribute 'σ_Cx' : Real = 28.721044428837228;
                                attribute Cy : Real = -42.11589437909424;
                                attribute 'σ_Cy' : Real = 28.23690002309109;
                                attribute Cz : Real = -80.6726023554802;
                                attribute 'σ_Cz' : Real = 29.057750463592832;
                                attribute Ixx : Real = 0.8736377868553544;
                                attribute 'σ_Ixx' : Real = 0.37074144170588635;
                                attribute Iyy : Real = 0.8523942566839732;
                                attribute 'σ_Iyy' : Real = 0.3723953238821935;
                                attribute Izz : Real = 0.8865886617287865;
                                attribute 'σ_Izz' : Real = 0.37017423652493897;
                                attribute Ixy : Real = 0.007195729646190966;
                                attribute 'σ_Ixy' : Real = 0.02351283871158888;
                                attribute Ixz : Real = 0.0664610558232108;
                                attribute 'σ_Ixz' : Real = 0.022566176940390956;
                                attribute Iyz : Real = 0.03868451980895579;
                                attribute 'σ_Iyz' : Real = 0.02209918015384651;
                            }
                        }
                        part <'C.1.1.2.3.3.3'> 'Subassembly 66' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.3.3.1'> 'Part 230' {
                                attribute POIconv : String = "+";
                                attribute Ipoint : Boolean = false;
                                attribute mass : Real = 0.4732876319605857;
                                attribute 'σ_mass' : Real = 0.28909372274994966;
                                attribute Cx : Real = -31.702012661844492;
                                attribute 'σ_Cx' : Real = 28.721044428837228;
                                attribute Cy : Real = -35.20986712537706;
                                attribute 'σ_Cy' : Real = 28.23690002309109;
                                attribute Cz : Real = -80.42764598503709;
                                attribute 'σ_Cz' : Real = 29.057750463592832;
                                attribute Ixx : Real = 0.5776282630512082;
                                attribute 'σ_Ixx' : Real = 0.37074144170588635;
                                attribute Iyy : Real = 0.612928435004331;
                                attribute 'σ_Iyy' : Real = 0.3723953238821935;
                                attribute Izz : Real = 0.657295392667476;
                                attribute 'σ_Izz' : Real = 0.37017423652493897;
                                attribute Ixy : Real = 0.047315951687357305;
                                attribute 'σ_Ixy' : Real = 0.02351283871158888;
                                attribute Ixz : Real = -0.020987713309808802;
                                attribute 'σ_Ixz' : Real = 0.022566176940390956;
                                attribute Iyz : Real = -0.025580359002634334;
                                attribute 'σ_Iyz' : Real = 0.02209918015384651;
                            }
                            part <'C.1.1.2.3.3.3.2'> 'Part 231' {
                                attribute POIconv : String = "+";
                                attribute Ipoint : Boolean = false;
                                attribute mass : Real = 0.5742559182213154;
                                attribute 'σ_mass' : Real = 0.28909372274994966;
                                attribute Cx : Real = -95.85042209364474;
                                attribute 'σ_Cx' : Real = 28.721044428837228;
                                attribute Cy : Real = -57.96284284442663;
                                attribute 'σ_Cy' : Real = 28.23690002309109;
                                attribute Cz : Real = 1.2327832635492086;
                                attribute 'σ_Cz' : Real = 29.057750463592832;
                                attribute Ixx : Real = 0.6094341659991354;
                                attribute 'σ_Ixx' : Real = 0.37074144170588635;
                                attribute Iyy : Real = 0.5918451796024123;
                                attribute 'σ_Iyy' : Real = 0.3723953238821935;
                                attribute Izz : Real = 0.5940358472508244;
                                attribute 'σ_Izz' : Real = 0.37017423652493897;
                                attribute Ixy : Real = -0.008256612516430856;
                                attribute 'σ_Ixy' : Real = 0.02351283871158888;
                                attribute Ixz : Real = -0.00900113820804338;
                                attribute 'σ_Ixz' : Real = 0.022566176940390956;
                                attribute Iyz : Real = -0.0053345997541966;
                                attribute 'σ_Iyz' : Real = 0.02209918015384651;
                            }
                        }
                        part <'C.1.1.2.3.3.4'> 'Subassembly 67' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.3.4.1'> 'Part 232' {
                                attribute POIconv : String = "-";
                                attribute Ipoint : Boolean = false;
                                attribute mass : Real = 0.04330555290146731;
                                attribute 'σ_mass' : Real = 0.28909372274994966;
                                attribute Cx : Real = -25.640655355527997;
                                attribute 'σ_Cx' : Real = 28.721044428837228;
                                attribute Cy : Real = -28.993777837604284;
                                attribute 'σ_Cy' : Real = 28.23690002309109;
                                attribute Cz : Real = 75.9551013354212;
                                attribute 'σ_Cz' : Real = 29.057750463592832;
                                attribute Ixx : Real = 0.043565605630665215;
                                attribute 'σ_Ixx' : Real = 0.37074144170588635;
                                attribute Iyy : Real = 0.048302207446119176;
                                attribute 'σ_Iyy' : Real = 0.3723953238821935;
                                attribute Izz : Real = 0.05053253801369557;
                                attribute 'σ_Izz' : Real = 0.37017423652493897;
                                attribute Ixy : Real = 0.0033737695972688793;
                                attribute 'σ_Ixy' : Real = 0.02351283871158888;
                                attribute Ixz : Real = -0.003095254732756547;
                                attribute 'σ_Ixz' : Real = 0.022566176940390956;
                                attribute Iyz : Real = -7.330748379831833e-4;
                                attribute 'σ_Iyz' : Real = 0.02209918015384651;
                            }
                            part <'C.1.1.2.3.3.4.2'> 'Part 233' {
                                attribute POIconv : String = "+";
                                attribute Ipoint : Boolean = false;
                                attribute mass : Real = 0.9409028713845182;
                                attribute 'σ_mass' : Real = 0.28909372274994966;
                                attribute Cx : Real = 54.69717029482126;
                                attribute 'σ_Cx' : Real = 28.721044428837228;
                                attribute Cy : Real = -13.32787531428039;
                                attribute 'σ_Cy' : Real = 28.23690002309109;
                                attribute Cz : Real = 55.245862528681755;
                                attribute 'σ_Cz' : Real = 29.057750463592832;
                                attribute Ixx : Real = 1.111065119286856;
                                attribute 'σ_Ixx' : Real = 0.37074144170588635;
                                attribute Iyy : Real = 1.2257314538222586;
                                attribute 'σ_Iyy' : Real = 0.3723953238821935;
                                attribute Izz : Real = 0.9732723834667619;
                                attribute 'σ_Izz' : Real = 0.37017423652493897;
                                attribute Ixy : Real = -0.05047023546156895;
                                attribute 'σ_Ixy' : Real = 0.02351283871158888;
                                attribute Ixz : Real = -0.0034150040870669952;
                                attribute 'σ_Ixz' : Real = 0.022566176940390956;
                                attribute Iyz : Real = -2.3428343943622182e-4;
                                attribute 'σ_Iyz' : Real = 0.02209918015384651;
                            }
                        }
                    }
                    part <'C.1.1.2.3.4'> 'Assembly 18' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.3.4.1'> 'Subassembly 68' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.4.1.1'> 'Part 234' {
                                attribute POIconv : String = "+";
                                attribute Ipoint : Boolean = false;
                                attribute mass : Real = 0.2811081306487322;
                                attribute 'σ_mass' : Real = 0.28909372274994966;
                                attribute Cx : Real = -27.522867592051625;
                                attribute 'σ_Cx' : Real = 28.721044428837228;
                                attribute Cy : Real = 59.66183729469776;
                                attribute 'σ_Cy' : Real = 28.23690002309109;
                                attribute Cz : Real = 19.088839506730437;
                                attribute 'σ_Cz' : Real = 29.057750463592832;
                                attribute Ixx : Real = 0.4283722611925715;
                                attribute 'σ_Ixx' : Real = 0.37074144170588635;
                                attribute Iyy : Real = 0.4406517655099938;
                                attribute 'σ_Iyy' : Real = 0.3723953238821935;
                                attribute Izz : Real = 0.4294795600464828;
                                attribute 'σ_Izz' : Real = 0.37017423652493897;
                                attribute Ixy : Real = 0.013364300055362094;
                                attribute 'σ_Ixy' : Real = 0.02351283871158888;
                                attribute Ixz : Real = 0.007087496858972354;
                                attribute 'σ_Ixz' : Real = 0.022566176940390956;
                                attribute Iyz : Real = -0.013233216165753982;
                                attribute 'σ_Iyz' : Real = 0.02209918015384651;
                            }
                            part <'C.1.1.2.3.4.1.2'> 'Part 235' {
                                attribute POIconv : String = "-";
                                attribute Ipoint : Boolean = false;
                                attribute mass : Real = 0.07347928326041438;
                                attribute 'σ_mass' : Real = 0.28909372274994966;
                                attribute Cx : Real = -94.68974452465773;
                                attribute 'σ_Cx' : Real = 28.721044428837228;
                                attribute Cy : Real = -51.4374659396708;
                                attribute 'σ_Cy' : Real = 28.23690002309109;
                                attribute Cz : Real = -27.355687180534005;
                                attribute 'σ_Cz' : Real = 29.057750463592832;
                                attribute Ixx : Real = 0.09184769553994289;
                                attribute 'σ_Ixx' : Real = 0.37074144170588635;
                                attribute Iyy : Real = 0.08356440776952441;
                                attribute 'σ_Iyy' : Real = 0.3723953238821935;
                                attribute Izz : Real = 0.0973344283336313;
                                attribute 'σ_Izz' : Real = 0.37017423652493897;
                                attribute Ixy : Real = 0.0017784309639501618;
                                attribute 'σ_Ixy' : Real = 0.02351283871158888;
                                attribute Ixz : Real = -0.001244502880692563;
                                attribute 'σ_Ixz' : Real = 0.022566176940390956;
                                attribute Iyz : Real = 0.004280943903010156;
                                attribute 'σ_Iyz' : Real = 0.02209918015384651;
                            }
                            part <'C.1.1.2.3.4.1.3'> 'Part 236' {
                                attribute POIconv : String = "-";
                                attribute Ipoint : Boolean = false;
                                attribute mass : Real = 0.862738692422863;
                                attribute 'σ_mass' : Real = 0.28909372274994966;
                                attribute Cx : Real = 94.40713622607291;
                                attribute 'σ_Cx' : Real = 28.721044428837228;
                                attribute Cy : Real = 68.24324573390186;
                                attribute 'σ_Cy' : Real = 28.23690002309109;
                                attribute Cz : Real = 99.64995072223246;
                                attribute 'σ_Cz' : Real = 29.057750463592832;
                                attribute Ixx : Real = 1.1817757892294176;
                                attribute 'σ_Ixx' : Real = 0.37074144170588635;
                                attribute Iyy : Real = 1.257720481406359;
                                attribute 'σ_Iyy' : Real = 0.3723953238821935;
                                attribute Izz : Real = 1.0375093898927759;
                                attribute 'σ_Izz' : Real = 0.37017423652493897;
                                attribute Ixy : Real = 0.03869749474441674;
                                attribute 'σ_Ixy' : Real = 0.02351283871158888;
                                attribute Ixz : Real = 0.0025811752327822715;
                                attribute 'σ_Ixz' : Real = 0.022566176940390956;
                                attribute Iyz : Real = 0.027866661974746687;
                                attribute 'σ_Iyz' : Real = 0.02209918015384651;
                            }
                            part <'C.1.1.2.3.4.1.4'> 'Part 237' {
                                attribute POIconv : String = "-";
                                attribute Ipoint : Boolean = false;
                                attribute mass : Real = 0.9244204802676104;
                                attribute 'σ_mass' : Real = 0.28909372274994966;
                                attribute Cx : Real = -93.82002893835306;
                                attribute 'σ_Cx' : Real = 28.721044428837228;
                                attribute Cy : Real = 28.217578772455454;
                                attribute 'σ_Cy' : Real = 28.23690002309109;
                                attribute Cz : Real = -48.54828384704888;
                                attribute 'σ_Cz' : Real = 29.057750463592832;
                                attribute Ixx : Real = 1.291964255238476;
                                attribute 'σ_Ixx' : Real = 0.37074144170588635;
                                attribute Iyy : Real = 1.2932585161554613;
                                attribute 'σ_Iyy' : Real = 0.3723953238821935;
                                attribute Izz : Real = 1.4997073295702223;
                                attribute 'σ_Izz' : Real = 0.37017423652493897;
                                attribute Ixy : Real = 0.006319896740008379;
                                attribute 'σ_Ixy' : Real = 0.02351283871158888;
                                attribute Ixz : Real = -0.06675934375577333;
                                attribute 'σ_Ixz' : Real = 0.022566176940390956;
                                attribute Iyz : Real = -0.02549416487631085;
                                attribute 'σ_Iyz' : Real = 0.02209918015384651;
                            }
                        }
                        part <'C.1.1.2.3.4.2'> 'Subassembly 69' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.4.2.1'> 'Part 238' {
                                attribute POIconv : String = "+";
                                attribute Ipoint : Boolean = false;
                                attribute mass : Real = 0.0019436514207627625;
                                attribute 'σ_mass' : Real = 0.28909372274994966;
                                attribute Cx : Real = -68.10006583109498;
                                attribute 'σ_Cx' : Real = 28.721044428837228;
                                attribute Cy : Real = 9.63552058674395;
                                attribute 'σ_Cy' : Real = 28.23690002309109;
                                attribute Cz : Real = 98.50059025920928;
                                attribute 'σ_Cz' : Real = 29.057750463592832;
                                attribute Ixx : Real = 0.002584144316889135;
                                attribute 'σ_Ixx' : Real = 0.37074144170588635;
                                attribute Iyy : Real = 0.002689371680209796;
                                attribute 'σ_Iyy' : Real = 0.3723953238821935;
                                attribute Izz : Real = 0.00271806309481121;
                                attribute 'σ_Izz' : Real = 0.37017423652493897;
                                attribute Ixy : Real = -8.529725864750898e-5;
                                attribute 'σ_Ixy' : Real = 0.02351283871158888;
                                attribute Ixz : Real = -3.44165367412081e-5;
                                attribute 'σ_Ixz' : Real = 0.022566176940390956;
                                attribute Iyz : Real = 5.08053796833044e-5;
                                attribute 'σ_Iyz' : Real = 0.02209918015384651;
                            }
                            part <'C.1.1.2.3.4.2.2'> 'Part 239' {
                                attribute POIconv : String = "+";
                                attribute Ipoint : Boolean = false;
                                attribute mass : Real = 0.9790661035573576;
                                attribute 'σ_mass' : Real = 0.28909372274994966;
                                attribute Cx : Real = -73.9092618227005;
                                attribute 'σ_Cx' : Real = 28.721044428837228;
                                attribute Cy : Real = 88.23915966786444;
                                attribute 'σ_Cy' : Real = 28.23690002309109;
                                attribute Cz : Real = 3.864906867966056;
                                attribute 'σ_Cz' : Real = 29.057750463592832;
                                attribute Ixx : Real = 1.2407586676459126;
                                attribute 'σ_Ixx' : Real = 0.37074144170588635;
                                attribute Iyy : Real = 1.2054609125229616;
                                attribute 'σ_Iyy' : Real = 0.3723953238821935;
                                attribute Izz : Real = 1.275079346344032;
                                attribute 'σ_Izz' : Real = 0.37017423652493897;
                                attribute Ixy : Real = -0.036854777886873635;
                                attribute 'σ_Ixy' : Real = 0.02351283871158888;
                                attribute Ixz : Real = 0.061095103961103514;
                                attribute 'σ_Ixz' : Real = 0.022566176940390956;
                                attribute Iyz : Real = 0.07972386482844457;
                                attribute 'σ_Iyz' : Real = 0.02209918015384651;
                            }
                            part <'C.1.1.2.3.4.2.3'> 'Part 240' {
                                attribute POIconv : String = "-";
                                attribute Ipoint : Boolean = false;
                                attribute mass : Real = 0.2003024841635488;
                                attribute 'σ_mass' : Real = 0.28909372274994966;
                                attribute Cx : Real = -93.90502953901887;
                                attribute 'σ_Cx' : Real = 28.721044428837228;
                                attribute Cy : Real = 34.372543124482036;
                                attribute 'σ_Cy' : Real = 28.23690002309109;
                                attribute Cz : Real = 49.69749189913273;
                                attribute 'σ_Cz' : Real = 29.057750463592832;
                                attribute Ixx : Real = 0.28662027833267745;
                                attribute 'σ_Ixx' : Real = 0.37074144170588635;
                                attribute Iyy : Real = 0.29221896998465985;
                                attribute 'σ_Iyy' : Real = 0.3723953238821935;
                                attribute Izz : Real = 0.2688814984333837;
                                attribute 'σ_Izz' : Real = 0.37017423652493897;
                                attribute Ixy : Real = 0.012961118038136304;
                                attribute 'σ_Ixy' : Real = 0.02351283871158888;
                                attribute Ixz : Real = 0.001663460913538437;
                                attribute 'σ_Ixz' : Real = 0.022566176940390956;
                                attribute Iyz : Real = 0.001974934410863552;
                                attribute 'σ_Iyz' : Real = 0.02209918015384651;
                            }
                        }
                    }
                    part <'C.1.1.2.3.5'> 'Assembly 19' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.2.3.5.1'> 'Subassembly 70' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.5.1.1'> 'Part 241' {
                                attribute POIconv : String = "-";
                                attribute Ipoint : Boolean = false;
                                attribute mass : Real = 0.40747015800722874;
                                attribute 'σ_mass' : Real = 0.28909372274994966;
                                attribute Cx : Real = 60.78723571263254;
                                attribute 'σ_Cx' : Real = 28.721044428837228;
                                attribute Cy : Real = 32.55494451150298;
                                attribute 'σ_Cy' : Real = 28.23690002309109;
                                attribute Cz : Real = -21.33576483465731;
                                attribute 'σ_Cz' : Real = 29.057750463592832;
                                attribute Ixx : Real = 0.4791398664944725;
                                attribute 'σ_Ixx' : Real = 0.37074144170588635;
                                attribute Iyy : Real = 0.4639180009684186;
                                attribute 'σ_Iyy' : Real = 0.3723953238821935;
                                attribute Izz : Real = 0.4648673295844197;
                                attribute 'σ_Izz' : Real = 0.37017423652493897;
                                attribute Ixy : Real = 0.026220854424162734;
                                attribute 'σ_Ixy' : Real = 0.02351283871158888;
                                attribute Ixz : Real = 0.031630515653453;
                                attribute 'σ_Ixz' : Real = 0.022566176940390956;
                                attribute Iyz : Real = 0.012390263391158172;
                                attribute 'σ_Iyz' : Real = 0.02209918015384651;
                            }
                            part <'C.1.1.2.3.5.1.2'> 'Part 242' {
                                attribute POIconv : String = "+";
                                attribute Ipoint : Boolean = false;
                                attribute mass : Real = 0.2652896823133342;
                                attribute 'σ_mass' : Real = 0.28909372274994966;
                                attribute Cx : Real = 63.52602634578943;
                                attribute 'σ_Cx' : Real = 28.721044428837228;
                                attribute Cy : Real = -85.54996876046062;
                                attribute 'σ_Cy' : Real = 28.23690002309109;
                                attribute Cz : Real = 13.051589811220765;
                                attribute 'σ_Cz' : Real = 29.057750463592832;
                                attribute Ixx : Real = 0.3076657600595202;
                                attribute 'σ_Ixx' : Real = 0.37074144170588635;
                                attribute Iyy : Real = 0.2772827945777175;
                                attribute 'σ_Iyy' : Real = 0.3723953238821935;
                                attribute Izz : Real = 0.32772355994094815;
                                attribute 'σ_Izz' : Real = 0.37017423652493897;
                                attribute Ixy : Real = 0.007565802376756121;
                                attribute 'σ_Ixy' : Real = 0.02351283871158888;
                                attribute Ixz : Real = 0.003281872609789513;
                                attribute 'σ_Ixz' : Real = 0.022566176940390956;
                                attribute Iyz : Real = 5.56871355465161e-4;
                                attribute 'σ_Iyz' : Real = 0.02209918015384651;
                            }
                        }
                        part <'C.1.1.2.3.5.2'> 'Subassembly 71' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.5.2.1'> 'Part 243' {
                                attribute POIconv : String = "-";
                                attribute Ipoint : Boolean = false;
                                attribute mass : Real = 0.6740902617666871;
                                attribute 'σ_mass' : Real = 0.28909372274994966;
                                attribute Cx : Real = 6.337791075929999;
                                attribute 'σ_Cx' : Real = 28.721044428837228;
                                attribute Cy : Real = -39.97856080532074;
                                attribute 'σ_Cy' : Real = 28.23690002309109;
                                attribute Cz : Real = -41.56942963600159;
                                attribute 'σ_Cz' : Real = 29.057750463592832;
                                attribute Ixx : Real = 0.9120442700703385;
                                attribute 'σ_Ixx' : Real = 0.37074144170588635;
                                attribute Iyy : Real = 0.8352067696535924;
                                attribute 'σ_Iyy' : Real = 0.3723953238821935;
                                attribute Izz : Real = 0.8566534960006296;
                                attribute 'σ_Izz' : Real = 0.37017423652493897;
                                attribute Ixy : Real = 0.10909237505333497;
                                attribute 'σ_Ixy' : Real = 0.02351283871158888;
                                attribute Ixz : Real = -0.07060637082347898;
                                attribute 'σ_Ixz' : Real = 0.022566176940390956;
                                attribute Iyz : Real = -0.0173487109896762;
                                attribute 'σ_Iyz' : Real = 0.02209918015384651;
                            }
                            part <'C.1.1.2.3.5.2.2'> 'Part 244' {
                                attribute POIconv : String = "+";
                                attribute Ipoint : Boolean = false;
                                attribute mass : Real = 0.5944403135681059;
                                attribute 'σ_mass' : Real = 0.28909372274994966;
                                attribute Cx : Real = 66.01294544525445;
                                attribute 'σ_Cx' : Real = 28.721044428837228;
                                attribute Cy : Real = -69.33551244437695;
                                attribute 'σ_Cy' : Real = 28.23690002309109;
                                attribute Cz : Real = -38.90138026326895;
                                attribute 'σ_Cz' : Real = 29.057750463592832;
                                attribute Ixx : Real = 0.6950740749304091;
                                attribute 'σ_Ixx' : Real = 0.37074144170588635;
                                attribute Iyy : Real = 0.7852348276637291;
                                attribute 'σ_Iyy' : Real = 0.3723953238821935;
                                attribute Izz : Real = 0.6884946302404884;
                                attribute 'σ_Izz' : Real = 0.37017423652493897;
                                attribute Ixy : Real = 0.04391105620897433;
                                attribute 'σ_Ixy' : Real = 0.02351283871158888;
                                attribute Ixz : Real = 0.0010093464096753483;
                                attribute 'σ_Ixz' : Real = 0.022566176940390956;
                                attribute Iyz : Real = 0.047806464977739126;
                                attribute 'σ_Iyz' : Real = 0.02209918015384651;
                            }
                            part <'C.1.1.2.3.5.2.3'> 'Part 245' {
                                attribute POIconv : String = "+";
                                attribute Ipoint : Boolean = false;
                                attribute mass : Real = 0.5960659829464275;
                                attribute 'σ_mass' : Real = 0.28909372274994966;
                                attribute Cx : Real = 4.4589875265955925;
                                attribute 'σ_Cx' : Real = 28.721044428837228;
                                attribute Cy : Real = 48.273782432079315;
                                attribute 'σ_Cy' : Real = 28.23690002309109;
                                attribute Cz : Real = 16.500426270067692;
                                attribute 'σ_Cz' : Real = 29.057750463592832;
                                attribute Ixx : Real = 0.7515715892082144;
                                attribute 'σ_Ixx' : Real = 0.37074144170588635;
                                attribute Iyy : Real = 0.7149020029049378;
                                attribute 'σ_Iyy' : Real = 0.3723953238821935;
                                attribute Izz : Real = 0.6442586150956495;
                                attribute 'σ_Izz' : Real = 0.37017423652493897;
                                attribute Ixy : Real = -0.012609304131748197;
                                attribute 'σ_Ixy' : Real = 0.02351283871158888;
                                attribute Ixz : Real = -0.027343461633190867;
                                attribute 'σ_Ixz' : Real = 0.022566176940390956;
                                attribute Iyz : Real = 0.06778020234732142;
                                attribute 'σ_Iyz' : Real = 0.02209918015384651;
                            }
                        }
                        part <'C.1.1.2.3.5.3'> 'Subassembly 72' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.5.3.1'> 'Part 246' {
                                attribute POIconv : String = "-";
                                attribute Ipoint : Boolean = false;
                                attribute mass : Real = 0.426708983233897;
                                attribute 'σ_mass' : Real = 0.28909372274994966;
                                attribute Cx : Real = 54.957071831449866;
                                attribute 'σ_Cx' : Real = 28.721044428837228;
                                attribute Cy : Real = -26.894796872511506;
                                attribute 'σ_Cy' : Real = 28.23690002309109;
                                attribute Cz : Real = 40.740666817873716;
                                attribute 'σ_Cz' : Real = 29.057750463592832;
                                attribute Ixx : Real = 0.5666966112309123;
                                attribute 'σ_Ixx' : Real = 0.37074144170588635;
                                attribute Iyy : Real = 0.45225350431721256;
                                attribute 'σ_Iyy' : Real = 0.3723953238821935;
                                attribute Izz : Real = 0.5075383730044312;
                                attribute 'σ_Izz' : Real = 0.37017423652493897;
                                attribute Ixy : Real = 0.03395526593589006;
                                attribute 'σ_Ixy' : Real = 0.02351283871158888;
                                attribute Ixz : Real = -0.0037670822160265614;
                                attribute 'σ_Ixz' : Real = 0.022566176940390956;
                                attribute Iyz : Real = -0.024623832317804326;
                                attribute 'σ_Iyz' : Real = 0.02209918015384651;
                            }
                            part <'C.1.1.2.3.5.3.2'> 'Part 247' {
                                attribute POIconv : String = "-";
                                attribute Ipoint : Boolean = false;
                                attribute mass : Real = 0.03967274279939011;
                                attribute 'σ_mass' : Real = 0.28909372274994966;
                                attribute Cx : Real = -86.93004208616912;
                                attribute 'σ_Cx' : Real = 28.721044428837228;
                                attribute Cy : Real = -4.279834823682904;
                                attribute 'σ_Cy' : Real = 28.23690002309109;
                                attribute Cz : Real = -92.0446497388184;
                                attribute 'σ_Cz' : Real = 29.057750463592832;
                                attribute Ixx : Real = 0.052361918914424724;
                                attribute 'σ_Ixx' : Real = 0.37074144170588635;
                                attribute Iyy : Real = 0.05453069445344211;
                                attribute 'σ_Iyy' : Real = 0.3723953238821935;
                                attribute Izz : Real = 0.05101928682565523;
                                attribute 'σ_Izz' : Real = 0.37017423652493897;
                                attribute Ixy : Real = -6.893305535136083e-4;
                                attribute 'σ_Ixy' : Real = 0.02351283871158888;
                                attribute Ixz : Real = -1.8528774769578868e-4;
                                attribute 'σ_Ixz' : Real = 0.022566176940390956;
                                attribute Iyz : Real = 1.2095919189205661e-4;
                                attribute 'σ_Iyz' : Real = 0.02209918015384651;
                            }
                            part <'C.1.1.2.3.5.3.3'> 'Part 248' {
                                attribute POIconv : String = "+";
                                attribute Ipoint : Boolean = false;
                                attribute mass : Real = 0.28528343165386466;
                                attribute 'σ_mass' : Real = 0.28909372274994966;
                                attribute Cx : Real = 13.421092322096229;
                                attribute 'σ_Cx' : Real = 28.721044428837228;
                                attribute Cy : Real = 3.1691616401076317;
                                attribute 'σ_Cy' : Real = 28.23690002309109;
                                attribute Cz : Real = 67.5136974081397;
                                attribute 'σ_Cz' : Real = 29.057750463592832;
                                attribute Ixx : Real = 0.27782003406544536;
                                attribute 'σ_Ixx' : Real = 0.37074144170588635;
                                attribute Iyy : Real = 0.36603044168395876;
                                attribute 'σ_Iyy' : Real = 0.3723953238821935;
                                attribute Izz : Real = 0.375824505232686;
                                attribute 'σ_Izz' : Real = 0.37017423652493897;
                                attribute Ixy : Real = -0.001901370304835307;
                                attribute 'σ_Ixy' : Real = 0.02351283871158888;
                                attribute Ixz : Real = 0.002387921735145522;
                                attribute 'σ_Ixz' : Real = 0.022566176940390956;
                                attribute Iyz : Real = -0.015419167725190856;
                                attribute 'σ_Iyz' : Real = 0.02209918015384651;
                            }
                            part <'C.1.1.2.3.5.3.4'> 'Part 249' {
                                attribute POIconv : String = "+";
                                attribute Ipoint : Boolean = false;
                                attribute mass : Real = 0.7154089570406359;
                                attribute 'σ_mass' : Real = 0.28909372274994966;
                                attribute Cx : Real = 65.5456108506769;
                                attribute 'σ_Cx' : Real = 28.721044428837228;
                                attribute Cy : Real = 3.2566203270107508;
                                attribute 'σ_Cy' : Real = 28.23690002309109;
                                attribute Cz : Real = -69.9621846433729;
                                attribute 'σ_Cz' : Real = 29.057750463592832;
                                attribute Ixx : Real = 0.8590745322381049;
                                attribute 'σ_Ixx' : Real = 0.37074144170588635;
                                attribute Iyy : Real = 0.8258846949842853;
                                attribute 'σ_Iyy' : Real = 0.3723953238821935;
                                attribute Izz : Real = 0.9410905476130074;
                                attribute 'σ_Izz' : Real = 0.37017423652493897;
                                attribute Ixy : Real = -0.03242001221496807;
                                attribute 'σ_Ixy' : Real = 0.02351283871158888;
                                attribute Ixz : Real = 0.005518777833620126;
                                attribute 'σ_Ixz' : Real = 0.022566176940390956;
                                attribute Iyz : Real = -0.006471231020192947;
                                attribute 'σ_Iyz' : Real = 0.02209918015384651;
                            }
                            part <'C.1.1.2.3.5.3.5'> 'Part 250' {
                                attribute POIconv : String = "+";
                                attribute Ipoint : Boolean = false;
                                attribute mass : Real = 0.46728085903218014;
                                attribute 'σ_mass' : Real = 0.28909372274994966;
                                attribute Cx : Real = -42.38130250014365;
                                attribute 'σ_Cx' : Real = 28.721044428837228;
                                attribute Cy : Real = 91.84238146990538;
                                attribute 'σ_Cy' : Real = 28.23690002309109;
                                attribute Cz : Real = 45.81987471319735;
                                attribute 'σ_Cz' : Real = 29.057750463592832;
                                attribute Ixx : Real = 0.6514667621166179;
                                attribute 'σ_Ixx' : Real = 0.37074144170588635;
                                attribute Iyy : Real = 0.6869592564301479;
                                attribute 'σ_Iyy' : Real = 0.3723953238821935;
                                attribute Izz : Real = 0.6054931263830541;
                                attribute 'σ_Izz' : Real = 0.37017423652493897;
                                attribute Ixy : Real = -0.03015966653876525;
                                attribute 'σ_Ixy' : Real = 0.02351283871158888;
                                attribute Ixz : Real = -0.024446808654346737;
                                attribute 'σ_Ixz' : Real = 0.022566176940390956;
                                attribute Iyz : Real = -0.003821265151584969;
                                attribute 'σ_Iyz' : Real = 0.02209918015384651;
                            }
                        }
                        part <'C.1.1.2.3.5.4'> 'Subassembly 73' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.2.3.5.4.1'> 'Part 251' {
                                attribute POIconv : String = "-";
                                attribute Ipoint : Boolean = false;
                                attribute mass : Real = 0.7736773352290038;
                                attribute 'σ_mass' : Real = 0.28909372274994966;
                                attribute Cx : Real = 55.44500448741019;
                                attribute 'σ_Cx' : Real = 28.721044428837228;
                                attribute Cy : Real = -67.89552294649184;
                                attribute 'σ_Cy' : Real = 28.23690002309109;
                                attribute Cz : Real = 81.51691113598645;
                                attribute 'σ_Cz' : Real = 29.057750463592832;
                                attribute Ixx : Real = 0.9450998219769743;
                                attribute 'σ_Ixx' : Real = 0.37074144170588635;
                                attribute Iyy : Real = 0.9361747651469021;
                                attribute 'σ_Iyy' : Real = 0.3723953238821935;
                                attribute Izz : Real = 0.9812421124642215;
                                attribute 'σ_Izz' : Real = 0.37017423652493897;
                                attribute Ixy : Real = -0.034573533211430515;
                                attribute 'σ_Ixy' : Real = 0.02351283871158888;
                                attribute Ixz : Real = -0.05875326049368346;
                                attribute 'σ_Ixz' : Real = 0.022566176940390956;
                                attribute Iyz : Real = 0.0049728838083378775;
                                attribute 'σ_Iyz' : Real = 0.02209918015384651;
                            }
                            part <'C.1.1.2.3.5.4.2'> 'Part 252' {
                                attribute POIconv : String = "-";
                                attribute Ipoint : Boolean = false;
                                attribute mass : Real = 0.8191817951533013;
                                attribute 'σ_mass' : Real = 0.28909372274994966;
                                attribute Cx : Real = -99.47413657791913;
                                attribute 'σ_Cx' : Real = 28.721044428837228;
                                attribute Cy : Real = -79.58079921081662;
                                attribute 'σ_Cy' : Real = 28.23690002309109;
                                attribute Cz : Real = 69.34396345168352;
                                attribute 'σ_Cz' : Real = 29.057750463592832;
                                attribute Ixx : Real = 1.0165200114908017;
                                attribute 'σ_Ixx' : Real = 0.37074144170588635;
                                attribute Iyy : Real = 0.8619024267732524;
                                attribute 'σ_Iyy' : Real = 0.3723953238821935;
                                attribute Izz : Real = 0.9045909438979252;
                                attribute 'σ_Izz' : Real = 0.37017423652493897;
                                attribute Ixy : Real = -0.04499799537123948;
                                attribute 'σ_Ixy' : Real = 0.02351283871158888;
                                attribute Ixz : Real = 0.05661484550008761;
                                attribute 'σ_Ixz' : Real = 0.022566176940390956;
                                attribute Iyz : Real = 0.050151234001809805;
                                attribute 'σ_Iyz' : Real = 0.02209918015384651;
                            }
                        }
                    }
                }
            }
            part <'C.1.1.3'> 'Element 3' {
                attribute POIconv : String = "-";
                attribute Ipoint : Boolean;
                attribute mass : Real;
                attribute 'σ_mass' : Real;
                attribute Cx : Real;
                attribute 'σ_Cx' : Real;
                attribute Cy : Real;
                attribute 'σ_Cy' : Real;
                attribute Cz : Real;
                attribute 'σ_Cz' : Real;
                attribute Ixx : Real;
                attribute 'σ_Ixx' : Real;
                attribute Iyy : Real;
                attribute 'σ_Iyy' : Real;
                attribute Izz : Real;
                attribute 'σ_Izz' : Real;
                attribute Ixy : Real;
                attribute 'σ_Ixy' : Real;
                attribute Ixz : Real;
                attribute 'σ_Ixz' : Real;
                attribute Iyz : Real;
                attribute 'σ_Iyz' : Real;
                part <'C.1.1.3.1'> 'Subsystem 6' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.3.1.1'> 'Assembly 20' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.1.1.1'> 'Subassembly 74' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.1.1.1.1'> 'Part 253' {
                                attribute POIconv : String = "+";
                                attribute Ipoint : Boolean = false;
                                attribute mass : Real = 0.35033208354143425;
                                attribute 'σ_mass' : Real = 0.28909372274994966;
                                attribute Cx : Real = 13.602188974618912;
                                attribute 'σ_Cx' : Real = 28.721044428837228;
                                attribute Cy : Real = -65.77278128825128;
                                attribute 'σ_Cy' : Real = 28.23690002309109;
                                attribute Cz : Real = -6.666752602905035;
                                attribute 'σ_Cz' : Real = 29.057750463592832;
                                attribute Ixx : Real = 0.3451315091971734;
                                attribute 'σ_Ixx' : Real = 0.37074144170588635;
                                attribute Iyy : Real = 0.37349270270549456;
                                attribute 'σ_Iyy' : Real = 0.3723953238821935;
                                attribute Izz : Real = 0.36684707891031126;
                                attribute 'σ_Izz' : Real = 0.37017423652493897;
                                attribute Ixy : Real = 0.002415436040320097;
                                attribute 'σ_Ixy' : Real = 0.02351283871158888;
                                attribute Ixz : Real = -0.027704416596818528;
                                attribute 'σ_Ixz' : Real = 0.022566176940390956;
                                attribute Iyz : Real = -0.009512960607667983;
                                attribute 'σ_Iyz' : Real = 0.02209918015384651;
                            }
                            part <'C.1.1.3.1.1.1.2'> 'Part 254' {
                                attribute POIconv : String = "+";
                                attribute Ipoint : Boolean = false;
                                attribute mass : Real = 0.37120659729721955;
                                attribute 'σ_mass' : Real = 0.28909372274994966;
                                attribute Cx : Real = -62.285100715234876;
                                attribute 'σ_Cx' : Real = 28.721044428837228;
                                attribute Cy : Real = 57.06980703398585;
                                attribute 'σ_Cy' : Real = 28.23690002309109;
                                attribute Cz : Real = -43.37607226334512;
                                attribute 'σ_Cz' : Real = 29.057750463592832;
                                attribute Ixx : Real = 0.49607162528760934;
                                attribute 'σ_Ixx' : Real = 0.37074144170588635;
                                attribute Iyy : Real = 0.4775353950779882;
                                attribute 'σ_Iyy' : Real = 0.3723953238821935;
                                attribute Izz : Real = 0.4539264988517809;
                                attribute 'σ_Izz' : Real = 0.37017423652493897;
                                attribute Ixy : Real = -0.005497845660090447;
                                attribute 'σ_Ixy' : Real = 0.02351283871158888;
                                attribute Ixz : Real = 0.017209049791670917;
                                attribute 'σ_Ixz' : Real = 0.022566176940390956;
                                attribute Iyz : Real = -0.02672127156081648;
                                attribute 'σ_Iyz' : Real = 0.02209918015384651;
                            }
                            part <'C.1.1.3.1.1.1.3'> 'Part 255' {
                                attribute POIconv : String = "+";
                                attribute Ipoint : Boolean = false;
                                attribute mass : Real = 0.6543512409906834;
                                attribute 'σ_mass' : Real = 0.28909372274994966;
                                attribute Cx : Real = -51.047305250540376;
                                attribute 'σ_Cx' : Real = 28.721044428837228;
                                attribute Cy : Real = 64.39496669918299;
                                attribute 'σ_Cy' : Real = 28.23690002309109;
                                attribute Cz : Real = -63.441044837236404;
                                attribute 'σ_Cz' : Real = 29.057750463592832;
                                attribute Ixx : Real = 0.7911021543726762;
                                attribute 'σ_Ixx' : Real = 0.37074144170588635;
                                attribute Iyy : Real = 0.7677910643895419;
                                attribute 'σ_Iyy' : Real = 0.3723953238821935;
                                attribute Izz : Real = 0.7822651732118955;
                                attribute 'σ_Izz' : Real = 0.37017423652493897;
                                attribute Ixy : Real = 0.05353398171293455;
                                attribute 'σ_Ixy' : Real = 0.02351283871158888;
                                attribute Ixz : Real = -0.022248246027141726;
                                attribute 'σ_Ixz' : Real = 0.022566176940390956;
                                attribute Iyz : Real = 0.05630771579297367;
                                attribute 'σ_Iyz' : Real = 0.02209918015384651;
                            }
                            part <'C.1.1.3.1.1.1.4'> 'Part 256' {
                                attribute POIconv : String = "+";
                                attribute Ipoint : Boolean = false;
                                attribute mass : Real = 0.9333964975576382;
                                attribute 'σ_mass' : Real = 0.28909372274994966;
                                attribute Cx : Real = 83.1282596103847;
                                attribute 'σ_Cx' : Real = 28.721044428837228;
                                attribute Cy : Real = 60.246955370530486;
                                attribute 'σ_Cy' : Real = 28.23690002309109;
                                attribute Cz : Real = 80.36078028380871;
                                attribute 'σ_Cz' : Real = 29.057750463592832;
                                attribute Ixx : Real = 1.1941203888105794;
                                attribute 'σ_Ixx' : Real = 0.37074144170588635;
                                attribute Iyy : Real = 0.9467571635607344;
                                attribute 'σ_Iyy' : Real = 0.3723953238821935;
                                attribute Izz : Real = 1.2086177127420223;
                                attribute 'σ_Izz' : Real = 0.37017423652493897;
                                attribute Ixy : Real = -0.10079783510275;
                                attribute 'σ_Ixy' : Real = 0.02351283871158888;
                                attribute Ixz : Real = 0.011651422040814175;
                                attribute 'σ_Ixz' : Real = 0.022566176940390956;
                                attribute Iyz : Real = -0.06477818727760966;
                                attribute 'σ_Iyz' : Real = 0.02209918015384651;
                            }
                            part <'C.1.1.3.1.1.1.5'> 'Part 257' {
                                attribute POIconv : String = "+";
                                attribute Ipoint : Boolean = false;
                                attribute mass : Real = 0.3324100978076458;
                                attribute 'σ_mass' : Real = 0.28909372274994966;
                                attribute Cx : Real = 8.922457927837968;
                                attribute 'σ_Cx' : Real = 28.721044428837228;
                                attribute Cy : Real = -24.73820853047073;
                                attribute 'σ_Cy' : Real = 28.23690002309109;
                                attribute Cz : Real = 6.15625623613596;
                                attribute 'σ_Cz' : Real = 29.057750463592832;
                                attribute Ixx : Real = 0.4767158223678171;
                                attribute 'σ_Ixx' : Real = 0.37074144170588635;
                                attribute Iyy : Real = 0.4287285618635684;
                                attribute 'σ_Iyy' : Real = 0.3723953238821935;
                                attribute Izz : Real = 0.4339084575214057;
                                attribute 'σ_Izz' : Real = 0.37017423652493897;
                                attribute Ixy : Real = 0.006328744820123114;
                                attribute 'σ_Ixy' : Real = 0.02351283871158888;
                                attribute Ixz : Real = 0.01758982153966447;
                                attribute 'σ_Ixz' : Real = 0.022566176940390956;
                                attribute Iyz : Real = -0.02893292084444509;
                                attribute 'σ_Iyz' : Real = 0.02209918015384651;
                            }
                        }
                        part <'C.1.1.3.1.1.2'> 'Subassembly 75' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.1.1.2.1'> 'Part 258' {
                                attribute POIconv : String = "-";
                                attribute Ipoint : Boolean = false;
                                attribute mass : Real = 0.9713401052930858;
                                attribute 'σ_mass' : Real = 0.28909372274994966;
                                attribute Cx : Real = 11.97202461771667;
                                attribute 'σ_Cx' : Real = 28.721044428837228;
                                attribute Cy : Real = 19.448707485571504;
                                attribute 'σ_Cy' : Real = 28.23690002309109;
                                attribute Cz : Real = -68.73131752945483;
                                attribute 'σ_Cz' : Real = 29.057750463592832;
                                attribute Ixx : Real = 1.030563715857309;
                                attribute 'σ_Ixx' : Real = 0.37074144170588635;
                                attribute Iyy : Real = 1.0010890770162502;
                                attribute 'σ_Iyy' : Real = 0.3723953238821935;
                                attribute Izz : Real = 1.147349795278835;
                                attribute 'σ_Izz' : Real = 0.37017423652493897;
                                attribute Ixy : Real = 0.030591710421028935;
                                attribute 'σ_Ixy' : Real = 0.02351283871158888;
                                attribute Ixz : Real = -0.0042139216655627115;
                                attribute 'σ_Ixz' : Real = 0.022566176940390956;
                                attribute Iyz : Real = 0.040984992218540586;
                                attribute 'σ_Iyz' : Real = 0.02209918015384651;
                            }
                            part <'C.1.1.3.1.1.2.2'> 'Part 259' {
                                attribute POIconv : String = "+";
                                attribute Ipoint : Boolean = false;
                                attribute mass : Real = 0.6721225370683241;
                                attribute 'σ_mass' : Real = 0.28909372274994966;
                                attribute Cx : Real = -55.15542821958661;
                                attribute 'σ_Cx' : Real = 28.721044428837228;
                                attribute Cy : Real = 68.07067100889981;
                                attribute 'σ_Cy' : Real = 28.23690002309109;
                                attribute Cz : Real = 75.01546856947243;
                                attribute 'σ_Cz' : Real = 29.057750463592832;
                                attribute Ixx : Real = 0.6224034653634422;
                                attribute 'σ_Ixx' : Real = 0.37074144170588635;
                                attribute Iyy : Real = 0.6288802860472109;
                                attribute 'σ_Iyy' : Real = 0.3723953238821935;
                                attribute Izz : Real = 0.6216715156389743;
                                attribute 'σ_Izz' : Real = 0.37017423652493897;
                                attribute Ixy : Real = -0.002980722553823145;
                                attribute 'σ_Ixy' : Real = 0.02351283871158888;
                                attribute Ixz : Real = 0.0012678343995902587;
                                attribute 'σ_Ixz' : Real = 0.022566176940390956;
                                attribute Iyz : Real = -0.012983322297216344;
                                attribute 'σ_Iyz' : Real = 0.02209918015384651;
                            }
                            part <'C.1.1.3.1.1.2.3'> 'Part 260' {
                                attribute POIconv : String = "+";
                                attribute Ipoint : Boolean = false;
                                attribute mass : Real = 0.4500112885322887;
                                attribute 'σ_mass' : Real = 0.28909372274994966;
                                attribute Cx : Real = -35.49824417568743;
                                attribute 'σ_Cx' : Real = 28.721044428837228;
                                attribute Cy : Real = 91.78482885472476;
                                attribute 'σ_Cy' : Real = 28.23690002309109;
                                attribute Cz : Real = -75.32815379090607;
                                attribute 'σ_Cz' : Real = 29.057750463592832;
                                attribute Ixx : Real = 0.568529815188794;
                                attribute 'σ_Ixx' : Real = 0.37074144170588635;
                                attribute Iyy : Real = 0.5043313559220088;
                                attribute 'σ_Iyy' : Real = 0.3723953238821935;
                                attribute Izz : Real = 0.5860855112191878;
                                attribute 'σ_Izz' : Real = 0.37017423652493897;
                                attribute Ixy : Real = 0.023967253528599523;
                                attribute 'σ_Ixy' : Real = 0.02351283871158888;
                                attribute Ixz : Real = 0.0053934726510995795;
                                attribute 'σ_Ixz' : Real = 0.022566176940390956;
                                attribute Iyz : Real = 0.016128148044183502;
                                attribute 'σ_Iyz' : Real = 0.02209918015384651;
                            }
                        }
                    }
                    part <'C.1.1.3.1.2'> 'Assembly 21' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.1.2.1'> 'Subassembly 76' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.1.2.1.1'> 'Part 261' {
                                attribute POIconv : String = "-";
                                attribute Ipoint : Boolean = false;
                                attribute mass : Real = 0.9208727725881618;
                                attribute 'σ_mass' : Real = 0.28909372274994966;
                                attribute Cx : Real = 96.02795224636793;
                                attribute 'σ_Cx' : Real = 28.721044428837228;
                                attribute Cy : Real = 25.754825212061405;
                                attribute 'σ_Cy' : Real = 28.23690002309109;
                                attribute Cz : Real = -44.89626814611256;
                                attribute 'σ_Cz' : Real = 29.057750463592832;
                                attribute Ixx : Real = 1.1780845293487074;
                                attribute 'σ_Ixx' : Real = 0.37074144170588635;
                                attribute Iyy : Real = 1.468029121522247;
                                attribute 'σ_Iyy' : Real = 0.3723953238821935;
                                attribute Izz : Real = 1.1407529997326853;
                                attribute 'σ_Izz' : Real = 0.37017423652493897;
                                attribute Ixy : Real = -0.04012158849002713;
                                attribute 'σ_Ixy' : Real = 0.02351283871158888;
                                attribute Ixz : Real = 0.010713916873302944;
                                attribute 'σ_Ixz' : Real = 0.022566176940390956;
                                attribute Iyz : Real = 0.002397577920364697;
                                attribute 'σ_Iyz' : Real = 0.02209918015384651;
                            }
                            part <'C.1.1.3.1.2.1.2'> 'Part 262' {
                                attribute POIconv : String = "+";
                                attribute Ipoint : Boolean = false;
                                attribute mass : Real = 0.6900958022463601;
                                attribute 'σ_mass' : Real = 0.28909372274994966;
                                attribute Cx : Real = 33.805982908234;
                                attribute 'σ_Cx' : Real = 28.721044428837228;
                                attribute Cy : Real = 22.227299585938454;
                                attribute 'σ_Cy' : Real = 28.23690002309109;
                                attribute Cz : Real = -27.14954554103315;
                                attribute 'σ_Cz' : Real = 29.057750463592832;
                                attribute Ixx : Real = 0.7588880408306196;
                                attribute 'σ_Ixx' : Real = 0.37074144170588635;
                                attribute Iyy : Real = 0.8862795417196262;
                                attribute 'σ_Iyy' : Real = 0.3723953238821935;
                                attribute Izz : Real = 0.9004089994697978;
                                attribute 'σ_Izz' : Real = 0.37017423652493897;
                                attribute Ixy : Real = 0.014127457032560888;
                                attribute 'σ_Ixy' : Real = 0.02351283871158888;
                                attribute Ixz : Real = 0.027891246430802874;
                                attribute 'σ_Ixz' : Real = 0.022566176940390956;
                                attribute Iyz : Real = -0.01039358433194291;
                                attribute 'σ_Iyz' : Real = 0.02209918015384651;
                            }
                        }
                        part <'C.1.1.3.1.2.2'> 'Subassembly 77' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.1.2.2.1'> 'Part 263' {
                                attribute POIconv : String = "+";
                                attribute Ipoint : Boolean = false;
                                attribute mass : Real = 0.9413825466895942;
                                attribute 'σ_mass' : Real = 0.28909372274994966;
                                attribute Cx : Real = -84.61358374916017;
                                attribute 'σ_Cx' : Real = 28.721044428837228;
                                attribute Cy : Real = 45.72876738384366;
                                attribute 'σ_Cy' : Real = 28.23690002309109;
                                attribute Cz : Real = -69.54333679750562;
                                attribute 'σ_Cz' : Real = 29.057750463592832;
                                attribute Ixx : Real = 1.2695341479387285;
                                attribute 'σ_Ixx' : Real = 0.37074144170588635;
                                attribute Iyy : Real = 1.2036281343311614;
                                attribute 'σ_Iyy' : Real = 0.3723953238821935;
                                attribute Izz : Real = 1.1547955480858163;
                                attribute 'σ_Izz' : Real = 0.37017423652493897;
                                attribute Ixy : Real = -0.06875479925575317;
                                attribute 'σ_Ixy' : Real = 0.02351283871158888;
                                attribute Ixz : Real = -0.010738434992778009;
                                attribute 'σ_Ixz' : Real = 0.022566176940390956;
                                attribute Iyz : Real = 0.039220520668120984;
                                attribute 'σ_Iyz' : Real = 0.02209918015384651;
                            }
                            part <'C.1.1.3.1.2.2.2'> 'Part 264' {
                                attribute POIconv : String = "+";
                                attribute Ipoint : Boolean = false;
                                attribute mass : Real = 0.953823660824215;
                                attribute 'σ_mass' : Real = 0.28909372274994966;
                                attribute Cx : Real = -55.915615474805236;
                                attribute 'σ_Cx' : Real = 28.721044428837228;
                                attribute Cy : Real = -53.96787775680423;
                                attribute 'σ_Cy' : Real = 28.23690002309109;
                                attribute Cz : Real = -85.33980087377131;
                                attribute 'σ_Cz' : Real = 29.057750463592832;
                                attribute Ixx : Real = 0.9618780277315447;
                                attribute 'σ_Ixx' : Real = 0.37074144170588635;
                                attribute Iyy : Real = 0.9508211853745024;
                                attribute 'σ_Iyy' : Real = 0.3723953238821935;
                                attribute Izz : Real = 0.9059315953604018;
                                attribute 'σ_Izz' : Real = 0.37017423652493897;
                                attribute Ixy : Real = 0.0346433284407284;
                                attribute 'σ_Ixy' : Real = 0.02351283871158888;
                                attribute Ixz : Real = 0.024045305289706928;
                                attribute 'σ_Ixz' : Real = 0.022566176940390956;
                                attribute Iyz : Real = -0.013406080941731473;
                                attribute 'σ_Iyz' : Real = 0.02209918015384651;
                            }
                            part <'C.1.1.3.1.2.2.3'> 'Part 265' {
                                attribute POIconv : String = "-";
                                attribute Ipoint : Boolean = false;
                                attribute mass : Real = 0.9507657685515005;
                                attribute 'σ_mass' : Real = 0.28909372274994966;
                                attribute Cx : Real = -88.23057794943452;
                                attribute 'σ_Cx' : Real = 28.721044428837228;
                                attribute Cy : Real = 62.856541480869055;
                                attribute 'σ_Cy' : Real = 28.23690002309109;
                                attribute Cz : Real = 73.85254860855639;
                                attribute 'σ_Cz' : Real = 29.057750463592832;
                                attribute Ixx : Real = 1.245257917211919;
                                attribute 'σ_Ixx' : Real = 0.37074144170588635;
                                attribute Iyy : Real = 1.1715836147943077;
                                attribute 'σ_Iyy' : Real = 0.3723953238821935;
                                attribute Izz : Real = 1.088693176443494;
                                attribute 'σ_Izz' : Real = 0.37017423652493897;
                                attribute Ixy : Real = -0.023702967493313847;
                                attribute 'σ_Ixy' : Real = 0.02351283871158888;
                                attribute Ixz : Real = 0.06826779494755832;
                                attribute 'σ_Ixz' : Real = 0.022566176940390956;
                                attribute Iyz : Real = -0.0012854224717464267;
                                attribute 'σ_Iyz' : Real = 0.02209918015384651;
                            }
                            part <'C.1.1.3.1.2.2.4'> 'Part 266' {
                                attribute POIconv : String = "+";
                                attribute Ipoint : Boolean = false;
                                attribute mass : Real = 0.8449993459808175;
                                attribute 'σ_mass' : Real = 0.28909372274994966;
                                attribute Cx : Real = -35.575941717252135;
                                attribute 'σ_Cx' : Real = 28.721044428837228;
                                attribute Cy : Real = 41.66119294241071;
                                attribute 'σ_Cy' : Real = 28.23690002309109;
                                attribute Cz : Real = -41.5553062222898;
                                attribute 'σ_Cz' : Real = 29.057750463592832;
                                attribute Ixx : Real = 1.000740602264269;
                                attribute 'σ_Ixx' : Real = 0.37074144170588635;
                                attribute Iyy : Real = 1.0098566950774743;
                                attribute 'σ_Iyy' : Real = 0.3723953238821935;
                                attribute Izz : Real = 0.8955893944788258;
                                attribute 'σ_Izz' : Real = 0.37017423652493897;
                                attribute Ixy : Real = -0.07052705647277463;
                                attribute 'σ_Ixy' : Real = 0.02351283871158888;
                                attribute Ixz : Real = -0.02726766454590198;
                                attribute 'σ_Ixz' : Real = 0.022566176940390956;
                                attribute Iyz : Real = -0.029959999045877584;
                                attribute 'σ_Iyz' : Real = 0.02209918015384651;
                            }
                        }
                        part <'C.1.1.3.1.2.3'> 'Subassembly 78' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.1.2.3.1'> 'Part 267' {
                                attribute POIconv : String = "-";
                                attribute Ipoint : Boolean = false;
                                attribute mass : Real = 0.3990789232524112;
                                attribute 'σ_mass' : Real = 0.28909372274994966;
                                attribute Cx : Real = -87.92814319022;
                                attribute 'σ_Cx' : Real = 28.721044428837228;
                                attribute Cy : Real = 33.370931120589375;
                                attribute 'σ_Cy' : Real = 28.23690002309109;
                                attribute Cz : Real = 4.518514405936003;
                                attribute 'σ_Cz' : Real = 29.057750463592832;
                                attribute Ixx : Real = 0.4993905052332954;
                                attribute 'σ_Ixx' : Real = 0.37074144170588635;
                                attribute Iyy : Real = 0.4680890662663117;
                                attribute 'σ_Iyy' : Real = 0.3723953238821935;
                                attribute Izz : Real = 0.5236262643573312;
                                attribute 'σ_Izz' : Real = 0.37017423652493897;
                                attribute Ixy : Real = 0.035250958535723916;
                                attribute 'σ_Ixy' : Real = 0.02351283871158888;
                                attribute Ixz : Real = -0.01848529808548552;
                                attribute 'σ_Ixz' : Real = 0.022566176940390956;
                                attribute Iyz : Real = -0.007443518717315208;
                                attribute 'σ_Iyz' : Real = 0.02209918015384651;
                            }
                            part <'C.1.1.3.1.2.3.2'> 'Part 268' {
                                attribute POIconv : String = "-";
                                attribute Ipoint : Boolean = false;
                                attribute mass : Real = 0.7574910641552415;
                                attribute 'σ_mass' : Real = 0.28909372274994966;
                                attribute Cx : Real = -9.028540784493089;
                                attribute 'σ_Cx' : Real = 28.721044428837228;
                                attribute Cy : Real = 37.34443890862167;
                                attribute 'σ_Cy' : Real = 28.23690002309109;
                                attribute Cz : Real = 38.036530604586005;
                                attribute 'σ_Cz' : Real = 29.057750463592832;
                                attribute Ixx : Real = 1.085988324908633;
                                attribute 'σ_Ixx' : Real = 0.37074144170588635;
                                attribute Iyy : Real = 0.9411251785101542;
                                attribute 'σ_Iyy' : Real = 0.3723953238821935;
                                attribute Izz : Real = 0.8765610911194566;
                                attribute 'σ_Izz' : Real = 0.37017423652493897;
                                attribute Ixy : Real = -0.036515027284567736;
                                attribute 'σ_Ixy' : Real = 0.02351283871158888;
                                attribute Ixz : Real = 0.08152323760279603;
                                attribute 'σ_Ixz' : Real = 0.022566176940390956;
                                attribute Iyz : Real = -0.008338097411659216;
                                attribute 'σ_Iyz' : Real = 0.02209918015384651;
                            }
                        }
                    }
                    part <'C.1.1.3.1.3'> 'Assembly 22' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.1.3.1'> 'Subassembly 79' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.1.3.1.1'> 'Part 269' {
                                attribute POIconv : String = "-";
                                attribute Ipoint : Boolean = false;
                                attribute mass : Real = 0.7552149838383775;
                                attribute 'σ_mass' : Real = 0.28909372274994966;
                                attribute Cx : Real = 16.30487642250955;
                                attribute 'σ_Cx' : Real = 28.721044428837228;
                                attribute Cy : Real = 41.70290273614228;
                                attribute 'σ_Cy' : Real = 28.23690002309109;
                                attribute Cz : Real = -96.58639398403466;
                                attribute 'σ_Cz' : Real = 29.057750463592832;
                                attribute Ixx : Real = 0.9806093264436713;
                                attribute 'σ_Ixx' : Real = 0.37074144170588635;
                                attribute Iyy : Real = 1.0074705016244765;
                                attribute 'σ_Iyy' : Real = 0.3723953238821935;
                                attribute Izz : Real = 0.9560956446860153;
                                attribute 'σ_Izz' : Real = 0.37017423652493897;
                                attribute Ixy : Real = -0.08405008993904409;
                                attribute 'σ_Ixy' : Real = 0.02351283871158888;
                                attribute Ixz : Real = -0.08412041250075607;
                                attribute 'σ_Ixz' : Real = 0.022566176940390956;
                                attribute Iyz : Real = 0.03650060023863229;
                                attribute 'σ_Iyz' : Real = 0.02209918015384651;
                            }
                            part <'C.1.1.3.1.3.1.2'> 'Part 270' {
                                attribute POIconv : String = "-";
                                attribute Ipoint : Boolean = false;
                                attribute mass : Real = 0.6606783553028945;
                                attribute 'σ_mass' : Real = 0.28909372274994966;
                                attribute Cx : Real = 86.63584208115935;
                                attribute 'σ_Cx' : Real = 28.721044428837228;
                                attribute Cy : Real = 12.109112739562988;
                                attribute 'σ_Cy' : Real = 28.23690002309109;
                                attribute Cz : Real = -7.506129052489996;
                                attribute 'σ_Cz' : Real = 29.057750463592832;
                                attribute Ixx : Real = 0.9930458614088498;
                                attribute 'σ_Ixx' : Real = 0.37074144170588635;
                                attribute Iyy : Real = 0.991372570388312;
                                attribute 'σ_Iyy' : Real = 0.3723953238821935;
                                attribute Izz : Real = 0.9812374841152306;
                                attribute 'σ_Izz' : Real = 0.37017423652493897;
                                attribute Ixy : Real = 0.0025908724554307046;
                                attribute 'σ_Ixy' : Real = 0.02351283871158888;
                                attribute Ixz : Real = 1.8148602731744411e-4;
                                attribute 'σ_Ixz' : Real = 0.022566176940390956;
                                attribute Iyz : Real = 1.964727865071506e-4;
                                attribute 'σ_Iyz' : Real = 0.02209918015384651;
                            }
                            part <'C.1.1.3.1.3.1.3'> 'Part 271' {
                                attribute POIconv : String = "+";
                                attribute Ipoint : Boolean = false;
                                attribute mass : Real = 0.6912593172150664;
                                attribute 'σ_mass' : Real = 0.28909372274994966;
                                attribute Cx : Real = 88.21610664017498;
                                attribute 'σ_Cx' : Real = 28.721044428837228;
                                attribute Cy : Real = -17.485354654490948;
                                attribute 'σ_Cy' : Real = 28.23690002309109;
                                attribute Cz : Real = -65.57553191669285;
                                attribute 'σ_Cz' : Real = 29.057750463592832;
                                attribute Ixx : Real = 0.6100052526675863;
                                attribute 'σ_Ixx' : Real = 0.37074144170588635;
                                attribute Iyy : Real = 0.6529572923972892;
                                attribute 'σ_Iyy' : Real = 0.3723953238821935;
                                attribute Izz : Real = 0.678571295636607;
                                attribute 'σ_Izz' : Real = 0.37017423652493897;
                                attribute Ixy : Real = 0.04316205983161274;
                                attribute 'σ_Ixy' : Real = 0.02351283871158888;
                                attribute Ixz : Real = 0.008023826489047753;
                                attribute 'σ_Ixz' : Real = 0.022566176940390956;
                                attribute Iyz : Real = 0.004693404630064313;
                                attribute 'σ_Iyz' : Real = 0.02209918015384651;
                            }
                            part <'C.1.1.3.1.3.1.4'> 'Part 272' {
                                attribute POIconv : String = "-";
                                attribute Ipoint : Boolean = false;
                                attribute mass : Real = 0.788352834661724;
                                attribute 'σ_mass' : Real = 0.28909372274994966;
                                attribute Cx : Real = 86.8435769341886;
                                attribute 'σ_Cx' : Real = 28.721044428837228;
                                attribute Cy : Real = 39.96409913524985;
                                attribute 'σ_Cy' : Real = 28.23690002309109;
                                attribute Cz : Real = -99.45053015835583;
                                attribute 'σ_Cz' : Real = 29.057750463592832;
                                attribute Ixx : Real = 1.0525254060784688;
                                attribute 'σ_Ixx' : Real = 0.37074144170588635;
                                attribute Iyy : Real = 1.0648584150233433;
                                attribute 'σ_Iyy' : Real = 0.3723953238821935;
                                attribute Izz : Real = 1.0924118762277755;
                                attribute 'σ_Izz' : Real = 0.37017423652493897;
                                attribute Ixy : Real = 0.041606553373961644;
                                attribute 'σ_Ixy' : Real = 0.02351283871158888;
                                attribute Ixz : Real = -0.0031064086413085355;
                                attribute 'σ_Ixz' : Real = 0.022566176940390956;
                                attribute Iyz : Real = -3.8925071180354693e-4;
                                attribute 'σ_Iyz' : Real = 0.02209918015384651;
                            }
                        }
                        part <'C.1.1.3.1.3.2'> 'Subassembly 80' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.1.3.2.1'> 'Part 273' {
                                attribute POIconv : String = "-";
                                attribute Ipoint : Boolean = false;
                                attribute mass : Real = 0.9768240581154823;
                                attribute 'σ_mass' : Real = 0.28909372274994966;
                                attribute Cx : Real = -47.41086442954838;
                                attribute 'σ_Cx' : Real = 28.721044428837228;
                                attribute Cy : Real = 73.20753554813564;
                                attribute 'σ_Cy' : Real = 28.23690002309109;
                                attribute Cz : Real = -31.987325195223093;
                                attribute 'σ_Cz' : Real = 29.057750463592832;
                                attribute Ixx : Real = 0.8800924858894497;
                                attribute 'σ_Ixx' : Real = 0.37074144170588635;
                                attribute Iyy : Real = 0.9159050114096706;
                                attribute 'σ_Iyy' : Real = 0.3723953238821935;
                                attribute Izz : Real = 0.9523200161105341;
                                attribute 'σ_Izz' : Real = 0.37017423652493897;
                                attribute Ixy : Real = 0.001086591242318731;
                                attribute 'σ_Ixy' : Real = 0.02351283871158888;
                                attribute Ixz : Real = -0.012586614579215042;
                                attribute 'σ_Ixz' : Real = 0.022566176940390956;
                                attribute Iyz : Real = 0.012104638069395893;
                                attribute 'σ_Iyz' : Real = 0.02209918015384651;
                            }
                            part <'C.1.1.3.1.3.2.2'> 'Part 274' {
                                attribute POIconv : String = "+";
                                attribute Ipoint : Boolean = false;
                                attribute mass : Real = 0.25537284385273235;
                                attribute 'σ_mass' : Real = 0.28909372274994966;
                                attribute Cx : Real = 58.97910385392606;
                                attribute 'σ_Cx' : Real = 28.721044428837228;
                                attribute Cy : Real = 25.44229393824935;
                                attribute 'σ_Cy' : Real = 28.23690002309109;
                                attribute Cz : Real = 81.1688160058111;
                                attribute 'σ_Cz' : Real = 29.057750463592832;
                                attribute Ixx : Real = 0.29186901986818004;
                                attribute 'σ_Ixx' : Real = 0.37074144170588635;
                                attribute Iyy : Real = 0.29349861922566334;
                                attribute 'σ_Iyy' : Real = 0.3723953238821935;
                                attribute Izz : Real = 0.3122881687375152;
                                attribute 'σ_Izz' : Real = 0.37017423652493897;
                                attribute Ixy : Real = 0.014870443509481166;
                                attribute 'σ_Ixy' : Real = 0.02351283871158888;
                                attribute Ixz : Real = 0.0016174942667759751;
                                attribute 'σ_Ixz' : Real = 0.022566176940390956;
                                attribute Iyz : Real = 0.0016197103779840784;
                                attribute 'σ_Iyz' : Real = 0.02209918015384651;
                            }
                            part <'C.1.1.3.1.3.2.3'> 'Part 275' {
                                attribute POIconv : String = "+";
                                attribute Ipoint : Boolean = false;
                                attribute mass : Real = 0.477546617006883;
                                attribute 'σ_mass' : Real = 0.28909372274994966;
                                attribute Cx : Real = 72.51322655938566;
                                attribute 'σ_Cx' : Real = 28.721044428837228;
                                attribute Cy : Real = -13.688563043251634;
                                attribute 'σ_Cy' : Real = 28.23690002309109;
                                attribute Cz : Real = -1.2842373922467232;
                                attribute 'σ_Cz' : Real = 29.057750463592832;
                                attribute Ixx : Real = 0.603187338049231;
                                attribute 'σ_Ixx' : Real = 0.37074144170588635;
                                attribute Iyy : Real = 0.6019458182092132;
                                attribute 'σ_Iyy' : Real = 0.3723953238821935;
                                attribute Izz : Real = 0.5841928516360604;
                                attribute 'σ_Izz' : Real = 0.37017423652493897;
                                attribute Ixy : Real = 0.0018082758596553341;
                                attribute 'σ_Ixy' : Real = 0.02351283871158888;
                                attribute Ixz : Real = 0.003778141957881892;
                                attribute 'σ_Ixz' : Real = 0.022566176940390956;
                                attribute Iyz : Real = 0.0010040443577650823;
                                attribute 'σ_Iyz' : Real = 0.02209918015384651;
                            }
                        }
                        part <'C.1.1.3.1.3.3'> 'Subassembly 81' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.1.3.3.1'> 'Part 276' {
                                attribute POIconv : String = "+";
                                attribute Ipoint : Boolean = false;
                                attribute mass : Real = 0.3882750416311901;
                                attribute 'σ_mass' : Real = 0.28909372274994966;
                                attribute Cx : Real = 82.98041033558547;
                                attribute 'σ_Cx' : Real = 28.721044428837228;
                                attribute Cy : Real = 46.63001396693289;
                                attribute 'σ_Cy' : Real = 28.23690002309109;
                                attribute Cz : Real = 68.63532420247793;
                                attribute 'σ_Cz' : Real = 29.057750463592832;
                                attribute Ixx : Real = 0.5134519744349403;
                                attribute 'σ_Ixx' : Real = 0.37074144170588635;
                                attribute Iyy : Real = 0.5266967115668738;
                                attribute 'σ_Iyy' : Real = 0.3723953238821935;
                                attribute Izz : Real = 0.4363105052574482;
                                attribute 'σ_Izz' : Real = 0.37017423652493897;
                                attribute Ixy : Real = -0.002509714717017153;
                                attribute 'σ_Ixy' : Real = 0.02351283871158888;
                                attribute Ixz : Real = -0.0364854809768939;
                                attribute 'σ_Ixz' : Real = 0.022566176940390956;
                                attribute Iyz : Real = 0.0028371410191746927;
                                attribute 'σ_Iyz' : Real = 0.02209918015384651;
                            }
                            part <'C.1.1.3.1.3.3.2'> 'Part 277' {
                                attribute POIconv : String = "-";
                                attribute Ipoint : Boolean = false;
                                attribute mass : Real = 0.26259506153757683;
                                attribute 'σ_mass' : Real = 0.28909372274994966;
                                attribute Cx : Real = 78.57895875349641;
                                attribute 'σ_Cx' : Real = 28.721044428837228;
                                attribute Cy : Real = 18.341201590374112;
                                attribute 'σ_Cy' : Real = 28.23690002309109;
                                attribute Cz : Real = -74.68567094765604;
                                attribute 'σ_Cz' : Real = 29.057750463592832;
                                attribute Ixx : Real = 0.3317300256891948;
                                attribute 'σ_Ixx' : Real = 0.37074144170588635;
                                attribute Iyy : Real = 0.3187521032327962;
                                attribute 'σ_Iyy' : Real = 0.3723953238821935;
                                attribute Izz : Real = 0.31066051621656837;
                                attribute 'σ_Izz' : Real = 0.37017423652493897;
                                attribute Ixy : Real = 0.005221628987863486;
                                attribute 'σ_Ixy' : Real = 0.02351283871158888;
                                attribute Ixz : Real = 0.005274844018927083;
                                attribute 'σ_Ixz' : Real = 0.022566176940390956;
                                attribute Iyz : Real = -0.012544664523111773;
                                attribute 'σ_Iyz' : Real = 0.02209918015384651;
                            }
                            part <'C.1.1.3.1.3.3.3'> 'Part 278' {
                                attribute POIconv : String = "+";
                                attribute Ipoint : Boolean = false;
                                attribute mass : Real = 0.21215892461873592;
                                attribute 'σ_mass' : Real = 0.28909372274994966;
                                attribute Cx : Real = -82.1514209266752;
                                attribute 'σ_Cx' : Real = 28.721044428837228;
                                attribute Cy : Real = 58.627963392063975;
                                attribute 'σ_Cy' : Real = 28.23690002309109;
                                attribute Cz : Real = 66.21389323845506;
                                attribute 'σ_Cz' : Real = 29.057750463592832;
                                attribute Ixx : Real = 0.29804026080744483;
                                attribute 'σ_Ixx' : Real = 0.37074144170588635;
                                attribute Iyy : Real = 0.28662850783559407;
                                attribute 'σ_Iyy' : Real = 0.3723953238821935;
                                attribute Izz : Real = 0.28576333851084784;
                                attribute 'σ_Izz' : Real = 0.37017423652493897;
                                attribute Ixy : Real = -0.023939250208943632;
                                attribute 'σ_Ixy' : Real = 0.02351283871158888;
                                attribute Ixz : Real = 0.021341632877149998;
                                attribute 'σ_Ixz' : Real = 0.022566176940390956;
                                attribute Iyz : Real = 7.780960577164109e-4;
                                attribute 'σ_Iyz' : Real = 0.02209918015384651;
                            }
                        }
                        part <'C.1.1.3.1.3.4'> 'Subassembly 82' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.1.3.4.1'> 'Part 279' {
                                attribute POIconv : String = "-";
                                attribute Ipoint : Boolean = false;
                                attribute mass : Real = 0.0796404043759685;
                                attribute 'σ_mass' : Real = 0.28909372274994966;
                                attribute Cx : Real = -20.937465084716678;
                                attribute 'σ_Cx' : Real = 28.721044428837228;
                                attribute Cy : Real = 69.190364331007;
                                attribute 'σ_Cy' : Real = 28.23690002309109;
                                attribute Cz : Real = 86.66236279532313;
                                attribute 'σ_Cz' : Real = 29.057750463592832;
                                attribute Ixx : Real = 0.10368158308599461;
                                attribute 'σ_Ixx' : Real = 0.37074144170588635;
                                attribute Iyy : Real = 0.11016089598137602;
                                attribute 'σ_Iyy' : Real = 0.3723953238821935;
                                attribute Izz : Real = 0.10466910909698864;
                                attribute 'σ_Izz' : Real = 0.37017423652493897;
                                attribute Ixy : Real = -0.005090819739572896;
                                attribute 'σ_Ixy' : Real = 0.02351283871158888;
                                attribute Ixz : Real = -0.0018534140864118255;
                                attribute 'σ_Ixz' : Real = 0.022566176940390956;
                                attribute Iyz : Real = 1.970398635431634e-4;
                                attribute 'σ_Iyz' : Real = 0.02209918015384651;
                            }
                            part <'C.1.1.3.1.3.4.2'> 'Part 280' {
                                attribute POIconv : String = "-";
                                attribute Ipoint : Boolean = false;
                                attribute mass : Real = 0.5992493163826875;
                                attribute 'σ_mass' : Real = 0.28909372274994966;
                                attribute Cx : Real = 33.10775747522712;
                                attribute 'σ_Cx' : Real = 28.721044428837228;
                                attribute Cy : Real = -17.123185843229294;
                                attribute 'σ_Cy' : Real = 28.23690002309109;
                                attribute Cz : Real = 97.63681297190487;
                                attribute 'σ_Cz' : Real = 29.057750463592832;
                                attribute Ixx : Real = 0.7468408203521136;
                                attribute 'σ_Ixx' : Real = 0.37074144170588635;
                                attribute Iyy : Real = 0.7708896742742051;
                                attribute 'σ_Iyy' : Real = 0.3723953238821935;
                                attribute Izz : Real = 0.7961123529012294;
                                attribute 'σ_Izz' : Real = 0.37017423652493897;
                                attribute Ixy : Real = 0.008264479374425884;
                                attribute 'σ_Ixy' : Real = 0.02351283871158888;
                                attribute Ixz : Real = -0.02350251201482062;
                                attribute 'σ_Ixz' : Real = 0.022566176940390956;
                                attribute Iyz : Real = 0.01888485359550897;
                                attribute 'σ_Iyz' : Real = 0.02209918015384651;
                            }
                            part <'C.1.1.3.1.3.4.3'> 'Part 281' {
                                attribute POIconv : String = "+";
                                attribute Ipoint : Boolean = false;
                                attribute mass : Real = 0.33510842293617316;
                                attribute 'σ_mass' : Real = 0.28909372274994966;
                                attribute Cx : Real = 36.76092238165438;
                                attribute 'σ_Cx' : Real = 28.721044428837228;
                                attribute Cy : Real = 67.45433560572565;
                                attribute 'σ_Cy' : Real = 28.23690002309109;
                                attribute Cz : Real = -56.81755640543997;
                                attribute 'σ_Cz' : Real = 29.057750463592832;
                                attribute Ixx : Real = 0.36463873443370753;
                                attribute 'σ_Ixx' : Real = 0.37074144170588635;
                                attribute Iyy : Real = 0.4309386004329424;
                                attribute 'σ_Iyy' : Real = 0.3723953238821935;
                                attribute Izz : Real = 0.37829257303458796;
                                attribute 'σ_Izz' : Real = 0.37017423652493897;
                                attribute Ixy : Real = -0.004504852986252152;
                                attribute 'σ_Ixy' : Real = 0.02351283871158888;
                                attribute Ixz : Real = 0.038181641686040435;
                                attribute 'σ_Ixz' : Real = 0.022566176940390956;
                                attribute Iyz : Real = -0.012584964318461352;
                                attribute 'σ_Iyz' : Real = 0.02209918015384651;
                            }
                            part <'C.1.1.3.1.3.4.4'> 'Part 282' {
                                attribute POIconv : String = "-";
                                attribute Ipoint : Boolean = false;
                                attribute mass : Real = 0.6965594651980791;
                                attribute 'σ_mass' : Real = 0.28909372274994966;
                                attribute Cx : Real = 32.12253162637353;
                                attribute 'σ_Cx' : Real = 28.721044428837228;
                                attribute Cy : Real = 5.608240840956569;
                                attribute 'σ_Cy' : Real = 28.23690002309109;
                                attribute Cz : Real = -42.93682421557605;
                                attribute 'σ_Cz' : Real = 29.057750463592832;
                                attribute Ixx : Real = 0.9499373043627023;
                                attribute 'σ_Ixx' : Real = 0.37074144170588635;
                                attribute Iyy : Real = 0.8691069344418099;
                                attribute 'σ_Iyy' : Real = 0.3723953238821935;
                                attribute Izz : Real = 0.949128355553683;
                                attribute 'σ_Izz' : Real = 0.37017423652493897;
                                attribute Ixy : Real = -0.01117247453881469;
                                attribute 'σ_Ixy' : Real = 0.02351283871158888;
                                attribute Ixz : Real = -2.0040106540835425e-4;
                                attribute 'σ_Ixz' : Real = 0.022566176940390956;
                                attribute Iyz : Real = -9.360542018633984e-4;
                                attribute 'σ_Iyz' : Real = 0.02209918015384651;
                            }
                        }
                    }
                    part <'C.1.1.3.1.4'> 'Assembly 23' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.1.4.1'> 'Subassembly 83' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.1.4.1.1'> 'Part 283' {
                                attribute POIconv : String = "-";
                                attribute Ipoint : Boolean = false;
                                attribute mass : Real = 0.2084483498572372;
                                attribute 'σ_mass' : Real = 0.28909372274994966;
                                attribute Cx : Real = -96.01093241944909;
                                attribute 'σ_Cx' : Real = 28.721044428837228;
                                attribute Cy : Real = -81.30620876327157;
                                attribute 'σ_Cy' : Real = 28.23690002309109;
                                attribute Cz : Real = 1.0111707728356123;
                                attribute 'σ_Cz' : Real = 29.057750463592832;
                                attribute Ixx : Real = 0.26681576158109216;
                                attribute 'σ_Ixx' : Real = 0.37074144170588635;
                                attribute Iyy : Real = 0.2376899871101428;
                                attribute 'σ_Iyy' : Real = 0.3723953238821935;
                                attribute Izz : Real = 0.27077906223512227;
                                attribute 'σ_Izz' : Real = 0.37017423652493897;
                                attribute Ixy : Real = -0.012964369702082378;
                                attribute 'σ_Ixy' : Real = 0.02351283871158888;
                                attribute Ixz : Real = 0.019659304800306393;
                                attribute 'σ_Ixz' : Real = 0.022566176940390956;
                                attribute Iyz : Real = 0.017664549741799974;
                                attribute 'σ_Iyz' : Real = 0.02209918015384651;
                            }
                            part <'C.1.1.3.1.4.1.2'> 'Part 284' {
                                attribute POIconv : String = "-";
                                attribute Ipoint : Boolean = false;
                                attribute mass : Real = 0.7113561106431298;
                                attribute 'σ_mass' : Real = 0.28909372274994966;
                                attribute Cx : Real = 13.984119845554233;
                                attribute 'σ_Cx' : Real = 28.721044428837228;
                                attribute Cy : Real = 31.972823245450854;
                                attribute 'σ_Cy' : Real = 28.23690002309109;
                                attribute Cz : Real = 11.656727455556393;
                                attribute 'σ_Cz' : Real = 29.057750463592832;
                                attribute Ixx : Real = 0.8858934281676961;
                                attribute 'σ_Ixx' : Real = 0.37074144170588635;
                                attribute Iyy : Real = 0.9918782537469021;
                                attribute 'σ_Iyy' : Real = 0.3723953238821935;
                                attribute Izz : Real = 0.9695064216949099;
                                attribute 'σ_Izz' : Real = 0.37017423652493897;
                                attribute Ixy : Real = 0.004187664518983513;
                                attribute 'σ_Ixy' : Real = 0.02351283871158888;
                                attribute Ixz : Real = -0.03440105526948157;
                                attribute 'σ_Ixz' : Real = 0.022566176940390956;
                                attribute Iyz : Real = -1.6293245020117535e-4;
                                attribute 'σ_Iyz' : Real = 0.02209918015384651;
                            }
                        }
                        part <'C.1.1.3.1.4.2'> 'Subassembly 84' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.1.4.2.1'> 'Part 285' {
                                attribute POIconv : String = "+";
                                attribute Ipoint : Boolean = false;
                                attribute mass : Real = 0.5259021329942625;
                                attribute 'σ_mass' : Real = 0.28909372274994966;
                                attribute Cx : Real = -17.64671364799142;
                                attribute 'σ_Cx' : Real = 28.721044428837228;
                                attribute Cy : Real = 89.54165210016072;
                                attribute 'σ_Cy' : Real = 28.23690002309109;
                                attribute Cz : Real = 43.38798294775188;
                                attribute 'σ_Cz' : Real = 29.057750463592832;
                                attribute Ixx : Real = 0.5699289325638927;
                                attribute 'σ_Ixx' : Real = 0.37074144170588635;
                                attribute Iyy : Real = 0.5951089484357659;
                                attribute 'σ_Iyy' : Real = 0.3723953238821935;
                                attribute Izz : Real = 0.601127148301748;
                                attribute 'σ_Izz' : Real = 0.37017423652493897;
                                attribute Ixy : Real = 0.022493407523167995;
                                attribute 'σ_Ixy' : Real = 0.02351283871158888;
                                attribute Ixz : Real = 0.019144821259585804;
                                attribute 'σ_Ixz' : Real = 0.022566176940390956;
                                attribute Iyz : Real = 0.01057045903422532;
                                attribute 'σ_Iyz' : Real = 0.02209918015384651;
                            }
                            part <'C.1.1.3.1.4.2.2'> 'Part 286' {
                                attribute POIconv : String = "+";
                                attribute Ipoint : Boolean = false;
                                attribute mass : Real = 0.02628880715300329;
                                attribute 'σ_mass' : Real = 0.28909372274994966;
                                attribute Cx : Real = 0.01230696216225624;
                                attribute 'σ_Cx' : Real = 28.721044428837228;
                                attribute Cy : Real = 62.76070298627019;
                                attribute 'σ_Cy' : Real = 28.23690002309109;
                                attribute Cz : Real = -53.94966620951891;
                                attribute 'σ_Cz' : Real = 29.057750463592832;
                                attribute Ixx : Real = 0.029127629948469222;
                                attribute 'σ_Ixx' : Real = 0.37074144170588635;
                                attribute Iyy : Real = 0.026762449049083932;
                                attribute 'σ_Iyy' : Real = 0.3723953238821935;
                                attribute Izz : Real = 0.027475363535445323;
                                attribute 'σ_Izz' : Real = 0.37017423652493897;
                                attribute Ixy : Real = -2.1024904939354158e-4;
                                attribute 'σ_Ixy' : Real = 0.02351283871158888;
                                attribute Ixz : Real = 0.0016200013543922697;
                                attribute 'σ_Ixz' : Real = 0.022566176940390956;
                                attribute Iyz : Real = 6.147594074536535e-4;
                                attribute 'σ_Iyz' : Real = 0.02209918015384651;
                            }
                            part <'C.1.1.3.1.4.2.3'> 'Part 287' {
                                attribute POIconv : String = "+";
                                attribute Ipoint : Boolean = false;
                                attribute mass : Real = 0.7893841061438434;
                                attribute 'σ_mass' : Real = 0.28909372274994966;
                                attribute Cx : Real = 66.85028658248484;
                                attribute 'σ_Cx' : Real = 28.721044428837228;
                                attribute Cy : Real = 48.17043375223875;
                                attribute 'σ_Cy' : Real = 28.23690002309109;
                                attribute Cz : Real = -42.84108933061361;
                                attribute 'σ_Cz' : Real = 29.057750463592832;
                                attribute Ixx : Real = 1.091784143986187;
                                attribute 'σ_Ixx' : Real = 0.37074144170588635;
                                attribute Iyy : Real = 1.067747839567025;
                                attribute 'σ_Iyy' : Real = 0.3723953238821935;
                                attribute Izz : Real = 0.9870523454670007;
                                attribute 'σ_Izz' : Real = 0.37017423652493897;
                                attribute Ixy : Real = -0.018251024293104035;
                                attribute 'σ_Ixy' : Real = 0.02351283871158888;
                                attribute Ixz : Real = -0.03305758531602982;
                                attribute 'σ_Ixz' : Real = 0.022566176940390956;
                                attribute Iyz : Real = 0.06358601399355998;
                                attribute 'σ_Iyz' : Real = 0.02209918015384651;
                            }
                            part <'C.1.1.3.1.4.2.4'> 'Part 288' {
                                attribute POIconv : String = "-";
                                attribute Ipoint : Boolean = false;
                                attribute mass : Real = 0.5997321608329658;
                                attribute 'σ_mass' : Real = 0.28909372274994966;
                                attribute Cx : Real = -60.982941929250956;
                                attribute 'σ_Cx' : Real = 28.721044428837228;
                                attribute Cy : Real = 81.23541325330734;
                                attribute 'σ_Cy' : Real = 28.23690002309109;
                                attribute Cz : Real = 78.97178935818374;
                                attribute 'σ_Cz' : Real = 29.057750463592832;
                                attribute Ixx : Real = 0.5724571920338896;
                                attribute 'σ_Ixx' : Real = 0.37074144170588635;
                                attribute Iyy : Real = 0.602166344081884;
                                attribute 'σ_Iyy' : Real = 0.3723953238821935;
                                attribute Izz : Real = 0.6050067643493143;
                                attribute 'σ_Izz' : Real = 0.37017423652493897;
                                attribute Ixy : Real = -0.004557661028207018;
                                attribute 'σ_Ixy' : Real = 0.02351283871158888;
                                attribute Ixz : Real = -0.007580448849620853;
                                attribute 'σ_Ixz' : Real = 0.022566176940390956;
                                attribute Iyz : Real = 0.028612424439612358;
                                attribute 'σ_Iyz' : Real = 0.02209918015384651;
                            }
                        }
                        part <'C.1.1.3.1.4.3'> 'Subassembly 85' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.1.4.3.1'> 'Part 289' {
                                attribute POIconv : String = "+";
                                attribute Ipoint : Boolean = false;
                                attribute mass : Real = 0.5838619578559883;
                                attribute 'σ_mass' : Real = 0.28909372274994966;
                                attribute Cx : Real = -44.54403277486563;
                                attribute 'σ_Cx' : Real = 28.721044428837228;
                                attribute Cy : Real = -15.438520535826683;
                                attribute 'σ_Cy' : Real = 28.23690002309109;
                                attribute Cz : Real = 1.3942868448793888;
                                attribute 'σ_Cz' : Real = 29.057750463592832;
                                attribute Ixx : Real = 0.5610682329908524;
                                attribute 'σ_Ixx' : Real = 0.37074144170588635;
                                attribute Iyy : Real = 0.6361642061100627;
                                attribute 'σ_Iyy' : Real = 0.3723953238821935;
                                attribute Izz : Real = 0.6411788066437182;
                                attribute 'σ_Izz' : Real = 0.37017423652493897;
                                attribute Ixy : Real = -0.043219678325177244;
                                attribute 'σ_Ixy' : Real = 0.02351283871158888;
                                attribute Ixz : Real = -0.03578488802047932;
                                attribute 'σ_Ixz' : Real = 0.022566176940390956;
                                attribute Iyz : Real = 0.02160606419841678;
                                attribute 'σ_Iyz' : Real = 0.02209918015384651;
                            }
                            part <'C.1.1.3.1.4.3.2'> 'Part 290' {
                                attribute POIconv : String = "+";
                                attribute Ipoint : Boolean = false;
                                attribute mass : Real = 0.1373074025469832;
                                attribute 'σ_mass' : Real = 0.28909372274994966;
                                attribute Cx : Real = 49.899795511737466;
                                attribute 'σ_Cx' : Real = 28.721044428837228;
                                attribute Cy : Real = 52.46009826660156;
                                attribute 'σ_Cy' : Real = 28.23690002309109;
                                attribute Cz : Real = -45.36074777133763;
                                attribute 'σ_Cz' : Real = 29.057750463592832;
                                attribute Ixx : Real = 0.14359605070649073;
                                attribute 'σ_Ixx' : Real = 0.37074144170588635;
                                attribute Iyy : Real = 0.16375187259050455;
                                attribute 'σ_Iyy' : Real = 0.3723953238821935;
                                attribute Izz : Real = 0.15566337197996727;
                                attribute 'σ_Izz' : Real = 0.37017423652493897;
                                attribute Ixy : Real = -0.010840928079334247;
                                attribute 'σ_Ixy' : Real = 0.02351283871158888;
                                attribute Ixz : Real = 0.0013230675657378201;
                                attribute 'σ_Ixz' : Real = 0.022566176940390956;
                                attribute Iyz : Real = 0.008099615278531801;
                                attribute 'σ_Iyz' : Real = 0.02209918015384651;
                            }
                        }
                    }
                }
                part <'C.1.1.3.2'> 'Subsystem 7' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.3.2.1'> 'Assembly 24' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.2.1.1'> 'Subassembly 86' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.1.1.1'> 'Part 291' {
                                attribute POIconv : String = "+";
                                attribute Ipoint : Boolean = false;
                                attribute mass : Real = 0.20872391965100542;
                                attribute 'σ_mass' : Real = 0.28909372274994966;
                                attribute Cx : Real = -42.453552316874266;
                                attribute 'σ_Cx' : Real = 28.721044428837228;
                                attribute Cy : Real = -91.48890930227935;
                                attribute 'σ_Cy' : Real = 28.23690002309109;
                                attribute Cz : Real = -1.6845434438437223;
                                attribute 'σ_Cz' : Real = 29.057750463592832;
                                attribute Ixx : Real = 0.3030029730743317;
                                attribute 'σ_Ixx' : Real = 0.37074144170588635;
                                attribute Iyy : Real = 0.30041611316587397;
                                attribute 'σ_Iyy' : Real = 0.3723953238821935;
                                attribute Izz : Real = 0.2710764406007241;
                                attribute 'σ_Izz' : Real = 0.37017423652493897;
                                attribute Ixy : Real = 0.021860966315056476;
                                attribute 'σ_Ixy' : Real = 0.02351283871158888;
                                attribute Ixz : Real = 0.0015074379416920045;
                                attribute 'σ_Ixz' : Real = 0.022566176940390956;
                                attribute Iyz : Real = -0.0018500085562770416;
                                attribute 'σ_Iyz' : Real = 0.02209918015384651;
                            }
                            part <'C.1.1.3.2.1.1.2'> 'Part 292' {
                                attribute POIconv : String = "+";
                                attribute Ipoint : Boolean = false;
                                attribute mass : Real = 0.09709896455309354;
                                attribute 'σ_mass' : Real = 0.28909372274994966;
                                attribute Cx : Real = -63.63059016875923;
                                attribute 'σ_Cx' : Real = 28.721044428837228;
                                attribute Cy : Real = -33.34314785897732;
                                attribute 'σ_Cy' : Real = 28.23690002309109;
                                attribute Cz : Real = -29.783048667013645;
                                attribute 'σ_Cz' : Real = 29.057750463592832;
                                attribute Ixx : Real = 0.12761271868433127;
                                attribute 'σ_Ixx' : Real = 0.37074144170588635;
                                attribute Iyy : Real = 0.1259134873340282;
                                attribute 'σ_Iyy' : Real = 0.3723953238821935;
                                attribute Izz : Real = 0.15196374709935354;
                                attribute 'σ_Izz' : Real = 0.37017423652493897;
                                attribute Ixy : Real = -3.372534402745728e-4;
                                attribute 'σ_Ixy' : Real = 0.02351283871158888;
                                attribute Ixz : Real = -0.0023482677694220333;
                                attribute 'σ_Ixz' : Real = 0.022566176940390956;
                                attribute Iyz : Real = -4.0643321109515175e-5;
                                attribute 'σ_Iyz' : Real = 0.02209918015384651;
                            }
                            part <'C.1.1.3.2.1.1.3'> 'Part 293' {
                                attribute POIconv : String = "+";
                                attribute Ipoint : Boolean = false;
                                attribute mass : Real = 0.1320042049740441;
                                attribute 'σ_mass' : Real = 0.28909372274994966;
                                attribute Cx : Real = -51.368594728410244;
                                attribute 'σ_Cx' : Real = 28.721044428837228;
                                attribute Cy : Real = 6.137400772422552;
                                attribute 'σ_Cy' : Real = 28.23690002309109;
                                attribute Cz : Real = 5.860640527680516;
                                attribute 'σ_Cz' : Real = 29.057750463592832;
                                attribute Ixx : Real = 0.1403687501784012;
                                attribute 'σ_Ixx' : Real = 0.37074144170588635;
                                attribute Iyy : Real = 0.13532897377185216;
                                attribute 'σ_Iyy' : Real = 0.3723953238821935;
                                attribute Izz : Real = 0.15687191133581685;
                                attribute 'σ_Izz' : Real = 0.37017423652493897;
                                attribute Ixy : Real = 0.0014135462505616815;
                                attribute 'σ_Ixy' : Real = 0.02351283871158888;
                                attribute Ixz : Real = -0.0029205264864954673;
                                attribute 'σ_Ixz' : Real = 0.022566176940390956;
                                attribute Iyz : Real = -1.900350111307211e-4;
                                attribute 'σ_Iyz' : Real = 0.02209918015384651;
                            }
                            part <'C.1.1.3.2.1.1.4'> 'Part 294' {
                                attribute POIconv : String = "+";
                                attribute Ipoint : Boolean = false;
                                attribute mass : Real = 0.5710190714714117;
                                attribute 'σ_mass' : Real = 0.28909372274994966;
                                attribute Cx : Real = -93.14301228150725;
                                attribute 'σ_Cx' : Real = 28.721044428837228;
                                attribute Cy : Real = -59.18976194225252;
                                attribute 'σ_Cy' : Real = 28.23690002309109;
                                attribute Cz : Real = -7.19731543213129;
                                attribute 'σ_Cz' : Real = 29.057750463592832;
                                attribute Ixx : Real = 0.7935785843580989;
                                attribute 'σ_Ixx' : Real = 0.37074144170588635;
                                attribute Iyy : Real = 0.797762672320005;
                                attribute 'σ_Iyy' : Real = 0.3723953238821935;
                                attribute Izz : Real = 0.7653546626028505;
                                attribute 'σ_Izz' : Real = 0.37017423652493897;
                                attribute Ixy : Real = 9.849175668522937e-4;
                                attribute 'σ_Ixy' : Real = 0.02351283871158888;
                                attribute Ixz : Real = 0.007588358096666954;
                                attribute 'σ_Ixz' : Real = 0.022566176940390956;
                                attribute Iyz : Real = -0.0010469011182626;
                                attribute 'σ_Iyz' : Real = 0.02209918015384651;
                            }
                            part <'C.1.1.3.2.1.1.5'> 'Part 295' {
                                attribute POIconv : String = "-";
                                attribute Ipoint : Boolean = false;
                                attribute mass : Real = 0.5509190735432785;
                                attribute 'σ_mass' : Real = 0.28909372274994966;
                                attribute Cx : Real = -8.113324595615268;
                                attribute 'σ_Cx' : Real = 28.721044428837228;
                                attribute Cy : Real = 35.629220586270094;
                                attribute 'σ_Cy' : Real = 28.23690002309109;
                                attribute Cz : Real = 22.592925187200308;
                                attribute 'σ_Cz' : Real = 29.057750463592832;
                                attribute Ixx : Real = 0.6620054601795933;
                                attribute 'σ_Ixx' : Real = 0.37074144170588635;
                                attribute Iyy : Real = 0.6585418270075559;
                                attribute 'σ_Iyy' : Real = 0.3723953238821935;
                                attribute Izz : Real = 0.6926666756982013;
                                attribute 'σ_Izz' : Real = 0.37017423652493897;
                                attribute Ixy : Real = 0.015376956555522788;
                                attribute 'σ_Ixy' : Real = 0.02351283871158888;
                                attribute Ixz : Real = -0.006891601694035384;
                                attribute 'σ_Ixz' : Real = 0.022566176940390956;
                                attribute Iyz : Real = -6.528032837741772e-4;
                                attribute 'σ_Iyz' : Real = 0.02209918015384651;
                            }
                        }
                        part <'C.1.1.3.2.1.2'> 'Subassembly 87' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.1.2.1'> 'Part 296' {
                                attribute POIconv : String = "-";
                                attribute Ipoint : Boolean = false;
                                attribute mass : Real = 0.7267857742926571;
                                attribute 'σ_mass' : Real = 0.28909372274994966;
                                attribute Cx : Real = 17.65443291515112;
                                attribute 'σ_Cx' : Real = 28.721044428837228;
                                attribute Cy : Real = -99.3824243079871;
                                attribute 'σ_Cy' : Real = 28.23690002309109;
                                attribute Cz : Real = 7.7377688605338335;
                                attribute 'σ_Cz' : Real = 29.057750463592832;
                                attribute Ixx : Real = 1.0189699300613975;
                                attribute 'σ_Ixx' : Real = 0.37074144170588635;
                                attribute Iyy : Real = 1.011737945280532;
                                attribute 'σ_Iyy' : Real = 0.3723953238821935;
                                attribute Izz : Real = 1.1016671032062197;
                                attribute 'σ_Izz' : Real = 0.37017423652493897;
                                attribute Ixy : Real = 0.01032309855838883;
                                attribute 'σ_Ixy' : Real = 0.02351283871158888;
                                attribute Ixz : Real = -0.0376202693240189;
                                attribute 'σ_Ixz' : Real = 0.022566176940390956;
                                attribute Iyz : Real = -0.026749786745504305;
                                attribute 'σ_Iyz' : Real = 0.02209918015384651;
                            }
                            part <'C.1.1.3.2.1.2.2'> 'Part 297' {
                                attribute POIconv : String = "+";
                                attribute Ipoint : Boolean = false;
                                attribute mass : Real = 0.6219178375320044;
                                attribute 'σ_mass' : Real = 0.28909372274994966;
                                attribute Cx : Real = -62.12940663099289;
                                attribute 'σ_Cx' : Real = 28.721044428837228;
                                attribute Cy : Real = -75.98449559882283;
                                attribute 'σ_Cy' : Real = 28.23690002309109;
                                attribute Cz : Real = 68.68572356179357;
                                attribute 'σ_Cz' : Real = 29.057750463592832;
                                attribute Ixx : Real = 0.7294250165007358;
                                attribute 'σ_Ixx' : Real = 0.37074144170588635;
                                attribute Iyy : Real = 0.7688521813045557;
                                attribute 'σ_Iyy' : Real = 0.3723953238821935;
                                attribute Izz : Real = 0.8059909878297835;
                                attribute 'σ_Izz' : Real = 0.37017423652493897;
                                attribute Ixy : Real = 0.0014787089402329059;
                                attribute 'σ_Ixy' : Real = 0.02351283871158888;
                                attribute Ixz : Real = -0.011753972019579508;
                                attribute 'σ_Ixz' : Real = 0.022566176940390956;
                                attribute Iyz : Real = -0.012296948840622305;
                                attribute 'σ_Iyz' : Real = 0.02209918015384651;
                            }
                            part <'C.1.1.3.2.1.2.3'> 'Part 298' {
                                attribute POIconv : String = "-";
                                attribute Ipoint : Boolean = false;
                                attribute mass : Real = 0.9906643488102127;
                                attribute 'σ_mass' : Real = 0.28909372274994966;
                                attribute Cx : Real = -5.472022807225585;
                                attribute 'σ_Cx' : Real = 28.721044428837228;
                                attribute Cy : Real = 23.642810713499784;
                                attribute 'σ_Cy' : Real = 28.23690002309109;
                                attribute Cz : Real = -93.32370357587934;
                                attribute 'σ_Cz' : Real = 29.057750463592832;
                                attribute Ixx : Real = 1.3695070907128233;
                                attribute 'σ_Ixx' : Real = 0.37074144170588635;
                                attribute Iyy : Real = 1.5401452426070448;
                                attribute 'σ_Iyy' : Real = 0.3723953238821935;
                                attribute Izz : Real = 1.3913389016039324;
                                attribute 'σ_Izz' : Real = 0.37017423652493897;
                                attribute Ixy : Real = -0.0515723913759841;
                                attribute 'σ_Ixy' : Real = 0.02351283871158888;
                                attribute Ixz : Real = 0.010653319753149162;
                                attribute 'σ_Ixz' : Real = 0.022566176940390956;
                                attribute Iyz : Real = -0.007955411765144669;
                                attribute 'σ_Iyz' : Real = 0.02209918015384651;
                            }
                            part <'C.1.1.3.2.1.2.4'> 'Part 299' {
                                attribute POIconv : String = "-";
                                attribute Ipoint : Boolean = false;
                                attribute mass : Real = 0.5965689031465444;
                                attribute 'σ_mass' : Real = 0.28909372274994966;
                                attribute Cx : Real = 19.347883528098464;
                                attribute 'σ_Cx' : Real = 28.721044428837228;
                                attribute Cy : Real = -51.34479599073529;
                                attribute 'σ_Cy' : Real = 28.23690002309109;
                                attribute Cz : Real = -20.803561015054584;
                                attribute 'σ_Cz' : Real = 29.057750463592832;
                                attribute Ixx : Real = 0.7892307138756195;
                                attribute 'σ_Ixx' : Real = 0.37074144170588635;
                                attribute Iyy : Real = 0.7601693816530307;
                                attribute 'σ_Iyy' : Real = 0.3723953238821935;
                                attribute Izz : Real = 0.8082400186559422;
                                attribute 'σ_Izz' : Real = 0.37017423652493897;
                                attribute Ixy : Real = 0.023249749580558605;
                                attribute 'σ_Ixy' : Real = 0.02351283871158888;
                                attribute Ixz : Real = -0.021664098105181082;
                                attribute 'σ_Ixz' : Real = 0.022566176940390956;
                                attribute Iyz : Real = 0.044985378330058015;
                                attribute 'σ_Iyz' : Real = 0.02209918015384651;
                            }
                        }
                        part <'C.1.1.3.2.1.3'> 'Subassembly 88' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.1.3.1'> 'Part 300' {
                                attribute POIconv : String = "-";
                                attribute Ipoint : Boolean = false;
                                attribute mass : Real = 0.3302818592193071;
                                attribute 'σ_mass' : Real = 0.28909372274994966;
                                attribute Cx : Real = 18.362718960270286;
                                attribute 'σ_Cx' : Real = 28.721044428837228;
                                attribute Cy : Real = -49.72509811632335;
                                attribute 'σ_Cy' : Real = 28.23690002309109;
                                attribute Cz : Real = -7.727361470460892;
                                attribute 'σ_Cz' : Real = 29.057750463592832;
                                attribute Ixx : Real = 0.469462949777523;
                                attribute 'σ_Ixx' : Real = 0.37074144170588635;
                                attribute Iyy : Real = 0.4981432648281274;
                                attribute 'σ_Iyy' : Real = 0.3723953238821935;
                                attribute Izz : Real = 0.4917618774933188;
                                attribute 'σ_Izz' : Real = 0.37017423652493897;
                                attribute Ixy : Real = -0.010115855753077836;
                                attribute 'σ_Ixy' : Real = 0.02351283871158888;
                                attribute Ixz : Real = -0.02150208003476731;
                                attribute 'σ_Ixz' : Real = 0.022566176940390956;
                                attribute Iyz : Real = -8.7923625547887e-4;
                                attribute 'σ_Iyz' : Real = 0.02209918015384651;
                            }
                            part <'C.1.1.3.2.1.3.2'> 'Part 301' {
                                attribute POIconv : String = "-";
                                attribute Ipoint : Boolean = false;
                                attribute mass : Real = 0.3170500951097347;
                                attribute 'σ_mass' : Real = 0.28909372274994966;
                                attribute Cx : Real = 39.879792649298906;
                                attribute 'σ_Cx' : Real = 28.721044428837228;
                                attribute Cy : Real = 49.74324256181717;
                                attribute 'σ_Cy' : Real = 28.23690002309109;
                                attribute Cz : Real = -16.910056164488196;
                                attribute 'σ_Cz' : Real = 29.057750463592832;
                                attribute Ixx : Real = 0.3868403339358573;
                                attribute 'σ_Ixx' : Real = 0.37074144170588635;
                                attribute Iyy : Real = 0.4332074035148762;
                                attribute 'σ_Iyy' : Real = 0.3723953238821935;
                                attribute Izz : Real = 0.3714825106179182;
                                attribute 'σ_Izz' : Real = 0.37017423652493897;
                                attribute Ixy : Real = 0.016979672110440942;
                                attribute 'σ_Ixy' : Real = 0.02351283871158888;
                                attribute Ixz : Real = 3.085962524271642e-5;
                                attribute 'σ_Ixz' : Real = 0.022566176940390956;
                                attribute Iyz : Real = 5.943747919141626e-4;
                                attribute 'σ_Iyz' : Real = 0.02209918015384651;
                            }
                            part <'C.1.1.3.2.1.3.3'> 'Part 302' {
                                attribute POIconv : String = "-";
                                attribute Ipoint : Boolean = false;
                                attribute mass : Real = 0.004349761590827257;
                                attribute 'σ_mass' : Real = 0.28909372274994966;
                                attribute Cx : Real = -88.5775972623378;
                                attribute 'σ_Cx' : Real = 28.721044428837228;
                                attribute Cy : Real = 85.53621731698513;
                                attribute 'σ_Cy' : Real = 28.23690002309109;
                                attribute Cz : Real = -5.550558585673571;
                                attribute 'σ_Cz' : Real = 29.057750463592832;
                                attribute Ixx : Real = 0.005913005331301421;
                                attribute 'σ_Ixx' : Real = 0.37074144170588635;
                                attribute Iyy : Real = 0.005501464960847597;
                                attribute 'σ_Iyy' : Real = 0.3723953238821935;
                                attribute Izz : Real = 0.0052591730843552;
                                attribute 'σ_Izz' : Real = 0.37017423652493897;
                                attribute Ixy : Real = 4.279151971362525e-4;
                                attribute 'σ_Ixy' : Real = 0.02351283871158888;
                                attribute Ixz : Real = 2.36131770010035e-5;
                                attribute 'σ_Ixz' : Real = 0.022566176940390956;
                                attribute Iyz : Real = 2.209161769528973e-4;
                                attribute 'σ_Iyz' : Real = 0.02209918015384651;
                            }
                            part <'C.1.1.3.2.1.3.4'> 'Part 303' {
                                attribute POIconv : String = "-";
                                attribute Ipoint : Boolean = false;
                                attribute mass : Real = 0.42648385343886913;
                                attribute 'σ_mass' : Real = 0.28909372274994966;
                                attribute Cx : Real = 86.82163748890162;
                                attribute 'σ_Cx' : Real = 28.721044428837228;
                                attribute Cy : Real = 49.98750961385667;
                                attribute 'σ_Cy' : Real = 28.23690002309109;
                                attribute Cz : Real = -4.82497401535511;
                                attribute 'σ_Cz' : Real = 29.057750463592832;
                                attribute Ixx : Real = 0.6509581627977518;
                                attribute 'σ_Ixx' : Real = 0.37074144170588635;
                                attribute Iyy : Real = 0.6067174619344557;
                                attribute 'σ_Iyy' : Real = 0.3723953238821935;
                                attribute Izz : Real = 0.6184371040711442;
                                attribute 'σ_Izz' : Real = 0.37017423652493897;
                                attribute Ixy : Real = -0.022935411706845953;
                                attribute 'σ_Ixy' : Real = 0.02351283871158888;
                                attribute Ixz : Real = -0.029081380340360178;
                                attribute 'σ_Ixz' : Real = 0.022566176940390956;
                                attribute Iyz : Real = 0.013408712220088409;
                                attribute 'σ_Iyz' : Real = 0.02209918015384651;
                            }
                        }
                        part <'C.1.1.3.2.1.4'> 'Subassembly 89' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.1.4.1'> 'Part 304' {
                                attribute POIconv : String = "+";
                                attribute Ipoint : Boolean = false;
                                attribute mass : Real = 0.7463409944160376;
                                attribute 'σ_mass' : Real = 0.28909372274994966;
                                attribute Cx : Real = -26.504614809527993;
                                attribute 'σ_Cx' : Real = 28.721044428837228;
                                attribute Cy : Real = 62.05139560624957;
                                attribute 'σ_Cy' : Real = 28.23690002309109;
                                attribute Cz : Real = 61.13782003521919;
                                attribute 'σ_Cz' : Real = 29.057750463592832;
                                attribute Ixx : Real = 1.0452339481371151;
                                attribute 'σ_Ixx' : Real = 0.37074144170588635;
                                attribute Iyy : Real = 1.1456713743509077;
                                attribute 'σ_Iyy' : Real = 0.3723953238821935;
                                attribute Izz : Real = 0.9965550771022512;
                                attribute 'σ_Izz' : Real = 0.37017423652493897;
                                attribute Ixy : Real = -0.0037844778312448903;
                                attribute 'σ_Ixy' : Real = 0.02351283871158888;
                                attribute Ixz : Real = -0.018690386601199538;
                                attribute 'σ_Ixz' : Real = 0.022566176940390956;
                                attribute Iyz : Real = -0.0353752081346525;
                                attribute 'σ_Iyz' : Real = 0.02209918015384651;
                            }
                            part <'C.1.1.3.2.1.4.2'> 'Part 305' {
                                attribute POIconv : String = "-";
                                attribute Ipoint : Boolean = false;
                                attribute mass : Real = 0.07366071792808361;
                                attribute 'σ_mass' : Real = 0.28909372274994966;
                                attribute Cx : Real = -79.16469965130091;
                                attribute 'σ_Cx' : Real = 28.721044428837228;
                                attribute Cy : Real = 81.36048577725887;
                                attribute 'σ_Cy' : Real = 28.23690002309109;
                                attribute Cz : Real = 63.619013130664825;
                                attribute 'σ_Cz' : Real = 29.057750463592832;
                                attribute Ixx : Real = 0.07950071933095791;
                                attribute 'σ_Ixx' : Real = 0.37074144170588635;
                                attribute Iyy : Real = 0.08860937141400956;
                                attribute 'σ_Iyy' : Real = 0.3723953238821935;
                                attribute Izz : Real = 0.08804109037191804;
                                attribute 'σ_Izz' : Real = 0.37017423652493897;
                                attribute Ixy : Real = -0.008543395605583287;
                                attribute 'σ_Ixy' : Real = 0.02351283871158888;
                                attribute Ixz : Real = 0.00783892662881568;
                                attribute 'σ_Ixz' : Real = 0.022566176940390956;
                                attribute Iyz : Real = 0.002312820694277688;
                                attribute 'σ_Iyz' : Real = 0.02209918015384651;
                            }
                            part <'C.1.1.3.2.1.4.3'> 'Part 306' {
                                attribute POIconv : String = "+";
                                attribute Ipoint : Boolean = false;
                                attribute mass : Real = 0.7772379204537719;
                                attribute 'σ_mass' : Real = 0.28909372274994966;
                                attribute Cx : Real = -19.621654599905014;
                                attribute 'σ_Cx' : Real = 28.721044428837228;
                                attribute Cy : Real = -78.24674462899566;
                                attribute 'σ_Cy' : Real = 28.23690002309109;
                                attribute Cz : Real = 89.25165296532214;
                                attribute 'σ_Cz' : Real = 29.057750463592832;
                                attribute Ixx : Real = 0.9711164702176183;
                                attribute 'σ_Ixx' : Real = 0.37074144170588635;
                                attribute Iyy : Real = 0.9466826681114774;
                                attribute 'σ_Iyy' : Real = 0.3723953238821935;
                                attribute Izz : Real = 0.8791674095456459;
                                attribute 'σ_Izz' : Real = 0.37017423652493897;
                                attribute Ixy : Real = 0.0035185979756948505;
                                attribute 'σ_Ixy' : Real = 0.02351283871158888;
                                attribute Ixz : Real = 0.0022976645382708125;
                                attribute 'σ_Ixz' : Real = 0.022566176940390956;
                                attribute Iyz : Real = 0.0030417589459110278;
                                attribute 'σ_Iyz' : Real = 0.02209918015384651;
                            }
                            part <'C.1.1.3.2.1.4.4'> 'Part 307' {
                                attribute POIconv : String = "-";
                                attribute Ipoint : Boolean = false;
                                attribute mass : Real = 0.8501022058944218;
                                attribute 'σ_mass' : Real = 0.28909372274994966;
                                attribute Cx : Real = -51.454595290124416;
                                attribute 'σ_Cx' : Real = 28.721044428837228;
                                attribute Cy : Real = 25.23170718923211;
                                attribute 'σ_Cy' : Real = 28.23690002309109;
                                attribute Cz : Real = 21.931632049381733;
                                attribute 'σ_Cz' : Real = 29.057750463592832;
                                attribute Ixx : Real = 0.9203361436659883;
                                attribute 'σ_Ixx' : Real = 0.37074144170588635;
                                attribute Iyy : Real = 1.0513699248062658;
                                attribute 'σ_Iyy' : Real = 0.3723953238821935;
                                attribute Izz : Real = 1.0125844164820472;
                                attribute 'σ_Izz' : Real = 0.37017423652493897;
                                attribute Ixy : Real = 0.03954797218949646;
                                attribute 'σ_Ixy' : Real = 0.02351283871158888;
                                attribute Ixz : Real = -0.0855337919866877;
                                attribute 'σ_Ixz' : Real = 0.022566176940390956;
                                attribute Iyz : Real = 0.019948801103531054;
                                attribute 'σ_Iyz' : Real = 0.02209918015384651;
                            }
                        }
                    }
                    part <'C.1.1.3.2.2'> 'Assembly 25' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.2.2.1'> 'Subassembly 90' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.2.1.1'> 'Part 308' {
                                attribute POIconv : String = "-";
                                attribute Ipoint : Boolean = false;
                                attribute mass : Real = 0.9628821893972345;
                                attribute 'σ_mass' : Real = 0.28909372274994966;
                                attribute Cx : Real = -67.02563893049955;
                                attribute 'σ_Cx' : Real = 28.721044428837228;
                                attribute Cy : Real = 38.92446053214371;
                                attribute 'σ_Cy' : Real = 28.23690002309109;
                                attribute Cz : Real = -91.79585943929851;
                                attribute 'σ_Cz' : Real = 29.057750463592832;
                                attribute Ixx : Real = 1.325991570317825;
                                attribute 'σ_Ixx' : Real = 0.37074144170588635;
                                attribute Iyy : Real = 1.3767848150268163;
                                attribute 'σ_Iyy' : Real = 0.3723953238821935;
                                attribute Izz : Real = 1.331913580574206;
                                attribute 'σ_Izz' : Real = 0.37017423652493897;
                                attribute Ixy : Real = -0.08235468955166947;
                                attribute 'σ_Ixy' : Real = 0.02351283871158888;
                                attribute Ixz : Real = -0.005362268663962171;
                                attribute 'σ_Ixz' : Real = 0.022566176940390956;
                                attribute Iyz : Real = -0.08305653325092678;
                                attribute 'σ_Iyz' : Real = 0.02209918015384651;
                            }
                            part <'C.1.1.3.2.2.1.2'> 'Part 309' {
                                attribute POIconv : String = "+";
                                attribute Ipoint : Boolean = false;
                                attribute mass : Real = 0.5805594417655375;
                                attribute 'σ_mass' : Real = 0.28909372274994966;
                                attribute Cx : Real = 79.54693427309394;
                                attribute 'σ_Cx' : Real = 28.721044428837228;
                                attribute Cy : Real = 65.67559484392405;
                                attribute 'σ_Cy' : Real = 28.23690002309109;
                                attribute Cz : Real = -44.329586112871766;
                                attribute 'σ_Cz' : Real = 29.057750463592832;
                                attribute Ixx : Real = 0.7634266870756968;
                                attribute 'σ_Ixx' : Real = 0.37074144170588635;
                                attribute Iyy : Real = 0.7509323257853486;
                                attribute 'σ_Iyy' : Real = 0.3723953238821935;
                                attribute Izz : Real = 0.7493895127889785;
                                attribute 'σ_Izz' : Real = 0.37017423652493897;
                                attribute Ixy : Real = -7.868340243789797e-4;
                                attribute 'σ_Ixy' : Real = 0.02351283871158888;
                                attribute Ixz : Real = -0.003883483413904091;
                                attribute 'σ_Ixz' : Real = 0.022566176940390956;
                                attribute Iyz : Real = 0.014998158225549642;
                                attribute 'σ_Iyz' : Real = 0.02209918015384651;
                            }
                            part <'C.1.1.3.2.2.1.3'> 'Part 310' {
                                attribute POIconv : String = "+";
                                attribute Ipoint : Boolean = false;
                                attribute mass : Real = 0.006278796201571822;
                                attribute 'σ_mass' : Real = 0.28909372274994966;
                                attribute Cx : Real = -87.68620318733156;
                                attribute 'σ_Cx' : Real = 28.721044428837228;
                                attribute Cy : Real = 66.55258950777352;
                                attribute 'σ_Cy' : Real = 28.23690002309109;
                                attribute Cz : Real = 70.25857497937977;
                                attribute 'σ_Cz' : Real = 29.057750463592832;
                                attribute Ixx : Real = 0.009083717793138048;
                                attribute 'σ_Ixx' : Real = 0.37074144170588635;
                                attribute Iyy : Real = 0.00852770142378268;
                                attribute 'σ_Iyy' : Real = 0.3723953238821935;
                                attribute Izz : Real = 0.007307598921316748;
                                attribute 'σ_Izz' : Real = 0.37017423652493897;
                                attribute Ixy : Real = -7.172538256833759e-4;
                                attribute 'σ_Ixy' : Real = 0.02351283871158888;
                                attribute Ixz : Real = -2.211488279135332e-4;
                                attribute 'σ_Ixz' : Real = 0.022566176940390956;
                                attribute Iyz : Real = -2.006876692919036e-5;
                                attribute 'σ_Iyz' : Real = 0.02209918015384651;
                            }
                        }
                        part <'C.1.1.3.2.2.2'> 'Subassembly 91' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.2.2.1'> 'Part 311' {
                                attribute POIconv : String = "-";
                                attribute Ipoint : Boolean = false;
                                attribute mass : Real = 0.507306068098871;
                                attribute 'σ_mass' : Real = 0.28909372274994966;
                                attribute Cx : Real = 51.52768441475928;
                                attribute 'σ_Cx' : Real = 28.721044428837228;
                                attribute Cy : Real = -43.57835128903389;
                                attribute 'σ_Cy' : Real = 28.23690002309109;
                                attribute Cz : Real = -80.80584607087076;
                                attribute 'σ_Cz' : Real = 29.057750463592832;
                                attribute Ixx : Real = 0.5182907025904251;
                                attribute 'σ_Ixx' : Real = 0.37074144170588635;
                                attribute Iyy : Real = 0.6396566292883058;
                                attribute 'σ_Iyy' : Real = 0.3723953238821935;
                                attribute Izz : Real = 0.60675846262782;
                                attribute 'σ_Izz' : Real = 0.37017423652493897;
                                attribute Ixy : Real = 0.027774789788406237;
                                attribute 'σ_Ixy' : Real = 0.02351283871158888;
                                attribute Ixz : Real = -0.05421418779891808;
                                attribute 'σ_Ixz' : Real = 0.022566176940390956;
                                attribute Iyz : Real = 0.013214062933677433;
                                attribute 'σ_Iyz' : Real = 0.02209918015384651;
                            }
                            part <'C.1.1.3.2.2.2.2'> 'Part 312' {
                                attribute POIconv : String = "-";
                                attribute Ipoint : Boolean = false;
                                attribute mass : Real = 0.27923376768874003;
                                attribute 'σ_mass' : Real = 0.28909372274994966;
                                attribute Cx : Real = -58.8215580675751;
                                attribute 'σ_Cx' : Real = 28.721044428837228;
                                attribute Cy : Real = -27.714911568909883;
                                attribute 'σ_Cy' : Real = 28.23690002309109;
                                attribute Cz : Real = 39.66203657910228;
                                attribute 'σ_Cz' : Real = 29.057750463592832;
                                attribute Ixx : Real = 0.3003349372228094;
                                attribute 'σ_Ixx' : Real = 0.37074144170588635;
                                attribute Iyy : Real = 0.30397909106428844;
                                attribute 'σ_Iyy' : Real = 0.3723953238821935;
                                attribute Izz : Real = 0.3530848292248687;
                                attribute 'σ_Izz' : Real = 0.37017423652493897;
                                attribute Ixy : Real = -0.0016256423900652857;
                                attribute 'σ_Ixy' : Real = 0.02351283871158888;
                                attribute Ixz : Real = -0.004426881182763229;
                                attribute 'σ_Ixz' : Real = 0.022566176940390956;
                                attribute Iyz : Real = 0.01567681694051682;
                                attribute 'σ_Iyz' : Real = 0.02209918015384651;
                            }
                            part <'C.1.1.3.2.2.2.3'> 'Part 313' {
                                attribute POIconv : String = "+";
                                attribute Ipoint : Boolean = false;
                                attribute mass : Real = 0.053065631135599686;
                                attribute 'σ_mass' : Real = 0.28909372274994966;
                                attribute Cx : Real = 74.80520722456276;
                                attribute 'σ_Cx' : Real = 28.721044428837228;
                                attribute Cy : Real = -99.91779676638544;
                                attribute 'σ_Cy' : Real = 28.23690002309109;
                                attribute Cz : Real = 72.3065145779401;
                                attribute 'σ_Cz' : Real = 29.057750463592832;
                                attribute Ixx : Real = 0.06803522128108468;
                                attribute 'σ_Ixx' : Real = 0.37074144170588635;
                                attribute Iyy : Real = 0.06849965363191944;
                                attribute 'σ_Iyy' : Real = 0.3723953238821935;
                                attribute Izz : Real = 0.07269471227138315;
                                attribute 'σ_Izz' : Real = 0.37017423652493897;
                                attribute Ixy : Real = 1.5071735385599846e-4;
                                attribute 'σ_Ixy' : Real = 0.02351283871158888;
                                attribute Ixz : Real = -7.294193082956819e-4;
                                attribute 'σ_Ixz' : Real = 0.022566176940390956;
                                attribute Iyz : Real = -0.0010525329059136177;
                                attribute 'σ_Iyz' : Real = 0.02209918015384651;
                            }
                            part <'C.1.1.3.2.2.2.4'> 'Part 314' {
                                attribute POIconv : String = "+";
                                attribute Ipoint : Boolean = false;
                                attribute mass : Real = 0.025723440255038442;
                                attribute 'σ_mass' : Real = 0.28909372274994966;
                                attribute Cx : Real = -56.83076097629964;
                                attribute 'σ_Cx' : Real = 28.721044428837228;
                                attribute Cy : Real = 49.14056593552232;
                                attribute 'σ_Cy' : Real = 28.23690002309109;
                                attribute Cz : Real = -59.64905023574829;
                                attribute 'σ_Cz' : Real = 29.057750463592832;
                                attribute Ixx : Real = 0.03401345992686182;
                                attribute 'σ_Ixx' : Real = 0.37074144170588635;
                                attribute Iyy : Real = 0.03412561256690141;
                                attribute 'σ_Iyy' : Real = 0.3723953238821935;
                                attribute Izz : Real = 0.03451290554819782;
                                attribute 'σ_Izz' : Real = 0.37017423652493897;
                                attribute Ixy : Real = -3.071215644418075e-4;
                                attribute 'σ_Ixy' : Real = 0.02351283871158888;
                                attribute Ixz : Real = 8.896193491510361e-4;
                                attribute 'σ_Ixz' : Real = 0.022566176940390956;
                                attribute Iyz : Real = -7.108032788825308e-4;
                                attribute 'σ_Iyz' : Real = 0.02209918015384651;
                            }
                        }
                        part <'C.1.1.3.2.2.3'> 'Subassembly 92' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.2.3.1'> 'Part 315' {
                                attribute POIconv : String = "+";
                                attribute Ipoint : Boolean = false;
                                attribute mass : Real = 0.8841884749981109;
                                attribute 'σ_mass' : Real = 0.28909372274994966;
                                attribute Cx : Real = -2.67761186696589;
                                attribute 'σ_Cx' : Real = 28.721044428837228;
                                attribute Cy : Real = 69.39258752390742;
                                attribute 'σ_Cy' : Real = 28.23690002309109;
                                attribute Cz : Real = 46.854346012696624;
                                attribute 'σ_Cz' : Real = 29.057750463592832;
                                attribute Ixx : Real = 1.189376320613317;
                                attribute 'σ_Ixx' : Real = 0.37074144170588635;
                                attribute Iyy : Real = 1.205941083905937;
                                attribute 'σ_Iyy' : Real = 0.3723953238821935;
                                attribute Izz : Real = 1.1648997578996236;
                                attribute 'σ_Izz' : Real = 0.37017423652493897;
                                attribute Ixy : Real = 0.014061573413145526;
                                attribute 'σ_Ixy' : Real = 0.02351283871158888;
                                attribute Ixz : Real = -0.013567785908019301;
                                attribute 'σ_Ixz' : Real = 0.022566176940390956;
                                attribute Iyz : Real = -0.03654059910570495;
                                attribute 'σ_Iyz' : Real = 0.02209918015384651;
                            }
                            part <'C.1.1.3.2.2.3.2'> 'Part 316' {
                                attribute POIconv : String = "+";
                                attribute Ipoint : Boolean = false;
                                attribute mass : Real = 0.05425436808075756;
                                attribute 'σ_mass' : Real = 0.28909372274994966;
                                attribute Cx : Real = -33.90569421462715;
                                attribute 'σ_Cx' : Real = 28.721044428837228;
                                attribute Cy : Real = -9.006574749946594;
                                attribute 'σ_Cy' : Real = 28.23690002309109;
                                attribute Cz : Real = -83.4563790820539;
                                attribute 'σ_Cz' : Real = 29.057750463592832;
                                attribute Ixx : Real = 0.06582503402006419;
                                attribute 'σ_Ixx' : Real = 0.37074144170588635;
                                attribute Iyy : Real = 0.0727462769581792;
                                attribute 'σ_Iyy' : Real = 0.3723953238821935;
                                attribute Izz : Real = 0.07228960061863357;
                                attribute 'σ_Izz' : Real = 0.37017423652493897;
                                attribute Ixy : Real = -0.004232131433138974;
                                attribute 'σ_Ixy' : Real = 0.02351283871158888;
                                attribute Ixz : Real = -2.3667541681533072e-4;
                                attribute 'σ_Ixz' : Real = 0.022566176940390956;
                                attribute Iyz : Real = -0.0045218793984314505;
                                attribute 'σ_Iyz' : Real = 0.02209918015384651;
                            }
                            part <'C.1.1.3.2.2.3.3'> 'Part 317' {
                                attribute POIconv : String = "-";
                                attribute Ipoint : Boolean = false;
                                attribute mass : Real = 0.7166010126913898;
                                attribute 'σ_mass' : Real = 0.28909372274994966;
                                attribute Cx : Real = 56.1417390126735;
                                attribute 'σ_Cx' : Real = 28.721044428837228;
                                attribute Cy : Real = 47.701892303302884;
                                attribute 'σ_Cy' : Real = 28.23690002309109;
                                attribute Cz : Real = -75.77182915993035;
                                attribute 'σ_Cz' : Real = 29.057750463592832;
                                attribute Ixx : Real = 0.8076271387470669;
                                attribute 'σ_Ixx' : Real = 0.37074144170588635;
                                attribute Iyy : Real = 0.986578090013967;
                                attribute 'σ_Iyy' : Real = 0.3723953238821935;
                                attribute Izz : Real = 0.7817123876828004;
                                attribute 'σ_Izz' : Real = 0.37017423652493897;
                                attribute Ixy : Real = -0.0071684844781875045;
                                attribute 'σ_Ixy' : Real = 0.02351283871158888;
                                attribute Ixz : Real = -7.451193538291595e-4;
                                attribute 'σ_Ixz' : Real = 0.022566176940390956;
                                attribute Iyz : Real = -0.007232231292846808;
                                attribute 'σ_Iyz' : Real = 0.02209918015384651;
                            }
                        }
                        part <'C.1.1.3.2.2.4'> 'Subassembly 93' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.2.4.1'> 'Part 318' {
                                attribute POIconv : String = "+";
                                attribute Ipoint : Boolean = false;
                                attribute mass : Real = 0.88897562152659515;
                                attribute 'σ_mass' : Real = 0.28909372274994966;
                                attribute Cx : Real = -32.88555843755603;
                                attribute 'σ_Cx' : Real = 28.721044428837228;
                                attribute Cy : Real = -45.80324599519372;
                                attribute 'σ_Cy' : Real = 28.23690002309109;
                                attribute Cz : Real = 42.835584888234735;
                                attribute 'σ_Cz' : Real = 29.057750463592832;
                                attribute Ixx : Real = 1.1406320663721565;
                                attribute 'σ_Ixx' : Real = 0.37074144170588635;
                                attribute Iyy : Real = 1.3118710687285449;
                                attribute 'σ_Iyy' : Real = 0.3723953238821935;
                                attribute Izz : Real = 1.218674073820137;
                                attribute 'σ_Izz' : Real = 0.37017423652493897;
                                attribute Ixy : Real = 0.07079337227403804;
                                attribute 'σ_Ixy' : Real = 0.02351283871158888;
                                attribute Ixz : Real = 0.02208765741710296;
                                attribute 'σ_Ixz' : Real = 0.022566176940390956;
                                attribute Iyz : Real = 0.05792516059510751;
                                attribute 'σ_Iyz' : Real = 0.02209918015384651;
                            }
                            part <'C.1.1.3.2.2.4.2'> 'Part 319' {
                                attribute POIconv : String = "+";
                                attribute Ipoint : Boolean = false;
                                attribute mass : Real = 0.9409341678854544;
                                attribute 'σ_mass' : Real = 0.28909372274994966;
                                attribute Cx : Real = 97.86626021377742;
                                attribute 'σ_Cx' : Real = 28.721044428837228;
                                attribute Cy : Real = -19.441911624744534;
                                attribute 'σ_Cy' : Real = 28.23690002309109;
                                attribute Cz : Real = -32.84712606109679;
                                attribute 'σ_Cz' : Real = 29.057750463592832;
                                attribute Ixx : Real = 1.3635594218624387;
                                attribute 'σ_Ixx' : Real = 0.37074144170588635;
                                attribute Iyy : Real = 1.25727050418053;
                                attribute 'σ_Iyy' : Real = 0.3723953238821935;
                                attribute Izz : Real = 1.1556787094732983;
                                attribute 'σ_Izz' : Real = 0.37017423652493897;
                                attribute Ixy : Real = 0.10141737961065309;
                                attribute 'σ_Ixy' : Real = 0.02351283871158888;
                                attribute Ixz : Real = -0.016584724243580835;
                                attribute 'σ_Ixz' : Real = 0.022566176940390956;
                                attribute Iyz : Real = 0.0080741474919051575;
                                attribute 'σ_Iyz' : Real = 0.02209918015384651;
                            }
                            part <'C.1.1.3.2.2.4.3'> 'Part 320' {
                                attribute POIconv : String = "-";
                                attribute Ipoint : Boolean = false;
                                attribute mass : Real = 0.9677422760413028;
                                attribute 'σ_mass' : Real = 0.28909372274994966;
                                attribute Cx : Real = 54.965718602761626;
                                attribute 'σ_Cx' : Real = 28.721044428837228;
                                attribute Cy : Real = 39.3487214576453;
                                attribute 'σ_Cy' : Real = 28.23690002309109;
                                attribute Cz : Real = 40.10970429517329;
                                attribute 'σ_Cz' : Real = 29.057750463592832;
                                attribute Ixx : Real = 0.9196409710813536;
                                attribute 'σ_Ixx' : Real = 0.37074144170588635;
                                attribute Iyy : Real = 0.940467217425216;
                                attribute 'σ_Iyy' : Real = 0.3723953238821935;
                                attribute Izz : Real = 0.9065334421784903;
                                attribute 'σ_Izz' : Real = 0.37017423652493897;
                                attribute Ixy : Real = -0.005298217016151351;
                                attribute 'σ_Ixy' : Real = 0.02351283871158888;
                                attribute Ixz : Real = -0.021174314867082475;
                                attribute 'σ_Ixz' : Real = 0.022566176940390956;
                                attribute Iyz : Real = 0.010126942005534816;
                                attribute 'σ_Iyz' : Real = 0.02209918015384651;
                            }
                        }
                        part <'C.1.1.3.2.2.5'> 'Subassembly 94' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.2.5.1'> 'Part 321' {
                                attribute POIconv : String = "+";
                                attribute Ipoint : Boolean = false;
                                attribute mass : Real = 0.38982657161960377;
                                attribute 'σ_mass' : Real = 0.28909372274994966;
                                attribute Cx : Real = 10.995585890486836;
                                attribute 'σ_Cx' : Real = 28.721044428837228;
                                attribute Cy : Real = 55.75889269821346;
                                attribute 'σ_Cy' : Real = 28.23690002309109;
                                attribute Cz : Real = 4.62368200533092;
                                attribute 'σ_Cz' : Real = 29.057750463592832;
                                attribute Ixx : Real = 0.593875336164907;
                                attribute 'σ_Ixx' : Real = 0.37074144170588635;
                                attribute Iyy : Real = 0.570095051626122;
                                attribute 'σ_Iyy' : Real = 0.3723953238821935;
                                attribute Izz : Real = 0.5977647188323771;
                                attribute 'σ_Izz' : Real = 0.37017423652493897;
                                attribute Ixy : Real = -0.008331680534444092;
                                attribute 'σ_Ixy' : Real = 0.02351283871158888;
                                attribute Ixz : Real = -0.0018383308505807877;
                                attribute 'σ_Ixz' : Real = 0.022566176940390956;
                                attribute Iyz : Real = -0.00862451112800756;
                                attribute 'σ_Iyz' : Real = 0.02209918015384651;
                            }
                            part <'C.1.1.3.2.2.5.2'> 'Part 322' {
                                attribute POIconv : String = "-";
                                attribute Ipoint : Boolean = false;
                                attribute mass : Real = 0.7070334905567579;
                                attribute 'σ_mass' : Real = 0.28909372274994966;
                                attribute Cx : Real = 49.39921302720904;
                                attribute 'σ_Cx' : Real = 28.721044428837228;
                                attribute Cy : Real = -95.53828649222851;
                                attribute 'σ_Cy' : Real = 28.23690002309109;
                                attribute Cz : Real = -34.6599371638149;
                                attribute 'σ_Cz' : Real = 29.057750463592832;
                                attribute Ixx : Real = 0.8683287334960428;
                                attribute 'σ_Ixx' : Real = 0.37074144170588635;
                                attribute Iyy : Real = 0.8252912129048904;
                                attribute 'σ_Iyy' : Real = 0.3723953238821935;
                                attribute Izz : Real = 0.8172652405743035;
                                attribute 'σ_Izz' : Real = 0.37017423652493897;
                                attribute Ixy : Real = -0.04404569806229386;
                                attribute 'σ_Ixy' : Real = 0.02351283871158888;
                                attribute Ixz : Real = -0.052528960149597084;
                                attribute 'σ_Ixz' : Real = 0.022566176940390956;
                                attribute Iyz : Real = 0.02704553983832496;
                                attribute 'σ_Iyz' : Real = 0.02209918015384651;
                            }
                        }
                    }
                    part <'C.1.1.3.2.3'> 'Assembly 26' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.2.3.1'> 'Subassembly 95' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.3.1.1'> 'Part 323' {
                                attribute POIconv : String = "+";
                                attribute Ipoint : Boolean = false;
                                attribute mass : Real = 0.3878688797953073;
                                attribute 'σ_mass' : Real = 0.28909372274994966;
                                attribute Cx : Real = -43.5926400590688;
                                attribute 'σ_Cx' : Real = 28.721044428837228;
                                attribute Cy : Real = -91.387655492872;
                                attribute 'σ_Cy' : Real = 28.23690002309109;
                                attribute Cz : Real = -48.86414282955229;
                                attribute 'σ_Cz' : Real = 29.057750463592832;
                                attribute Ixx : Real = 0.42184964004594716;
                                attribute 'σ_Ixx' : Real = 0.37074144170588635;
                                attribute Iyy : Real = 0.41817877777390067;
                                attribute 'σ_Iyy' : Real = 0.3723953238821935;
                                attribute Izz : Real = 0.4444434323184965;
                                attribute 'σ_Izz' : Real = 0.37017423652493897;
                                attribute Ixy : Real = -0.005996255359739961;
                                attribute 'σ_Ixy' : Real = 0.02351283871158888;
                                attribute Ixz : Real = -0.001913937062915384;
                                attribute 'σ_Ixz' : Real = 0.022566176940390956;
                                attribute Iyz : Real = 0.002494752411062521;
                                attribute 'σ_Iyz' : Real = 0.02209918015384651;
                            }
                            part <'C.1.1.3.2.3.1.2'> 'Part 324' {
                                attribute POIconv : String = "+";
                                attribute Ipoint : Boolean = false;
                                attribute mass : Real = 0.13268335476797075;
                                attribute 'σ_mass' : Real = 0.28909372274994966;
                                attribute Cx : Real = 8.055883552879095;
                                attribute 'σ_Cx' : Real = 28.721044428837228;
                                attribute Cy : Real = 10.273663187399507;
                                attribute 'σ_Cy' : Real = 28.23690002309109;
                                attribute Cz : Real = -61.78037249483168;
                                attribute 'σ_Cz' : Real = 29.057750463592832;
                                attribute Ixx : Real = 0.14959516876052975;
                                attribute 'σ_Ixx' : Real = 0.37074144170588635;
                                attribute Iyy : Real = 0.15794006943016725;
                                attribute 'σ_Iyy' : Real = 0.3723953238821935;
                                attribute Izz : Real = 0.17241936283603132;
                                attribute 'σ_Izz' : Real = 0.37017423652493897;
                                attribute Ixy : Real = -0.004380634094447134;
                                attribute 'σ_Ixy' : Real = 0.02351283871158888;
                                attribute Ixz : Real = -0.004021442459459437;
                                attribute 'σ_Ixz' : Real = 0.022566176940390956;
                                attribute Iyz : Real = -0.01596463004876237;
                                attribute 'σ_Iyz' : Real = 0.02209918015384651;
                            }
                        }
                        part <'C.1.1.3.2.3.2'> 'Subassembly 96' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.3.2.1'> 'Part 325' {
                                attribute POIconv : String = "+";
                                attribute Ipoint : Boolean = false;
                                attribute mass : Real = 0.5126135343068745;
                                attribute 'σ_mass' : Real = 0.28909372274994966;
                                attribute Cx : Real = -88.23857898823917;
                                attribute 'σ_Cx' : Real = 28.721044428837228;
                                attribute Cy : Real = 62.4933329410851;
                                attribute 'σ_Cy' : Real = 28.23690002309109;
                                attribute Cz : Real = -67.9025755263865;
                                attribute 'σ_Cz' : Real = 29.057750463592832;
                                attribute Ixx : Real = 0.48396662788528616;
                                attribute 'σ_Ixx' : Real = 0.37074144170588635;
                                attribute Iyy : Real = 0.5335215442545749;
                                attribute 'σ_Iyy' : Real = 0.3723953238821935;
                                attribute Izz : Real = 0.479101358373085;
                                attribute 'σ_Izz' : Real = 0.37017423652493897;
                                attribute Ixy : Real = 0.001507180322832044;
                                attribute 'σ_Ixy' : Real = 0.02351283871158888;
                                attribute Ixz : Real = 0.03241985306728057;
                                attribute 'σ_Ixz' : Real = 0.022566176940390956;
                                attribute Iyz : Real = 2.4370241434969285e-5;
                                attribute 'σ_Iyz' : Real = 0.02209918015384651;
                            }
                            part <'C.1.1.3.2.3.2.2'> 'Part 326' {
                                attribute POIconv : String = "+";
                                attribute Ipoint : Boolean = false;
                                attribute mass : Real = 0.534949642943684;
                                attribute 'σ_mass' : Real = 0.28909372274994966;
                                attribute Cx : Real = 52.64794761314988;
                                attribute 'σ_Cx' : Real = 28.721044428837228;
                                attribute Cy : Real = 46.47494424134493;
                                attribute 'σ_Cy' : Real = 28.23690002309109;
                                attribute Cz : Real = 28.902780450880527;
                                attribute 'σ_Cz' : Real = 29.057750463592832;
                                attribute Ixx : Real = 0.7796976661674203;
                                attribute 'σ_Ixx' : Real = 0.37074144170588635;
                                attribute Iyy : Real = 0.7908133779174921;
                                attribute 'σ_Iyy' : Real = 0.3723953238821935;
                                attribute Izz : Real = 0.8014815913535941;
                                attribute 'σ_Izz' : Real = 0.37017423652493897;
                                attribute Ixy : Real = -0.01290336293397582;
                                attribute 'σ_Ixy' : Real = 0.02351283871158888;
                                attribute Ixz : Real = 8.880044080371539e-4;
                                attribute 'σ_Ixz' : Real = 0.022566176940390956;
                                attribute Iyz : Real = 0.017782637268793578;
                                attribute 'σ_Iyz' : Real = 0.02209918015384651;
                            }
                        }
                        part <'C.1.1.3.2.3.3'> 'Subassembly 97' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.3.3.1'> 'Part 327' {
                                attribute POIconv : String = "-";
                                attribute Ipoint : Boolean = false;
                                attribute mass : Real = 0.829036572795827;
                                attribute 'σ_mass' : Real = 0.28909372274994966;
                                attribute Cx : Real = 46.66926125064492;
                                attribute 'σ_Cx' : Real = 28.721044428837228;
                                attribute Cy : Real = 90.90984002687037;
                                attribute 'σ_Cy' : Real = 28.23690002309109;
                                attribute Cz : Real = -97.02342553064227;
                                attribute 'σ_Cz' : Real = 29.057750463592832;
                                attribute Ixx : Real = 0.792048226688685;
                                attribute 'σ_Ixx' : Real = 0.37074144170588635;
                                attribute Iyy : Real = 0.9074065093255873;
                                attribute 'σ_Iyy' : Real = 0.3723953238821935;
                                attribute Izz : Real = 0.8705383520500798;
                                attribute 'σ_Izz' : Real = 0.37017423652493897;
                                attribute Ixy : Real = -0.002907549974660929;
                                attribute 'σ_Ixy' : Real = 0.02351283871158888;
                                attribute Ixz : Real = -0.004094885363753678;
                                attribute 'σ_Ixz' : Real = 0.022566176940390956;
                                attribute Iyz : Real = 0.024382285112802046;
                                attribute 'σ_Iyz' : Real = 0.02209918015384651;
                            }
                            part <'C.1.1.3.2.3.3.2'> 'Part 328' {
                                attribute POIconv : String = "+";
                                attribute Ipoint : Boolean = false;
                                attribute mass : Real = 0.17266600727359765;
                                attribute 'σ_mass' : Real = 0.28909372274994966;
                                attribute Cx : Real = 32.73006435483694;
                                attribute 'σ_Cx' : Real = 28.721044428837228;
                                attribute Cy : Real = 25.773396529257298;
                                attribute 'σ_Cy' : Real = 28.23690002309109;
                                attribute Cz : Real = -6.840196717530489;
                                attribute 'σ_Cz' : Real = 29.057750463592832;
                                attribute Ixx : Real = 0.18975978613601396;
                                attribute 'σ_Ixx' : Real = 0.37074144170588635;
                                attribute Iyy : Real = 0.16764062792869464;
                                attribute 'σ_Iyy' : Real = 0.3723953238821935;
                                attribute Izz : Real = 0.18417335811917462;
                                attribute 'σ_Izz' : Real = 0.37017423652493897;
                                attribute Ixy : Real = 0.004465007722107403;
                                attribute 'σ_Ixy' : Real = 0.02351283871158888;
                                attribute Ixz : Real = -0.007410885440029033;
                                attribute 'σ_Ixz' : Real = 0.022566176940390956;
                                attribute Iyz : Real = -0.006391626421596712;
                                attribute 'σ_Iyz' : Real = 0.02209918015384651;
                            }
                        }
                    }
                    part <'C.1.1.3.2.4'> 'Assembly 27' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.2.4.1'> 'Subassembly 98' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.4.1.1'> 'Part 329' {
                                attribute POIconv : String = "-";
                                attribute Ipoint : Boolean = false;
                                attribute mass : Real = 0.1287167886684183;
                                attribute 'σ_mass' : Real = 0.28909372274994966;
                                attribute Cx : Real = 87.03090269118547;
                                attribute 'σ_Cx' : Real = 28.721044428837228;
                                attribute Cy : Real = -30.540409218519926;
                                attribute 'σ_Cy' : Real = 28.23690002309109;
                                attribute Cz : Real = 90.15979957766831;
                                attribute 'σ_Cz' : Real = 29.057750463592832;
                                attribute Ixx : Real = 0.16228324661940166;
                                attribute 'σ_Ixx' : Real = 0.37074144170588635;
                                attribute Iyy : Real = 0.18592483896238873;
                                attribute 'σ_Iyy' : Real = 0.3723953238821935;
                                attribute Izz : Real = 0.169379665314911;
                                attribute 'σ_Izz' : Real = 0.37017423652493897;
                                attribute Ixy : Real = -0.005206167910981763;
                                attribute 'σ_Ixy' : Real = 0.02351283871158888;
                                attribute Ixz : Real = -3.557462758003533e-4;
                                attribute 'σ_Ixz' : Real = 0.022566176940390956;
                                attribute Iyz : Real = -0.012137712710591424;
                                attribute 'σ_Iyz' : Real = 0.02209918015384651;
                            }
                            part <'C.1.1.3.2.4.1.2'> 'Part 330' {
                                attribute POIconv : String = "-";
                                attribute Ipoint : Boolean = false;
                                attribute mass : Real = 0.7194973043771461;
                                attribute 'σ_mass' : Real = 0.28909372274994966;
                                attribute Cx : Real = -5.321806250140071;
                                attribute 'σ_Cx' : Real = 28.721044428837228;
                                attribute Cy : Real = 5.8911309111863375;
                                attribute 'σ_Cy' : Real = 28.23690002309109;
                                attribute Cz : Real = 64.91381684318185;
                                attribute 'σ_Cz' : Real = 29.057750463592832;
                                attribute Ixx : Real = 0.7433649994239266;
                                attribute 'σ_Ixx' : Real = 0.37074144170588635;
                                attribute Iyy : Real = 0.7614583436374497;
                                attribute 'σ_Iyy' : Real = 0.3723953238821935;
                                attribute Izz : Real = 0.7599770598861778;
                                attribute 'σ_Izz' : Real = 0.37017423652493897;
                                attribute Ixy : Real = -0.0073631579731272675;
                                attribute 'σ_Ixy' : Real = 0.02351283871158888;
                                attribute Ixz : Real = 0.01065898338305345;
                                attribute 'σ_Ixz' : Real = 0.022566176940390956;
                                attribute Iyz : Real = 0.010820393022586878;
                                attribute 'σ_Iyz' : Real = 0.02209918015384651;
                            }
                            part <'C.1.1.3.2.4.1.3'> 'Part 331' {
                                attribute POIconv : String = "+";
                                attribute Ipoint : Boolean = false;
                                attribute mass : Real = 0.9811546714256983;
                                attribute 'σ_mass' : Real = 0.28909372274994966;
                                attribute Cx : Real = -26.812841603532434;
                                attribute 'σ_Cx' : Real = 28.721044428837228;
                                attribute Cy : Real = 52.877956395968795;
                                attribute 'σ_Cy' : Real = 28.23690002309109;
                                attribute Cz : Real = -78.44380689784884;
                                attribute 'σ_Cz' : Real = 29.057750463592832;
                                attribute Ixx : Real = 1.1952775255256611;
                                attribute 'σ_Ixx' : Real = 0.37074144170588635;
                                attribute Iyy : Real = 1.1333585747959691;
                                attribute 'σ_Iyy' : Real = 0.3723953238821935;
                                attribute Izz : Real = 1.2088887158634742;
                                attribute 'σ_Izz' : Real = 0.37017423652493897;
                                attribute Ixy : Real = 0.04448588940602053;
                                attribute 'σ_Ixy' : Real = 0.02351283871158888;
                                attribute Ixz : Real = 0.014076505407049527;
                                attribute 'σ_Ixz' : Real = 0.022566176940390956;
                                attribute Iyz : Real = 0.030402675473276016;
                                attribute 'σ_Iyz' : Real = 0.02209918015384651;
                            }
                        }
                        part <'C.1.1.3.2.4.2'> 'Subassembly 99' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.4.2.1'> 'Part 332' {
                                attribute POIconv : String = "+";
                                attribute Ipoint : Boolean = false;
                                attribute mass : Real = 0.8908846303960308;
                                attribute 'σ_mass' : Real = 0.28909372274994966;
                                attribute Cx : Real = 6.145137874409556;
                                attribute 'σ_Cx' : Real = 28.721044428837228;
                                attribute Cy : Real = 30.200060736387968;
                                attribute 'σ_Cy' : Real = 28.23690002309109;
                                attribute Cz : Real = 86.38933976180851;
                                attribute 'σ_Cz' : Real = 29.057750463592832;
                                attribute Ixx : Real = 1.1732807924076296;
                                attribute 'σ_Ixx' : Real = 0.37074144170588635;
                                attribute Iyy : Real = 1.2262073962193647;
                                attribute 'σ_Iyy' : Real = 0.3723953238821935;
                                attribute Izz : Real = 1.1639888072078595;
                                attribute 'σ_Izz' : Real = 0.37017423652493897;
                                attribute Ixy : Real = 0.08138156012891873;
                                attribute 'σ_Ixy' : Real = 0.02351283871158888;
                                attribute Ixz : Real = -0.06547237091048538;
                                attribute 'σ_Ixz' : Real = 0.022566176940390956;
                                attribute Iyz : Real = 0.016495638048970227;
                                attribute 'σ_Iyz' : Real = 0.02209918015384651;
                            }
                            part <'C.1.1.3.2.4.2.2'> 'Part 333' {
                                attribute POIconv : String = "-";
                                attribute Ipoint : Boolean = false;
                                attribute mass : Real = 0.10032512529427186;
                                attribute 'σ_mass' : Real = 0.28909372274994966;
                                attribute Cx : Real = 92.65729235485196;
                                attribute 'σ_Cx' : Real = 28.721044428837228;
                                attribute Cy : Real = -89.4319798797369;
                                attribute 'σ_Cy' : Real = 28.23690002309109;
                                attribute Cz : Real = 25.90523068793118;
                                attribute 'σ_Cz' : Real = 29.057750463592832;
                                attribute Ixx : Real = 0.11913864855595321;
                                attribute 'σ_Ixx' : Real = 0.37074144170588635;
                                attribute Iyy : Real = 0.134912528368046;
                                attribute 'σ_Iyy' : Real = 0.3723953238821935;
                                attribute Izz : Real = 0.12936075126750263;
                                attribute 'σ_Izz' : Real = 0.37017423652493897;
                                attribute Ixy : Real = 0.0073934246424274975;
                                attribute 'σ_Ixy' : Real = 0.02351283871158888;
                                attribute Ixz : Real = -0.007472614650957768;
                                attribute 'σ_Ixz' : Real = 0.022566176940390956;
                                attribute Iyz : Real = -0.006519047686285644;
                                attribute 'σ_Iyz' : Real = 0.02209918015384651;
                            }
                            part <'C.1.1.3.2.4.2.3'> 'Part 334' {
                                attribute POIconv : String = "-";
                                attribute Ipoint : Boolean = false;
                                attribute mass : Real = 0.12425316546182148;
                                attribute 'σ_mass' : Real = 0.28909372274994966;
                                attribute Cx : Real = 43.277207762002945;
                                attribute 'σ_Cx' : Real = 28.721044428837228;
                                attribute Cy : Real = 40.1331914588809;
                                attribute 'σ_Cy' : Real = 28.23690002309109;
                                attribute Cz : Real = 45.36066073924303;
                                attribute 'σ_Cz' : Real = 29.057750463592832;
                                attribute Ixx : Real = 0.16995944008708636;
                                attribute 'σ_Ixx' : Real = 0.37074144170588635;
                                attribute Iyy : Real = 0.1719286949193182;
                                attribute 'σ_Iyy' : Real = 0.3723953238821935;
                                attribute Izz : Real = 0.1619421745124618;
                                attribute 'σ_Izz' : Real = 0.37017423652493897;
                                attribute Ixy : Real = 3.326645094867894e-5;
                                attribute 'σ_Ixy' : Real = 0.02351283871158888;
                                attribute Ixz : Real = 0.0014322597037123236;
                                attribute 'σ_Ixz' : Real = 0.022566176940390956;
                                attribute Iyz : Real = -0.001125542427615782;
                                attribute 'σ_Iyz' : Real = 0.02209918015384651;
                            }
                        }
                        part <'C.1.1.3.2.4.3'> 'Subassembly 100' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.4.3.1'> 'Part 335' {
                                attribute POIconv : String = "-";
                                attribute Ipoint : Boolean = false;
                                attribute mass : Real = 0.8138346412456594;
                                attribute 'σ_mass' : Real = 0.28909372274994966;
                                attribute Cx : Real = -19.35315211303532;
                                attribute 'σ_Cx' : Real = 28.721044428837228;
                                attribute Cy : Real = -9.34449820779264;
                                attribute 'σ_Cy' : Real = 28.23690002309109;
                                attribute Cz : Real = 11.100184358656406;
                                attribute 'σ_Cz' : Real = 29.057750463592832;
                                attribute Ixx : Real = 1.254307671626655;
                                attribute 'σ_Ixx' : Real = 0.37074144170588635;
                                attribute Iyy : Real = 1.2892499073621049;
                                attribute 'σ_Iyy' : Real = 0.3723953238821935;
                                attribute Izz : Real = 1.2123385561143551;
                                attribute 'σ_Izz' : Real = 0.37017423652493897;
                                attribute Ixy : Real = 0.00475683828348402;
                                attribute 'σ_Ixy' : Real = 0.02351283871158888;
                                attribute Ixz : Real = -0.005411595769007989;
                                attribute 'σ_Ixz' : Real = 0.022566176940390956;
                                attribute Iyz : Real = 0.030432322462455426;
                                attribute 'σ_Iyz' : Real = 0.02209918015384651;
                            }
                            part <'C.1.1.3.2.4.3.2'> 'Part 336' {
                                attribute POIconv : String = "-";
                                attribute Ipoint : Boolean = false;
                                attribute mass : Real = 0.44453583809034897;
                                attribute 'σ_mass' : Real = 0.28909372274994966;
                                attribute Cx : Real = -38.185068173334;
                                attribute 'σ_Cx' : Real = 28.721044428837228;
                                attribute Cy : Real = -54.80590360239148;
                                attribute 'σ_Cy' : Real = 28.23690002309109;
                                attribute Cz : Real = 76.77488313056529;
                                attribute 'σ_Cz' : Real = 29.057750463592832;
                                attribute Ixx : Real = 0.5605673530624556;
                                attribute 'σ_Ixx' : Real = 0.37074144170588635;
                                attribute Iyy : Real = 0.5885100498271254;
                                attribute 'σ_Iyy' : Real = 0.3723953238821935;
                                attribute Izz : Real = 0.4944968784011927;
                                attribute 'σ_Izz' : Real = 0.37017423652493897;
                                attribute Ixy : Real = 0.0011743317180756795;
                                attribute 'σ_Ixy' : Real = 0.02351283871158888;
                                attribute Ixz : Real = 0.017871565634935114;
                                attribute 'σ_Ixz' : Real = 0.022566176940390956;
                                attribute Iyz : Real = -0.0019844118834329845;
                                attribute 'σ_Iyz' : Real = 0.02209918015384651;
                            }
                        }
                        part <'C.1.1.3.2.4.4'> 'Subassembly 101' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.2.4.4.1'> 'Part 337' {
                                attribute POIconv : String = "+";
                                attribute Ipoint : Boolean = false;
                                attribute mass : Real = 0.9935060153647791;
                                attribute 'σ_mass' : Real = 0.28909372274994966;
                                attribute Cx : Real = 99.54300043173134;
                                attribute 'σ_Cx' : Real = 28.721044428837228;
                                attribute Cy : Real = 52.90783024393022;
                                attribute 'σ_Cy' : Real = 28.23690002309109;
                                attribute Cz : Real = -3.098144009709358;
                                attribute 'σ_Cz' : Real = 29.057750463592832;
                                attribute Ixx : Real = 1.2726673316890742;
                                attribute 'σ_Ixx' : Real = 0.37074144170588635;
                                attribute Iyy : Real = 1.104507471678157;
                                attribute 'σ_Iyy' : Real = 0.3723953238821935;
                                attribute Izz : Real = 1.2862151596833427;
                                attribute 'σ_Izz' : Real = 0.37017423652493897;
                                attribute Ixy : Real = 0.113966584528572;
                                attribute 'σ_Ixy' : Real = 0.02351283871158888;
                                attribute Ixz : Real = -0.06579783463571051;
                                attribute 'σ_Ixz' : Real = 0.022566176940390956;
                                attribute Iyz : Real = 0.04940191283725343;
                                attribute 'σ_Iyz' : Real = 0.02209918015384651;
                            }
                            part <'C.1.1.3.2.4.4.2'> 'Part 338' {
                                attribute POIconv : String = "+";
                                attribute Ipoint : Boolean = false;
                                attribute mass : Real = 0.831485853352584;
                                attribute 'σ_mass' : Real = 0.28909372274994966;
                                attribute Cx : Real = -83.13076198101044;
                                attribute 'σ_Cx' : Real = 28.721044428837228;
                                attribute Cy : Real = -7.2145487647503614;
                                attribute 'σ_Cy' : Real = 28.23690002309109;
                                attribute Cz : Real = 24.929682817310095;
                                attribute 'σ_Cz' : Real = 29.057750463592832;
                                attribute Ixx : Real = 1.1061638413519386;
                                attribute 'σ_Ixx' : Real = 0.37074144170588635;
                                attribute Iyy : Real = 0.9906589384755864;
                                attribute 'σ_Iyy' : Real = 0.3723953238821935;
                                attribute Izz : Real = 1.1828486285053241;
                                attribute 'σ_Izz' : Real = 0.37017423652493897;
                                attribute Ixy : Real = -0.024591749429249916;
                                attribute 'σ_Ixy' : Real = 0.02351283871158888;
                                attribute Ixz : Real = -0.027798027141805084;
                                attribute 'σ_Ixz' : Real = 0.022566176940390956;
                                attribute Iyz : Real = -0.06585028412634386;
                                attribute 'σ_Iyz' : Real = 0.02209918015384651;
                            }
                        }
                    }
                }
                part <'C.1.1.3.3'> 'Subsystem 8' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.3.3.1'> 'Assembly 28' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.3.1.1'> 'Subassembly 102' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.1.1.1'> 'Part 339' {
                                attribute POIconv : String = "+";
                                attribute Ipoint : Boolean = false;
                                attribute mass : Real = 0.17296256762440315;
                                attribute 'σ_mass' : Real = 0.28909372274994966;
                                attribute Cx : Real = -14.564425311982632;
                                attribute 'σ_Cx' : Real = 28.721044428837228;
                                attribute Cy : Real = -26.097243139520288;
                                attribute 'σ_Cy' : Real = 28.23690002309109;
                                attribute Cz : Real = 68.29932532273233;
                                attribute 'σ_Cz' : Real = 29.057750463592832;
                                attribute Ixx : Real = 0.23515190848664183;
                                attribute 'σ_Ixx' : Real = 0.37074144170588635;
                                attribute Iyy : Real = 0.24636589810555753;
                                attribute 'σ_Iyy' : Real = 0.3723953238821935;
                                attribute Izz : Real = 0.23377505428179532;
                                attribute 'σ_Izz' : Real = 0.37017423652493897;
                                attribute Ixy : Real = 9.190094128724061e-4;
                                attribute 'σ_Ixy' : Real = 0.02351283871158888;
                                attribute Ixz : Real = -0.010515800318927333;
                                attribute 'σ_Ixz' : Real = 0.022566176940390956;
                                attribute Iyz : Real = 0.002593748427671645;
                                attribute 'σ_Iyz' : Real = 0.02209918015384651;
                            }
                            part <'C.1.1.3.3.1.1.2'> 'Part 340' {
                                attribute POIconv : String = "+";
                                attribute Ipoint : Boolean = false;
                                attribute mass : Real = 0.9838198948616628;
                                attribute 'σ_mass' : Real = 0.28909372274994966;
                                attribute Cx : Real = -14.145324239507318;
                                attribute 'σ_Cx' : Real = 28.721044428837228;
                                attribute Cy : Real = -73.95228827372193;
                                attribute 'σ_Cy' : Real = 28.23690002309109;
                                attribute Cz : Real = -77.64726332388818;
                                attribute 'σ_Cz' : Real = 29.057750463592832;
                                attribute Ixx : Real = 1.272949086677975;
                                attribute 'σ_Ixx' : Real = 0.37074144170588635;
                                attribute Iyy : Real = 1.1470384580883433;
                                attribute 'σ_Iyy' : Real = 0.3723953238821935;
                                attribute Izz : Real = 1.2795345707875208;
                                attribute 'σ_Izz' : Real = 0.37017423652493897;
                                attribute Ixy : Real = -0.06831570111704816;
                                attribute 'σ_Ixy' : Real = 0.02351283871158888;
                                attribute Ixz : Real = -0.030336452443956587;
                                attribute 'σ_Ixz' : Real = 0.022566176940390956;
                                attribute Iyz : Real = 0.1408859925617021;
                                attribute 'σ_Iyz' : Real = 0.02209918015384651;
                            }
                        }
                        part <'C.1.1.3.3.1.2'> 'Subassembly 103' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.1.2.1'> 'Part 341' {
                                attribute POIconv : String = "-";
                                attribute Ipoint : Boolean = false;
                                attribute mass : Real = 0.5552727924224455;
                                attribute 'σ_mass' : Real = 0.28909372274994966;
                                attribute Cx : Real = 45.22345131263137;
                                attribute 'σ_Cx' : Real = 28.721044428837228;
                                attribute Cy : Real = 99.64423952624202;
                                attribute 'σ_Cy' : Real = 28.23690002309109;
                                attribute Cz : Real = -92.10035386495292;
                                attribute 'σ_Cz' : Real = 29.057750463592832;
                                attribute Ixx : Real = 0.6266058186470491;
                                attribute 'σ_Ixx' : Real = 0.37074144170588635;
                                attribute Iyy : Real = 0.6183279141637241;
                                attribute 'σ_Iyy' : Real = 0.3723953238821935;
                                attribute Izz : Real = 0.6721429327674253;
                                attribute 'σ_Izz' : Real = 0.37017423652493897;
                                attribute Ixy : Real = 0.014988545156790763;
                                attribute 'σ_Ixy' : Real = 0.02351283871158888;
                                attribute Ixz : Real = -0.042082998472465646;
                                attribute 'σ_Ixz' : Real = 0.022566176940390956;
                                attribute Iyz : Real = -0.0326383529731137;
                                attribute 'σ_Iyz' : Real = 0.02209918015384651;
                            }
                            part <'C.1.1.3.3.1.2.2'> 'Part 342' {
                                attribute POIconv : String = "+";
                                attribute Ipoint : Boolean = false;
                                attribute mass : Real = 0.6642862837191206;
                                attribute 'σ_mass' : Real = 0.28909372274994966;
                                attribute Cx : Real = -0.12150341644883156;
                                attribute 'σ_Cx' : Real = 28.721044428837228;
                                attribute Cy : Real = -22.469228319823742;
                                attribute 'σ_Cy' : Real = 28.23690002309109;
                                attribute Cz : Real = 3.6420139484107494;
                                attribute 'σ_Cz' : Real = 29.057750463592832;
                                attribute Ixx : Real = 0.788842049384512;
                                attribute 'σ_Ixx' : Real = 0.37074144170588635;
                                attribute Iyy : Real = 0.8668521507371356;
                                attribute 'σ_Iyy' : Real = 0.3723953238821935;
                                attribute Izz : Real = 0.7379916356314895;
                                attribute 'σ_Izz' : Real = 0.37017423652493897;
                                attribute Ixy : Real = -0.010146073839353233;
                                attribute 'σ_Ixy' : Real = 0.02351283871158888;
                                attribute Ixz : Real = -7.11125070657171e-4;
                                attribute 'σ_Ixz' : Real = 0.022566176940390956;
                                attribute Iyz : Real = 0.0012417534232498;
                                attribute 'σ_Iyz' : Real = 0.02209918015384651;
                            }
                            part <'C.1.1.3.3.1.2.3'> 'Part 343' {
                                attribute POIconv : String = "-";
                                attribute Ipoint : Boolean = false;
                                attribute mass : Real = 0.4971872412322555;
                                attribute 'σ_mass' : Real = 0.28909372274994966;
                                attribute Cx : Real = 68.30497281625867;
                                attribute 'σ_Cx' : Real = 28.721044428837228;
                                attribute Cy : Real = -64.88379389047623;
                                attribute 'σ_Cy' : Real = 28.23690002309109;
                                attribute Cz : Real = 71.64839040488005;
                                attribute 'σ_Cz' : Real = 29.057750463592832;
                                attribute Ixx : Real = 0.7390924411943168;
                                attribute 'σ_Ixx' : Real = 0.37074144170588635;
                                attribute Iyy : Real = 0.6412912874456442;
                                attribute 'σ_Iyy' : Real = 0.3723953238821935;
                                attribute Izz : Real = 0.5967274879637402;
                                attribute 'σ_Izz' : Real = 0.37017423652493897;
                                attribute Ixy : Real = -0.007283921236905591;
                                attribute 'σ_Ixy' : Real = 0.02351283871158888;
                                attribute Ixz : Real = 0.0013296151538236527;
                                attribute 'σ_Ixz' : Real = 0.022566176940390956;
                                attribute Iyz : Real = 0.010705195410016874;
                                attribute 'σ_Iyz' : Real = 0.02209918015384651;
                            }
                        }
                        part <'C.1.1.3.3.1.3'> 'Subassembly 104' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.1.3.1'> 'Part 344' {
                                attribute POIconv : String = "+";
                                attribute Ipoint : Boolean = false;
                                attribute mass : Real = 0.7082670163041912;
                                attribute 'σ_mass' : Real = 0.28909372274994966;
                                attribute Cx : Real = -7.923644687980413;
                                attribute 'σ_Cx' : Real = 28.721044428837228;
                                attribute Cy : Real = -49.34416888281703;
                                attribute 'σ_Cy' : Real = 28.23690002309109;
                                attribute Cz : Real = -5.094885872676969;
                                attribute 'σ_Cz' : Real = 29.057750463592832;
                                attribute Ixx : Real = 0.8310048517949346;
                                attribute 'σ_Ixx' : Real = 0.37074144170588635;
                                attribute Iyy : Real = 0.8171105974087458;
                                attribute 'σ_Iyy' : Real = 0.3723953238821935;
                                attribute Izz : Real = 0.9152684446968447;
                                attribute 'σ_Izz' : Real = 0.37017423652493897;
                                attribute Ixy : Real = -0.006635538494853262;
                                attribute 'σ_Ixy' : Real = 0.02351283871158888;
                                attribute Ixz : Real = 0.004183277509689184;
                                attribute 'σ_Ixz' : Real = 0.022566176940390956;
                                attribute Iyz : Real = -0.04061732463389712;
                                attribute 'σ_Iyz' : Real = 0.02209918015384651;
                            }
                            part <'C.1.1.3.3.1.3.2'> 'Part 345' {
                                attribute POIconv : String = "+";
                                attribute Ipoint : Boolean = false;
                                attribute mass : Real = 0.7039202037192881;
                                attribute 'σ_mass' : Real = 0.28909372274994966;
                                attribute Cx : Real = 77.4934052489698;
                                attribute 'σ_Cx' : Real = 28.721044428837228;
                                attribute Cy : Real = 77.67855464480817;
                                attribute 'σ_Cy' : Real = 28.23690002309109;
                                attribute Cz : Real = -36.64542925544083;
                                attribute 'σ_Cz' : Real = 29.057750463592832;
                                attribute Ixx : Real = 0.8978087242555083;
                                attribute 'σ_Ixx' : Real = 0.37074144170588635;
                                attribute Iyy : Real = 0.9427405973278487;
                                attribute 'σ_Iyy' : Real = 0.3723953238821935;
                                attribute Izz : Real = 0.9582910226102995;
                                attribute 'σ_Izz' : Real = 0.37017423652493897;
                                attribute Ixy : Real = 0.047254869640635154;
                                attribute 'σ_Ixy' : Real = 0.02351283871158888;
                                attribute Ixz : Real = -0.003307730206997259;
                                attribute 'σ_Ixz' : Real = 0.022566176940390956;
                                attribute Iyz : Real = -0.002696946277858248;
                                attribute 'σ_Iyz' : Real = 0.02209918015384651;
                            }
                            part <'C.1.1.3.3.1.3.3'> 'Part 346' {
                                attribute POIconv : String = "+";
                                attribute Ipoint : Boolean = false;
                                attribute mass : Real = 0.5958952019563876;
                                attribute 'σ_mass' : Real = 0.28909372274994966;
                                attribute Cx : Real = 44.66969342902303;
                                attribute 'σ_Cx' : Real = 28.721044428837228;
                                attribute Cy : Real = 85.3391538374126;
                                attribute 'σ_Cy' : Real = 28.23690002309109;
                                attribute Cz : Real = 24.265004228800535;
                                attribute 'σ_Cz' : Real = 29.057750463592832;
                                attribute Ixx : Real = 0.7713652964993101;
                                attribute 'σ_Ixx' : Real = 0.37074144170588635;
                                attribute Iyy : Real = 0.6968887104444396;
                                attribute 'σ_Iyy' : Real = 0.3723953238821935;
                                attribute Izz : Real = 0.7985076519388641;
                                attribute 'σ_Izz' : Real = 0.37017423652493897;
                                attribute Ixy : Real = -0.017454868630698374;
                                attribute 'σ_Ixy' : Real = 0.02351283871158888;
                                attribute Ixz : Real = 0.09199885539149083;
                                attribute 'σ_Ixz' : Real = 0.022566176940390956;
                                attribute Iyz : Real = 0.02230476182137807;
                                attribute 'σ_Iyz' : Real = 0.02209918015384651;
                            }
                            part <'C.1.1.3.3.1.3.4'> 'Part 347' {
                                attribute POIconv : String = "+";
                                attribute Ipoint : Boolean = false;
                                attribute mass : Real = 0.8632667303956114;
                                attribute 'σ_mass' : Real = 0.28909372274994966;
                                attribute Cx : Real = 30.22816083393991;
                                attribute 'σ_Cx' : Real = 28.721044428837228;
                                attribute Cy : Real = 19.483605585992336;
                                attribute 'σ_Cy' : Real = 28.23690002309109;
                                attribute Cz : Real = 65.16060717403889;
                                attribute 'σ_Cz' : Real = 29.057750463592832;
                                attribute Ixx : Real = 1.310280276323307;
                                attribute 'σ_Ixx' : Real = 0.37074144170588635;
                                attribute Iyy : Real = 1.3092027430011184;
                                attribute 'σ_Iyy' : Real = 0.3723953238821935;
                                attribute Izz : Real = 1.219558064498851;
                                attribute 'σ_Izz' : Real = 0.37017423652493897;
                                attribute Ixy : Real = 0.004857887101179674;
                                attribute 'σ_Ixy' : Real = 0.02351283871158888;
                                attribute Ixz : Real = -0.002589224195977213;
                                attribute 'σ_Ixz' : Real = 0.022566176940390956;
                                attribute Iyz : Real = -0.001204902973619892;
                                attribute 'σ_Iyz' : Real = 0.02209918015384651;
                            }
                            part <'C.1.1.3.3.1.3.5'> 'Part 348' {
                                attribute POIconv : String = "-";
                                attribute Ipoint : Boolean = false;
                                attribute mass : Real = 0.8072724089231342;
                                attribute 'σ_mass' : Real = 0.28909372274994966;
                                attribute Cx : Real = -36.79119385778904;
                                attribute 'σ_Cx' : Real = 28.721044428837228;
                                attribute Cy : Real = -37.78122067451477;
                                attribute 'σ_Cy' : Real = 28.23690002309109;
                                attribute Cz : Real = -57.85218561068177;
                                attribute 'σ_Cz' : Real = 29.057750463592832;
                                attribute Ixx : Real = 0.8511451997168983;
                                attribute 'σ_Ixx' : Real = 0.37074144170588635;
                                attribute Iyy : Real = 0.9283186293498258;
                                attribute 'σ_Iyy' : Real = 0.3723953238821935;
                                attribute Izz : Real = 0.8772118188480884;
                                attribute 'σ_Izz' : Real = 0.37017423652493897;
                                attribute Ixy : Real = 0.024868290144069972;
                                attribute 'σ_Ixy' : Real = 0.02351283871158888;
                                attribute Ixz : Real = 0.038762012521037545;
                                attribute 'σ_Ixz' : Real = 0.022566176940390956;
                                attribute Iyz : Real = 0.05005484338480435;
                                attribute 'σ_Iyz' : Real = 0.02209918015384651;
                            }
                        }
                        part <'C.1.1.3.3.1.4'> 'Subassembly 105' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.1.4.1'> 'Part 349' {
                                attribute POIconv : String = "-";
                                attribute Ipoint : Boolean = false;
                                attribute mass : Real = 0.48454553055693395;
                                attribute 'σ_mass' : Real = 0.28909372274994966;
                                attribute Cx : Real = 76.3405176345259;
                                attribute 'σ_Cx' : Real = 28.721044428837228;
                                attribute Cy : Real = -19.746251730248332;
                                attribute 'σ_Cy' : Real = 28.23690002309109;
                                attribute Cz : Real = -40.3416823130101;
                                attribute 'σ_Cz' : Real = 29.057750463592832;
                                attribute Ixx : Real = 0.4435015590057802;
                                attribute 'σ_Ixx' : Real = 0.37074144170588635;
                                attribute Iyy : Real = 0.5665401783028494;
                                attribute 'σ_Iyy' : Real = 0.3723953238821935;
                                attribute Izz : Real = 0.5595896048069;
                                attribute 'σ_Izz' : Real = 0.37017423652493897;
                                attribute Ixy : Real = -0.026817732010076874;
                                attribute 'σ_Ixy' : Real = 0.02351283871158888;
                                attribute Ixz : Real = -0.012258042220934025;
                                attribute 'σ_Ixz' : Real = 0.022566176940390956;
                                attribute Iyz : Real = -0.004432627929189525;
                                attribute 'σ_Iyz' : Real = 0.02209918015384651;
                            }
                            part <'C.1.1.3.3.1.4.2'> 'Part 350' {
                                attribute POIconv : String = "+";
                                attribute Ipoint : Boolean = false;
                                attribute mass : Real = 0.10636566165601835;
                                attribute 'σ_mass' : Real = 0.28909372274994966;
                                attribute Cx : Real = 99.09410011023283;
                                attribute 'σ_Cx' : Real = 28.721044428837228;
                                attribute Cy : Real = 12.152099749073386;
                                attribute 'σ_Cy' : Real = 28.23690002309109;
                                attribute Cz : Real = 41.56476310454309;
                                attribute 'σ_Cz' : Real = 29.057750463592832;
                                attribute Ixx : Real = 0.12124309108592712;
                                attribute 'σ_Ixx' : Real = 0.37074144170588635;
                                attribute Iyy : Real = 0.11976485657182949;
                                attribute 'σ_Iyy' : Real = 0.3723953238821935;
                                attribute Izz : Real = 0.1381998386436675;
                                attribute 'σ_Izz' : Real = 0.37017423652493897;
                                attribute Ixy : Real = 0.0031644404808769274;
                                attribute 'σ_Ixy' : Real = 0.02351283871158888;
                                attribute Ixz : Real = -6.34067392692426e-5;
                                attribute 'σ_Ixz' : Real = 0.022566176940390956;
                                attribute Iyz : Real = -0.001641676819240469;
                                attribute 'σ_Iyz' : Real = 0.02209918015384651;
                            }
                        }
                    }
                    part <'C.1.1.3.3.2'> 'Assembly 29' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.3.2.1'> 'Subassembly 106' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.2.1.1'> 'Part 351' {
                                attribute POIconv : String = "-";
                                attribute Ipoint : Boolean = false;
                                attribute mass : Real = 0.77704927199753;
                                attribute 'σ_mass' : Real = 0.28909372274994966;
                                attribute Cx : Real = 70.05582912825048;
                                attribute 'σ_Cx' : Real = 28.721044428837228;
                                attribute Cy : Real = -90.65169123932719;
                                attribute 'σ_Cy' : Real = 28.23690002309109;
                                attribute Cz : Real = -53.16146709956229;
                                attribute 'σ_Cz' : Real = 29.057750463592832;
                                attribute Ixx : Real = 0.9895311238446165;
                                attribute 'σ_Ixx' : Real = 0.37074144170588635;
                                attribute Iyy : Real = 0.84551021282698;
                                attribute 'σ_Iyy' : Real = 0.3723953238821935;
                                attribute Izz : Real = 0.9724325137632895;
                                attribute 'σ_Izz' : Real = 0.37017423652493897;
                                attribute Ixy : Real = -0.036116724543611714;
                                attribute 'σ_Ixy' : Real = 0.02351283871158888;
                                attribute Ixz : Real = -0.0013055538886287076;
                                attribute 'σ_Ixz' : Real = 0.022566176940390956;
                                attribute Iyz : Real = -0.020873950018523157;
                                attribute 'σ_Iyz' : Real = 0.02209918015384651;
                            }
                            part <'C.1.1.3.3.2.1.2'> 'Part 352' {
                                attribute POIconv : String = "-";
                                attribute Ipoint : Boolean = false;
                                attribute mass : Real = 0.34672079734317957;
                                attribute 'σ_mass' : Real = 0.28909372274994966;
                                attribute Cx : Real = 90.2286637108773;
                                attribute 'σ_Cx' : Real = 28.721044428837228;
                                attribute Cy : Real = -14.014111133292317;
                                attribute 'σ_Cy' : Real = 28.23690002309109;
                                attribute Cz : Real = 10.395548678934574;
                                attribute 'σ_Cz' : Real = 29.057750463592832;
                                attribute Ixx : Real = 0.4724925320319602;
                                attribute 'σ_Ixx' : Real = 0.37074144170588635;
                                attribute Iyy : Real = 0.4765015014220238;
                                attribute 'σ_Iyy' : Real = 0.3723953238821935;
                                attribute Izz : Real = 0.48873816688708965;
                                attribute 'σ_Izz' : Real = 0.37017423652493897;
                                attribute Ixy : Real = -0.014557722872197195;
                                attribute 'σ_Ixy' : Real = 0.02351283871158888;
                                attribute Ixz : Real = -0.03173305962860533;
                                attribute 'σ_Ixz' : Real = 0.022566176940390956;
                                attribute Iyz : Real = 1.3034053223681666e-4;
                                attribute 'σ_Iyz' : Real = 0.02209918015384651;
                            }
                            part <'C.1.1.3.3.2.1.3'> 'Part 353' {
                                attribute POIconv : String = "+";
                                attribute Ipoint : Boolean = false;
                                attribute mass : Real = 0.8570563166863285;
                                attribute 'σ_mass' : Real = 0.28909372274994966;
                                attribute Cx : Real = -77.57854368537664;
                                attribute 'σ_Cx' : Real = 28.721044428837228;
                                attribute Cy : Real = 27.805724507197738;
                                attribute 'σ_Cy' : Real = 28.23690002309109;
                                attribute Cz : Real = 38.91883506439626;
                                attribute 'σ_Cz' : Real = 29.057750463592832;
                                attribute Ixx : Real = 1.1371704390374393;
                                attribute 'σ_Ixx' : Real = 0.37074144170588635;
                                attribute Iyy : Real = 1.1473445203900074;
                                attribute 'σ_Iyy' : Real = 0.3723953238821935;
                                attribute Izz : Real = 1.0822245381959128;
                                attribute 'σ_Izz' : Real = 0.37017423652493897;
                                attribute Ixy : Real = 0.021969742746294284;
                                attribute 'σ_Ixy' : Real = 0.02351283871158888;
                                attribute Ixz : Real = 0.08954292109316597;
                                attribute 'σ_Ixz' : Real = 0.022566176940390956;
                                attribute Iyz : Real = -0.09571725841884535;
                                attribute 'σ_Iyz' : Real = 0.02209918015384651;
                            }
                            part <'C.1.1.3.3.2.1.4'> 'Part 354' {
                                attribute POIconv : String = "+";
                                attribute Ipoint : Boolean = false;
                                attribute mass : Real = 0.8075060287709348;
                                attribute 'σ_mass' : Real = 0.28909372274994966;
                                attribute Cx : Real = 95.47860003076494;
                                attribute 'σ_Cx' : Real = 28.721044428837228;
                                attribute Cy : Real = -29.560013441368937;
                                attribute 'σ_Cy' : Real = 28.23690002309109;
                                attribute Cz : Real = 87.90220720693469;
                                attribute 'σ_Cz' : Real = 29.057750463592832;
                                attribute Ixx : Real = 1.0222307270645512;
                                attribute 'σ_Ixx' : Real = 0.37074144170588635;
                                attribute Iyy : Real = 1.0425468890200875;
                                attribute 'σ_Iyy' : Real = 0.3723953238821935;
                                attribute Izz : Real = 1.0088720804606368;
                                attribute 'σ_Izz' : Real = 0.37017423652493897;
                                attribute Ixy : Real = 0.06613813756534859;
                                attribute 'σ_Ixy' : Real = 0.02351283871158888;
                                attribute Ixz : Real = -0.051207983586662245;
                                attribute 'σ_Ixz' : Real = 0.022566176940390956;
                                attribute Iyz : Real = 0.056839000670519446;
                                attribute 'σ_Iyz' : Real = 0.02209918015384651;
                            }
                            part <'C.1.1.3.3.2.1.5'> 'Part 355' {
                                attribute POIconv : String = "-";
                                attribute Ipoint : Boolean = false;
                                attribute mass : Real = 0.20572458224953152;
                                attribute 'σ_mass' : Real = 0.28909372274994966;
                                attribute Cx : Real = -30.770735954865813;
                                attribute 'σ_Cx' : Real = 28.721044428837228;
                                attribute Cy : Real = 47.99015307798982;
                                attribute 'σ_Cy' : Real = 28.23690002309109;
                                attribute Cz : Real = 51.574612967669964;
                                attribute 'σ_Cz' : Real = 29.057750463592832;
                                attribute Ixx : Real = 0.2839137586999741;
                                attribute 'σ_Ixx' : Real = 0.37074144170588635;
                                attribute Iyy : Real = 0.2687665489168035;
                                attribute 'σ_Iyy' : Real = 0.3723953238821935;
                                attribute Izz : Real = 0.27125756260417366;
                                attribute 'σ_Izz' : Real = 0.37017423652493897;
                                attribute Ixy : Real = 0.0027132013043448767;
                                attribute 'σ_Ixy' : Real = 0.02351283871158888;
                                attribute Ixz : Real = -0.005324956905221535;
                                attribute 'σ_Ixz' : Real = 0.022566176940390956;
                                attribute Iyz : Real = -0.00343109518570215;
                                attribute 'σ_Iyz' : Real = 0.02209918015384651;
                            }
                        }
                        part <'C.1.1.3.3.2.2'> 'Subassembly 107' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.2.2.1'> 'Part 356' {
                                attribute POIconv : String = "-";
                                attribute Ipoint : Boolean = false;
                                attribute mass : Real = 0.2372182305334136;
                                attribute 'σ_mass' : Real = 0.28909372274994966;
                                attribute Cx : Real = -25.50076711922884;
                                attribute 'σ_Cx' : Real = 28.721044428837228;
                                attribute Cy : Real = 37.69216509535909;
                                attribute 'σ_Cy' : Real = 28.23690002309109;
                                attribute Cz : Real = 1.8723068293184042;
                                attribute 'σ_Cz' : Real = 29.057750463592832;
                                attribute Ixx : Real = 0.29134553987413647;
                                attribute 'σ_Ixx' : Real = 0.37074144170588635;
                                attribute Iyy : Real = 0.3015563682877139;
                                attribute 'σ_Iyy' : Real = 0.3723953238821935;
                                attribute Izz : Real = 0.3665896343791621;
                                attribute 'σ_Izz' : Real = 0.37017423652493897;
                                attribute Ixy : Real = -0.008189519011996816;
                                attribute 'σ_Ixy' : Real = 0.02351283871158888;
                                attribute Ixz : Real = 0.012289423546843217;
                                attribute 'σ_Ixz' : Real = 0.022566176940390956;
                                attribute Iyz : Real = -0.02760671114873288;
                                attribute 'σ_Iyz' : Real = 0.02209918015384651;
                            }
                            part <'C.1.1.3.3.2.2.2'> 'Part 357' {
                                attribute POIconv : String = "-";
                                attribute Ipoint : Boolean = false;
                                attribute mass : Real = 0.04752086375420913;
                                attribute 'σ_mass' : Real = 0.28909372274994966;
                                attribute Cx : Real = 66.05742904357612;
                                attribute 'σ_Cx' : Real = 28.721044428837228;
                                attribute Cy : Real = -46.46932524628937;
                                attribute 'σ_Cy' : Real = 28.23690002309109;
                                attribute Cz : Real = 28.583692107349634;
                                attribute 'σ_Cz' : Real = 29.057750463592832;
                                attribute Ixx : Real = 0.057919704634129085;
                                attribute 'σ_Ixx' : Real = 0.37074144170588635;
                                attribute Iyy : Real = 0.054995967699237265;
                                attribute 'σ_Iyy' : Real = 0.3723953238821935;
                                attribute Izz : Real = 0.0649351684678988;
                                attribute 'σ_Izz' : Real = 0.37017423652493897;
                                attribute Ixy : Real = -0.004256242558669406;
                                attribute 'σ_Ixy' : Real = 0.02351283871158888;
                                attribute Ixz : Real = 0.001327113246219507;
                                attribute 'σ_Ixz' : Real = 0.022566176940390956;
                                attribute Iyz : Real = -0.004210082649598986;
                                attribute 'σ_Iyz' : Real = 0.02209918015384651;
                            }
                            part <'C.1.1.3.3.2.2.3'> 'Part 358' {
                                attribute POIconv : String = "-";
                                attribute Ipoint : Boolean = false;
                                attribute mass : Real = 0.7245376036199741;
                                attribute 'σ_mass' : Real = 0.28909372274994966;
                                attribute Cx : Real = 35.23866543546319;
                                attribute 'σ_Cx' : Real = 28.721044428837228;
                                attribute Cy : Real = 34.217194048687816;
                                attribute 'σ_Cy' : Real = 28.23690002309109;
                                attribute Cz : Real = -11.421308340504766;
                                attribute 'σ_Cz' : Real = 29.057750463592832;
                                attribute Ixx : Real = 0.9112260261089657;
                                attribute 'σ_Ixx' : Real = 0.37074144170588635;
                                attribute Iyy : Real = 0.9854030878342958;
                                attribute 'σ_Iyy' : Real = 0.3723953238821935;
                                attribute Izz : Real = 0.9851808842484352;
                                attribute 'σ_Izz' : Real = 0.37017423652493897;
                                attribute Ixy : Real = -0.03404675019815247;
                                attribute 'σ_Ixy' : Real = 0.02351283871158888;
                                attribute Ixz : Real = -0.03454329038095409;
                                attribute 'σ_Ixz' : Real = 0.022566176940390956;
                                attribute Iyz : Real = -0.012396529647119573;
                                attribute 'σ_Iyz' : Real = 0.02209918015384651;
                            }
                        }
                    }
                    part <'C.1.1.3.3.3'> 'Assembly 30' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.3.3.1'> 'Subassembly 108' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.3.1.1'> 'Part 359' {
                                attribute POIconv : String = "+";
                                attribute Ipoint : Boolean = false;
                                attribute mass : Real = 0.8504522860716097;
                                attribute 'σ_mass' : Real = 0.28909372274994966;
                                attribute Cx : Real = -49.115600530058146;
                                attribute 'σ_Cx' : Real = 28.721044428837228;
                                attribute Cy : Real = 44.19183866120875;
                                attribute 'σ_Cy' : Real = 28.23690002309109;
                                attribute Cz : Real = -43.12542281113565;
                                attribute 'σ_Cz' : Real = 29.057750463592832;
                                attribute Ixx : Real = 1.2859925581689495;
                                attribute 'σ_Ixx' : Real = 0.37074144170588635;
                                attribute Iyy : Real = 1.2703321565005177;
                                attribute 'σ_Iyy' : Real = 0.3723953238821935;
                                attribute Izz : Real = 1.2792177094362849;
                                attribute 'σ_Izz' : Real = 0.37017423652493897;
                                attribute Ixy : Real = -0.012581350744978818;
                                attribute 'σ_Ixy' : Real = 0.02351283871158888;
                                attribute Ixz : Real = 0.017977905440962234;
                                attribute 'σ_Ixz' : Real = 0.022566176940390956;
                                attribute Iyz : Real = 0.011617879109940707;
                                attribute 'σ_Iyz' : Real = 0.02209918015384651;
                            }
                            part <'C.1.1.3.3.3.1.2'> 'Part 360' {
                                attribute POIconv : String = "-";
                                attribute Ipoint : Boolean = false;
                                attribute mass : Real = 0.6315701652944553;
                                attribute 'σ_mass' : Real = 0.28909372274994966;
                                attribute Cx : Real = -83.37428821250796;
                                attribute 'σ_Cx' : Real = 28.721044428837228;
                                attribute Cy : Real = 1.954424660652876;
                                attribute 'σ_Cy' : Real = 28.23690002309109;
                                attribute Cz : Real = 72.82711169682443;
                                attribute 'σ_Cz' : Real = 29.057750463592832;
                                attribute Ixx : Real = 0.7236730051605913;
                                attribute 'σ_Ixx' : Real = 0.37074144170588635;
                                attribute Iyy : Real = 0.7205043949279477;
                                attribute 'σ_Iyy' : Real = 0.3723953238821935;
                                attribute Izz : Real = 0.8530657457063536;
                                attribute 'σ_Izz' : Real = 0.37017423652493897;
                                attribute Ixy : Real = 0.016007201976327993;
                                attribute 'σ_Ixy' : Real = 0.02351283871158888;
                                attribute Ixz : Real = 0.06380973638404938;
                                attribute 'σ_Ixz' : Real = 0.022566176940390956;
                                attribute Iyz : Real = -0.02362741773822745;
                                attribute 'σ_Iyz' : Real = 0.02209918015384651;
                            }
                            part <'C.1.1.3.3.3.1.3'> 'Part 361' {
                                attribute POIconv : String = "+";
                                attribute Ipoint : Boolean = false;
                                attribute mass : Real = 0.6996143925464712;
                                attribute 'σ_mass' : Real = 0.28909372274994966;
                                attribute Cx : Real = -63.59420269727707;
                                attribute 'σ_Cx' : Real = 28.721044428837228;
                                attribute Cy : Real = -88.62598459236324;
                                attribute 'σ_Cy' : Real = 28.23690002309109;
                                attribute Cz : Real = -22.760992124676704;
                                attribute 'σ_Cz' : Real = 29.057750463592832;
                                attribute Ixx : Real = 0.9098811334073331;
                                attribute 'σ_Ixx' : Real = 0.37074144170588635;
                                attribute Iyy : Real = 0.8575401273555749;
                                attribute 'σ_Iyy' : Real = 0.3723953238821935;
                                attribute Izz : Real = 0.8742757121999164;
                                attribute 'σ_Izz' : Real = 0.37017423652493897;
                                attribute Ixy : Real = -0.04562700392134493;
                                attribute 'σ_Ixy' : Real = 0.02351283871158888;
                                attribute Ixz : Real = -0.022545919239275007;
                                attribute 'σ_Ixz' : Real = 0.022566176940390956;
                                attribute Iyz : Real = -0.0021049229370553877;
                                attribute 'σ_Iyz' : Real = 0.02209918015384651;
                            }
                            part <'C.1.1.3.3.3.1.4'> 'Part 362' {
                                attribute POIconv : String = "+";
                                attribute Ipoint : Boolean = false;
                                attribute mass : Real = 0.8161346968146972;
                                attribute 'σ_mass' : Real = 0.28909372274994966;
                                attribute Cx : Real = -50.07086815312505;
                                attribute 'σ_Cx' : Real = 28.721044428837228;
                                attribute Cy : Real = -15.8969531301409;
                                attribute 'σ_Cy' : Real = 28.23690002309109;
                                attribute Cz : Real = 58.48685218952596;
                                attribute 'σ_Cz' : Real = 29.057750463592832;
                                attribute Ixx : Real = 0.9474334592935165;
                                attribute 'σ_Ixx' : Real = 0.37074144170588635;
                                attribute Iyy : Real = 0.9142407891330531;
                                attribute 'σ_Iyy' : Real = 0.3723953238821935;
                                attribute Izz : Real = 0.9510547762293589;
                                attribute 'σ_Izz' : Real = 0.37017423652493897;
                                attribute Ixy : Real = 0.004616361332841578;
                                attribute 'σ_Ixy' : Real = 0.02351283871158888;
                                attribute Ixz : Real = -0.0045825795372115685;
                                attribute 'σ_Ixz' : Real = 0.022566176940390956;
                                attribute Iyz : Real = -0.015149540630757522;
                                attribute 'σ_Iyz' : Real = 0.02209918015384651;
                            }
                        }
                        part <'C.1.1.3.3.3.2'> 'Subassembly 109' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.3.2.1'> 'Part 363' {
                                attribute POIconv : String = "-";
                                attribute Ipoint : Boolean = false;
                                attribute mass : Real = 0.44449189454852606;
                                attribute 'σ_mass' : Real = 0.28909372274994966;
                                attribute Cx : Real = 73.33115013316274;
                                attribute 'σ_Cx' : Real = 28.721044428837228;
                                attribute Cy : Real = 3.464101580902934;
                                attribute 'σ_Cy' : Real = 28.23690002309109;
                                attribute Cz : Real = -44.381224643439054;
                                attribute 'σ_Cz' : Real = 29.057750463592832;
                                attribute Ixx : Real = 0.6340587886663713;
                                attribute 'σ_Ixx' : Real = 0.37074144170588635;
                                attribute Iyy : Real = 0.6257638950324168;
                                attribute 'σ_Iyy' : Real = 0.3723953238821935;
                                attribute Izz : Real = 0.6074280828308877;
                                attribute 'σ_Izz' : Real = 0.37017423652493897;
                                attribute Ixy : Real = -0.011954897470110134;
                                attribute 'σ_Ixy' : Real = 0.02351283871158888;
                                attribute Ixz : Real = -0.01721122078046567;
                                attribute 'σ_Ixz' : Real = 0.022566176940390956;
                                attribute Iyz : Real = 0.011125900437416226;
                                attribute 'σ_Iyz' : Real = 0.02209918015384651;
                            }
                            part <'C.1.1.3.3.3.2.2'> 'Part 364' {
                                attribute POIconv : String = "-";
                                attribute Ipoint : Boolean = false;
                                attribute mass : Real = 0.6195363764499779;
                                attribute 'σ_mass' : Real = 0.28909372274994966;
                                attribute Cx : Real = -51.22993038967252;
                                attribute 'σ_Cx' : Real = 28.721044428837228;
                                attribute Cy : Real = 5.6061300449073315;
                                attribute 'σ_Cy' : Real = 28.23690002309109;
                                attribute Cz : Real = 60.55085202679038;
                                attribute 'σ_Cz' : Real = 29.057750463592832;
                                attribute Ixx : Real = 0.766592003874242;
                                attribute 'σ_Ixx' : Real = 0.37074144170588635;
                                attribute Iyy : Real = 0.8736708767852546;
                                attribute 'σ_Iyy' : Real = 0.3723953238821935;
                                attribute Izz : Real = 0.8176724382256669;
                                attribute 'σ_Izz' : Real = 0.37017423652493897;
                                attribute Ixy : Real = 0.01026958985554561;
                                attribute 'σ_Ixy' : Real = 0.02351283871158888;
                                attribute Ixz : Real = -0.015242290774441194;
                                attribute 'σ_Ixz' : Real = 0.022566176940390956;
                                attribute Iyz : Real = 0.04479842730099822;
                                attribute 'σ_Iyz' : Real = 0.02209918015384651;
                            }
                        }
                        part <'C.1.1.3.3.3.3'> 'Subassembly 110' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.3.3.1'> 'Part 365' {
                                attribute POIconv : String = "+";
                                attribute Ipoint : Boolean = false;
                                attribute mass : Real = 0.6631013120673597;
                                attribute 'σ_mass' : Real = 0.28909372274994966;
                                attribute Cx : Real = -26.361875887960196;
                                attribute 'σ_Cx' : Real = 28.721044428837228;
                                attribute Cy : Real = -91.08197679743171;
                                attribute 'σ_Cy' : Real = 28.23690002309109;
                                attribute Cz : Real = 32.93327162973583;
                                attribute 'σ_Cz' : Real = 29.057750463592832;
                                attribute Ixx : Real = 0.8681920304754445;
                                attribute 'σ_Ixx' : Real = 0.37074144170588635;
                                attribute Iyy : Real = 0.8343259704647652;
                                attribute 'σ_Iyy' : Real = 0.3723953238821935;
                                attribute Izz : Real = 0.9656238455132924;
                                attribute 'σ_Izz' : Real = 0.37017423652493897;
                                attribute Ixy : Real = 0.010485765311351203;
                                attribute 'σ_Ixy' : Real = 0.02351283871158888;
                                attribute Ixz : Real = 0.07894198419442901;
                                attribute 'σ_Ixz' : Real = 0.022566176940390956;
                                attribute Iyz : Real = -0.006375601374078912;
                                attribute 'σ_Iyz' : Real = 0.02209918015384651;
                            }
                            part <'C.1.1.3.3.3.3.2'> 'Part 366' {
                                attribute POIconv : String = "-";
                                attribute Ipoint : Boolean = false;
                                attribute mass : Real = 0.43639439152251;
                                attribute 'σ_mass' : Real = 0.28909372274994966;
                                attribute Cx : Real = 60.67314734682441;
                                attribute 'σ_Cx' : Real = 28.721044428837228;
                                attribute Cy : Real = 51.530647557228804;
                                attribute 'σ_Cy' : Real = 28.23690002309109;
                                attribute Cz : Real = 34.53284106217325;
                                attribute 'σ_Cz' : Real = 29.057750463592832;
                                attribute Ixx : Real = 0.5965071925441982;
                                attribute 'σ_Ixx' : Real = 0.37074144170588635;
                                attribute Iyy : Real = 0.6196004966756115;
                                attribute 'σ_Iyy' : Real = 0.3723953238821935;
                                attribute Izz : Real = 0.6755973245670407;
                                attribute 'σ_Izz' : Real = 0.37017423652493897;
                                attribute Ixy : Real = 0.019010842469309133;
                                attribute 'σ_Ixy' : Real = 0.02351283871158888;
                                attribute Ixz : Real = 1.3449155068283064e-4;
                                attribute 'σ_Ixz' : Real = 0.022566176940390956;
                                attribute Iyz : Real = -2.0597936091259472e-4;
                                attribute 'σ_Iyz' : Real = 0.02209918015384651;
                            }
                            part <'C.1.1.3.3.3.3.3'> 'Part 367' {
                                attribute POIconv : String = "-";
                                attribute Ipoint : Boolean = false;
                                attribute mass : Real = 0.29280219084909187;
                                attribute 'σ_mass' : Real = 0.28909372274994966;
                                attribute Cx : Real = 51.96624989621341;
                                attribute 'σ_Cx' : Real = 28.721044428837228;
                                attribute Cy : Real = 20.35210942849517;
                                attribute 'σ_Cy' : Real = 28.23690002309109;
                                attribute Cz : Real = -84.27569982595742;
                                attribute 'σ_Cz' : Real = 29.057750463592832;
                                attribute Ixx : Real = 0.38775073085315237;
                                attribute 'σ_Ixx' : Real = 0.37074144170588635;
                                attribute Iyy : Real = 0.37682545416182517;
                                attribute 'σ_Iyy' : Real = 0.3723953238821935;
                                attribute Izz : Real = 0.41072470042932147;
                                attribute 'σ_Izz' : Real = 0.37017423652493897;
                                attribute Ixy : Real = -0.030480396750700398;
                                attribute 'σ_Ixy' : Real = 0.02351283871158888;
                                attribute Ixz : Real = 0.021042182170702382;
                                attribute 'σ_Ixz' : Real = 0.022566176940390956;
                                attribute Iyz : Real = 4.046926077895442e-4;
                                attribute 'σ_Iyz' : Real = 0.02209918015384651;
                            }
                            part <'C.1.1.3.3.3.3.4'> 'Part 368' {
                                attribute POIconv : String = "-";
                                attribute Ipoint : Boolean = false;
                                attribute mass : Real = 0.7366351738085505;
                                attribute 'σ_mass' : Real = 0.28909372274994966;
                                attribute Cx : Real = 61.88151203095913;
                                attribute 'σ_Cx' : Real = 28.721044428837228;
                                attribute Cy : Real = 62.26568752899766;
                                attribute 'σ_Cy' : Real = 28.23690002309109;
                                attribute Cz : Real = -88.20957448333502;
                                attribute 'σ_Cz' : Real = 29.057750463592832;
                                attribute Ixx : Real = 0.8327232536244488;
                                attribute 'σ_Ixx' : Real = 0.37074144170588635;
                                attribute Iyy : Real = 0.7531982390595652;
                                attribute 'σ_Iyy' : Real = 0.3723953238821935;
                                attribute Izz : Real = 0.8055498768810735;
                                attribute 'σ_Izz' : Real = 0.37017423652493897;
                                attribute Ixy : Real = 0.009441943800766153;
                                attribute 'σ_Ixy' : Real = 0.02351283871158888;
                                attribute Ixz : Real = -4.412399267944972e-4;
                                attribute 'σ_Ixz' : Real = 0.022566176940390956;
                                attribute Iyz : Real = -0.0024008129387950152;
                                attribute 'σ_Iyz' : Real = 0.02209918015384651;
                            }
                            part <'C.1.1.3.3.3.3.5'> 'Part 369' {
                                attribute POIconv : String = "+";
                                attribute Ipoint : Boolean = false;
                                attribute mass : Real = 0.2715729317017831;
                                attribute 'σ_mass' : Real = 0.28909372274994966;
                                attribute Cx : Real = -70.55536163970828;
                                attribute 'σ_Cx' : Real = 28.721044428837228;
                                attribute Cy : Real = -30.49886655062437;
                                attribute 'σ_Cy' : Real = 28.23690002309109;
                                attribute Cz : Real = -64.20878088101745;
                                attribute 'σ_Cz' : Real = 29.057750463592832;
                                attribute Ixx : Real = 0.3161118053732044;
                                attribute 'σ_Ixx' : Real = 0.37074144170588635;
                                attribute Iyy : Real = 0.36828978337773255;
                                attribute 'σ_Iyy' : Real = 0.3723953238821935;
                                attribute Izz : Real = 0.3312912321796915;
                                attribute 'σ_Izz' : Real = 0.37017423652493897;
                                attribute Ixy : Real = -0.00846343292733176;
                                attribute 'σ_Ixy' : Real = 0.02351283871158888;
                                attribute Ixz : Real = -0.033531751516162125;
                                attribute 'σ_Ixz' : Real = 0.022566176940390956;
                                attribute Iyz : Real = -0.009268383138734036;
                                attribute 'σ_Iyz' : Real = 0.02209918015384651;
                            }
                        }
                        part <'C.1.1.3.3.3.4'> 'Subassembly 111' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.3.4.1'> 'Part 370' {
                                attribute POIconv : String = "-";
                                attribute Ipoint : Boolean = false;
                                attribute mass : Real = 0.9836174107897095;
                                attribute 'σ_mass' : Real = 0.28909372274994966;
                                attribute Cx : Real = -11.059313593432307;
                                attribute 'σ_Cx' : Real = 28.721044428837228;
                                attribute Cy : Real = 65.70983855053782;
                                attribute 'σ_Cy' : Real = 28.23690002309109;
                                attribute Cz : Real = 23.10982048511505;
                                attribute 'σ_Cz' : Real = 29.057750463592832;
                                attribute Ixx : Real = 1.5057223389342758;
                                attribute 'σ_Ixx' : Real = 0.37074144170588635;
                                attribute Iyy : Real = 1.53427055622812;
                                attribute 'σ_Iyy' : Real = 0.3723953238821935;
                                attribute Izz : Real = 1.5314362347455965;
                                attribute 'σ_Izz' : Real = 0.37017423652493897;
                                attribute Ixy : Real = -0.012060290262935716;
                                attribute 'σ_Ixy' : Real = 0.02351283871158888;
                                attribute Ixz : Real = -0.01515338425031792;
                                attribute 'σ_Ixz' : Real = 0.022566176940390956;
                                attribute Iyz : Real = -0.0058937719634679555;
                                attribute 'σ_Iyz' : Real = 0.02209918015384651;
                            }
                            part <'C.1.1.3.3.3.4.2'> 'Part 371' {
                                attribute POIconv : String = "+";
                                attribute Ipoint : Boolean = false;
                                attribute mass : Real = 0.7890587515793741;
                                attribute 'σ_mass' : Real = 0.28909372274994966;
                                attribute Cx : Real = 53.98680209182203;
                                attribute 'σ_Cx' : Real = 28.721044428837228;
                                attribute Cy : Real = 95.98496975377202;
                                attribute 'σ_Cy' : Real = 28.23690002309109;
                                attribute Cz : Real = -39.544238056987524;
                                attribute 'σ_Cz' : Real = 29.057750463592832;
                                attribute Ixx : Real = 1.1721711015514373;
                                attribute 'σ_Ixx' : Real = 0.37074144170588635;
                                attribute Iyy : Real = 1.0951211235738731;
                                attribute 'σ_Iyy' : Real = 0.3723953238821935;
                                attribute Izz : Real = 1.1008474308553882;
                                attribute 'σ_Izz' : Real = 0.37017423652493897;
                                attribute Ixy : Real = -0.07280050465536486;
                                attribute 'σ_Ixy' : Real = 0.02351283871158888;
                                attribute Ixz : Real = 0.05799694573055922;
                                attribute 'σ_Ixz' : Real = 0.022566176940390956;
                                attribute Iyz : Real = 0.011487199058910876;
                                attribute 'σ_Iyz' : Real = 0.02209918015384651;
                            }
                            part <'C.1.1.3.3.3.4.3'> 'Part 372' {
                                attribute POIconv : String = "+";
                                attribute Ipoint : Boolean = false;
                                attribute mass : Real = 0.38300722730276177;
                                attribute 'σ_mass' : Real = 0.28909372274994966;
                                attribute Cx : Real = 52.177726570516825;
                                attribute 'σ_Cx' : Real = 28.721044428837228;
                                attribute Cy : Real = -3.9107633754611015;
                                attribute 'σ_Cy' : Real = 28.23690002309109;
                                attribute Cz : Real = -59.45711024105549;
                                attribute 'σ_Cz' : Real = 29.057750463592832;
                                attribute Ixx : Real = 0.38422021901327974;
                                attribute 'σ_Ixx' : Real = 0.37074144170588635;
                                attribute Iyy : Real = 0.4476683081339953;
                                attribute 'σ_Iyy' : Real = 0.3723953238821935;
                                attribute Izz : Real = 0.4538802454009414;
                                attribute 'σ_Izz' : Real = 0.37017423652493897;
                                attribute Ixy : Real = 0.027468949864668555;
                                attribute 'σ_Ixy' : Real = 0.02351283871158888;
                                attribute Ixz : Real = 0.039544325396093476;
                                attribute 'σ_Ixz' : Real = 0.022566176940390956;
                                attribute Iyz : Real = 0.011665527210420832;
                                attribute 'σ_Iyz' : Real = 0.02209918015384651;
                            }
                        }
                        part <'C.1.1.3.3.3.5'> 'Subassembly 112' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.3.5.1'> 'Part 373' {
                                attribute POIconv : String = "-";
                                attribute Ipoint : Boolean = false;
                                attribute mass : Real = 0.4930017203444149;
                                attribute 'σ_mass' : Real = 0.28909372274994966;
                                attribute Cx : Real = 48.9634505007416;
                                attribute 'σ_Cx' : Real = 28.721044428837228;
                                attribute Cy : Real = -30.859337421134114;
                                attribute 'σ_Cy' : Real = 28.23690002309109;
                                attribute Cz : Real = -24.25348130054772;
                                attribute 'σ_Cz' : Real = 29.057750463592832;
                                attribute Ixx : Real = 0.7428852804728492;
                                attribute 'σ_Ixx' : Real = 0.37074144170588635;
                                attribute Iyy : Real = 0.7512146991308191;
                                attribute 'σ_Iyy' : Real = 0.3723953238821935;
                                attribute Izz : Real = 0.7529417182912935;
                                attribute 'σ_Izz' : Real = 0.37017423652493897;
                                attribute Ixy : Real = 0.013259708736063101;
                                attribute 'σ_Ixy' : Real = 0.02351283871158888;
                                attribute Ixz : Real = 0.012344322066848802;
                                attribute 'σ_Ixz' : Real = 0.022566176940390956;
                                attribute Iyz : Real = -0.008900075135714076;
                                attribute 'σ_Iyz' : Real = 0.02209918015384651;
                            }
                            part <'C.1.1.3.3.3.5.2'> 'Part 374' {
                                attribute POIconv : String = "+";
                                attribute Ipoint : Boolean = false;
                                attribute mass : Real = 0.49086345958150923;
                                attribute 'σ_mass' : Real = 0.28909372274994966;
                                attribute Cx : Real = -71.60062612965703;
                                attribute 'σ_Cx' : Real = 28.721044428837228;
                                attribute Cy : Real = 56.60618063993752;
                                attribute 'σ_Cy' : Real = 28.23690002309109;
                                attribute Cz : Real = -78.87534759938717;
                                attribute 'σ_Cz' : Real = 29.057750463592832;
                                attribute Ixx : Real = 0.6061484588404196;
                                attribute 'σ_Ixx' : Real = 0.37074144170588635;
                                attribute Iyy : Real = 0.554689354793227;
                                attribute 'σ_Iyy' : Real = 0.3723953238821935;
                                attribute Izz : Real = 0.679233732908539;
                                attribute 'σ_Izz' : Real = 0.37017423652493897;
                                attribute Ixy : Real = 0.026031544239559713;
                                attribute 'σ_Ixy' : Real = 0.02351283871158888;
                                attribute Ixz : Real = -0.008043975478040356;
                                attribute 'σ_Ixz' : Real = 0.022566176940390956;
                                attribute Iyz : Real = -0.059851779504421804;
                                attribute 'σ_Iyz' : Real = 0.02209918015384651;
                            }
                            part <'C.1.1.3.3.3.5.3'> 'Part 375' {
                                attribute POIconv : String = "-";
                                attribute Ipoint : Boolean = false;
                                attribute mass : Real = 0.24642546586622485;
                                attribute 'σ_mass' : Real = 0.28909372274994966;
                                attribute Cx : Real = -84.09838699735701;
                                attribute 'σ_Cx' : Real = 28.721044428837228;
                                attribute Cy : Real = -18.07793523184955;
                                attribute 'σ_Cy' : Real = 28.23690002309109;
                                attribute Cz : Real = 1.7397694289684296;
                                attribute 'σ_Cz' : Real = 29.057750463592832;
                                attribute Ixx : Real = 0.30882200594334985;
                                attribute 'σ_Ixx' : Real = 0.37074144170588635;
                                attribute Iyy : Real = 0.3082591801718887;
                                attribute 'σ_Iyy' : Real = 0.3723953238821935;
                                attribute Izz : Real = 0.29144252165497686;
                                attribute 'σ_Izz' : Real = 0.37017423652493897;
                                attribute Ixy : Real = 0.014654766119721687;
                                attribute 'σ_Ixy' : Real = 0.02351283871158888;
                                attribute Ixz : Real = -0.021475599004901584;
                                attribute 'σ_Ixz' : Real = 0.022566176940390956;
                                attribute Iyz : Real = 0.02084967314682651;
                                attribute 'σ_Iyz' : Real = 0.02209918015384651;
                            }
                            part <'C.1.1.3.3.3.5.4'> 'Part 376' {
                                attribute POIconv : String = "-";
                                attribute Ipoint : Boolean = false;
                                attribute mass : Real = 0.6667201521121897;
                                attribute 'σ_mass' : Real = 0.28909372274994966;
                                attribute Cx : Real = -79.02822960168123;
                                attribute 'σ_Cx' : Real = 28.721044428837228;
                                attribute Cy : Real = 56.081335339695215;
                                attribute 'σ_Cy' : Real = 28.23690002309109;
                                attribute Cz : Real = 24.90436127409339;
                                attribute 'σ_Cz' : Real = 29.057750463592832;
                                attribute Ixx : Real = 0.8349685941386452;
                                attribute 'σ_Ixx' : Real = 0.37074144170588635;
                                attribute Iyy : Real = 0.8474066305350284;
                                attribute 'σ_Iyy' : Real = 0.3723953238821935;
                                attribute Izz : Real = 0.7989530974833681;
                                attribute 'σ_Izz' : Real = 0.37017423652493897;
                                attribute Ixy : Real = 0.009647740900007574;
                                attribute 'σ_Ixy' : Real = 0.02351283871158888;
                                attribute Ixz : Real = -0.03165659888702023;
                                attribute 'σ_Ixz' : Real = 0.022566176940390956;
                                attribute Iyz : Real = 0.01557464612257966;
                                attribute 'σ_Iyz' : Real = 0.02209918015384651;
                            }
                        }
                    }
                    part <'C.1.1.3.3.4'> 'Assembly 31' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.3.4.1'> 'Subassembly 113' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.4.1.1'> 'Part 377' {
                                attribute POIconv : String = "-";
                                attribute Ipoint : Boolean = false;
                                attribute mass : Real = 0.16786196228140035;
                                attribute 'σ_mass' : Real = 0.28909372274994966;
                                attribute Cx : Real = 85.8563244342804;
                                attribute 'σ_Cx' : Real = 28.721044428837228;
                                attribute Cy : Real = 16.847784537822008;
                                attribute 'σ_Cy' : Real = 28.23690002309109;
                                attribute Cz : Real = 68.2447683531791;
                                attribute 'σ_Cz' : Real = 29.057750463592832;
                                attribute Ixx : Real = 0.18772929224369217;
                                attribute 'σ_Ixx' : Real = 0.37074144170588635;
                                attribute Iyy : Real = 0.16351796613933164;
                                attribute 'σ_Iyy' : Real = 0.3723953238821935;
                                attribute Izz : Real = 0.18264884543448073;
                                attribute 'σ_Izz' : Real = 0.37017423652493897;
                                attribute Ixy : Real = 0.002366922563690748;
                                attribute 'σ_Ixy' : Real = 0.02351283871158888;
                                attribute Ixz : Real = -7.671349051615627e-5;
                                attribute 'σ_Ixz' : Real = 0.022566176940390956;
                                attribute Iyz : Real = -0.013367497632409162;
                                attribute 'σ_Iyz' : Real = 0.02209918015384651;
                            }
                            part <'C.1.1.3.3.4.1.2'> 'Part 378' {
                                attribute POIconv : String = "+";
                                attribute Ipoint : Boolean = false;
                                attribute mass : Real = 0.7761300614897627;
                                attribute 'σ_mass' : Real = 0.28909372274994966;
                                attribute Cx : Real = -40.10105608031154;
                                attribute 'σ_Cx' : Real = 28.721044428837228;
                                attribute Cy : Real = -18.691003043204546;
                                attribute 'σ_Cy' : Real = 28.23690002309109;
                                attribute Cz : Real = 82.37731056287885;
                                attribute 'σ_Cz' : Real = 29.057750463592832;
                                attribute Ixx : Real = 0.8337004375924344;
                                attribute 'σ_Ixx' : Real = 0.37074144170588635;
                                attribute Iyy : Real = 0.8948591043860825;
                                attribute 'σ_Iyy' : Real = 0.3723953238821935;
                                attribute Izz : Real = 0.9861817588244333;
                                attribute 'σ_Izz' : Real = 0.37017423652493897;
                                attribute Ixy : Real = -0.0727409255035611;
                                attribute 'σ_Ixy' : Real = 0.02351283871158888;
                                attribute Ixz : Real = 0.05749437187098973;
                                attribute 'σ_Ixz' : Real = 0.022566176940390956;
                                attribute Iyz : Real = -0.010528134551486382;
                                attribute 'σ_Iyz' : Real = 0.02209918015384651;
                            }
                            part <'C.1.1.3.3.4.1.3'> 'Part 379' {
                                attribute POIconv : String = "+";
                                attribute Ipoint : Boolean = false;
                                attribute mass : Real = 0.3677954891961999;
                                attribute 'σ_mass' : Real = 0.28909372274994966;
                                attribute Cx : Real = 6.675472250208259;
                                attribute 'σ_Cx' : Real = 28.721044428837228;
                                attribute Cy : Real = -64.9044412188232;
                                attribute 'σ_Cy' : Real = 28.23690002309109;
                                attribute Cz : Real = 6.5065456088632345;
                                attribute 'σ_Cz' : Real = 29.057750463592832;
                                attribute Ixx : Real = 0.45608195124425166;
                                attribute 'σ_Ixx' : Real = 0.37074144170588635;
                                attribute Iyy : Real = 0.4488835622870266;
                                attribute 'σ_Iyy' : Real = 0.3723953238821935;
                                attribute Izz : Real = 0.5122677597952316;
                                attribute 'σ_Izz' : Real = 0.37017423652493897;
                                attribute Ixy : Real = -0.028238561556379542;
                                attribute 'σ_Ixy' : Real = 0.02351283871158888;
                                attribute Ixz : Real = -0.003921683895963335;
                                attribute 'σ_Ixz' : Real = 0.022566176940390956;
                                attribute Iyz : Real = 0.046778849140629394;
                                attribute 'σ_Iyz' : Real = 0.02209918015384651;
                            }
                            part <'C.1.1.3.3.4.1.4'> 'Part 380' {
                                attribute POIconv : String = "-";
                                attribute Ipoint : Boolean = false;
                                attribute mass : Real = 0.35258977467520164;
                                attribute 'σ_mass' : Real = 0.28909372274994966;
                                attribute Cx : Real = -42.390523571521044;
                                attribute 'σ_Cx' : Real = 28.721044428837228;
                                attribute Cy : Real = 19.009209191426635;
                                attribute 'σ_Cy' : Real = 28.23690002309109;
                                attribute Cz : Real = 34.90069201216102;
                                attribute 'σ_Cz' : Real = 29.057750463592832;
                                attribute Ixx : Real = 0.35212763824570303;
                                attribute 'σ_Ixx' : Real = 0.37074144170588635;
                                attribute Iyy : Real = 0.3520464040277288;
                                attribute 'σ_Iyy' : Real = 0.3723953238821935;
                                attribute Izz : Real = 0.3167711626335207;
                                attribute 'σ_Izz' : Real = 0.37017423652493897;
                                attribute Ixy : Real = 0.004601997288405874;
                                attribute 'σ_Ixy' : Real = 0.02351283871158888;
                                attribute Ixz : Real = 0.0049188604272641405;
                                attribute 'σ_Ixz' : Real = 0.022566176940390956;
                                attribute Iyz : Real = -0.018591595479338606;
                                attribute 'σ_Iyz' : Real = 0.02209918015384651;
                            }
                            part <'C.1.1.3.3.4.1.5'> 'Part 381' {
                                attribute POIconv : String = "-";
                                attribute Ipoint : Boolean = false;
                                attribute mass : Real = 0.7519982337721158;
                                attribute 'σ_mass' : Real = 0.28909372274994966;
                                attribute Cx : Real = 93.94692704081535;
                                attribute 'σ_Cx' : Real = 28.721044428837228;
                                attribute Cy : Real = 60.78961477614939;
                                attribute 'σ_Cy' : Real = 28.23690002309109;
                                attribute Cz : Real = 78.5638467874378;
                                attribute 'σ_Cz' : Real = 29.057750463592832;
                                attribute Ixx : Real = 1.0658366598083429;
                                attribute 'σ_Ixx' : Real = 0.37074144170588635;
                                attribute Iyy : Real = 1.0515183722742143;
                                attribute 'σ_Iyy' : Real = 0.3723953238821935;
                                attribute Izz : Real = 0.9352413116792168;
                                attribute 'σ_Izz' : Real = 0.37017423652493897;
                                attribute Ixy : Real = -0.03138950107287084;
                                attribute 'σ_Ixy' : Real = 0.02351283871158888;
                                attribute Ixz : Real = -0.049741399104252855;
                                attribute 'σ_Ixz' : Real = 0.022566176940390956;
                                attribute Iyz : Real = 0.028469702048991283;
                                attribute 'σ_Iyz' : Real = 0.02209918015384651;
                            }
                        }
                        part <'C.1.1.3.3.4.2'> 'Subassembly 114' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.4.2.1'> 'Part 382' {
                                attribute POIconv : String = "-";
                                attribute Ipoint : Boolean = false;
                                attribute mass : Real = 0.62546605390287;
                                attribute 'σ_mass' : Real = 0.28909372274994966;
                                attribute Cx : Real = 2.355882665142417;
                                attribute 'σ_Cx' : Real = 28.721044428837228;
                                attribute Cy : Real = -3.5654504783451557;
                                attribute 'σ_Cy' : Real = 28.23690002309109;
                                attribute Cz : Real = 25.43421327136457;
                                attribute 'σ_Cz' : Real = 29.057750463592832;
                                attribute Ixx : Real = 0.6564305318742797;
                                attribute 'σ_Ixx' : Real = 0.37074144170588635;
                                attribute Iyy : Real = 0.7143324744289306;
                                attribute 'σ_Iyy' : Real = 0.3723953238821935;
                                attribute Izz : Real = 0.7175145145447938;
                                attribute 'σ_Izz' : Real = 0.37017423652493897;
                                attribute Ixy : Real = -0.0146954903636636;
                                attribute 'σ_Ixy' : Real = 0.02351283871158888;
                                attribute Ixz : Real = -0.01780526800032754;
                                attribute 'σ_Ixz' : Real = 0.022566176940390956;
                                attribute Iyz : Real = -0.025956038590863963;
                                attribute 'σ_Iyz' : Real = 0.02209918015384651;
                            }
                            part <'C.1.1.3.3.4.2.2'> 'Part 383' {
                                attribute POIconv : String = "-";
                                attribute Ipoint : Boolean = false;
                                attribute mass : Real = 0.14246590520720928;
                                attribute 'σ_mass' : Real = 0.28909372274994966;
                                attribute Cx : Real = -13.453342951834202;
                                attribute 'σ_Cx' : Real = 28.721044428837228;
                                attribute Cy : Real = -45.40736894123256;
                                attribute 'σ_Cy' : Real = 28.23690002309109;
                                attribute Cz : Real = -40.9826572984457;
                                attribute 'σ_Cz' : Real = 29.057750463592832;
                                attribute Ixx : Real = 0.16077365099943794;
                                attribute 'σ_Ixx' : Real = 0.37074144170588635;
                                attribute Iyy : Real = 0.15703020875757595;
                                attribute 'σ_Iyy' : Real = 0.3723953238821935;
                                attribute Izz : Real = 0.15542495318233188;
                                attribute 'σ_Izz' : Real = 0.37017423652493897;
                                attribute Ixy : Real = 5.4811923751243034e-5;
                                attribute 'σ_Ixy' : Real = 0.02351283871158888;
                                attribute Ixz : Real = -0.0028249315988940864;
                                attribute 'σ_Ixz' : Real = 0.022566176940390956;
                                attribute Iyz : Real = 0.00194954496673525;
                                attribute 'σ_Iyz' : Real = 0.02209918015384651;
                            }
                            part <'C.1.1.3.3.4.2.3'> 'Part 384' {
                                attribute POIconv : String = "+";
                                attribute Ipoint : Boolean = false;
                                attribute mass : Real = 0.30736152279307133;
                                attribute 'σ_mass' : Real = 0.28909372274994966;
                                attribute Cx : Real = 64.03149636462331;
                                attribute 'σ_Cx' : Real = 28.721044428837228;
                                attribute Cy : Real = 38.015674659982324;
                                attribute 'σ_Cy' : Real = 28.23690002309109;
                                attribute Cz : Real = 99.04580633156002;
                                attribute 'σ_Cz' : Real = 29.057750463592832;
                                attribute Ixx : Real = 0.36714965255547966;
                                attribute 'σ_Ixx' : Real = 0.37074144170588635;
                                attribute Iyy : Real = 0.4088369471696716;
                                attribute 'σ_Iyy' : Real = 0.3723953238821935;
                                attribute Izz : Real = 0.3272964155798288;
                                attribute 'σ_Izz' : Real = 0.37017423652493897;
                                attribute Ixy : Real = -0.004865696717759781;
                                attribute 'σ_Ixy' : Real = 0.02351283871158888;
                                attribute Ixz : Real = 0.04523094933536531;
                                attribute 'σ_Ixz' : Real = 0.022566176940390956;
                                attribute Iyz : Real = 0.010244793744234936;
                                attribute 'σ_Iyz' : Real = 0.02209918015384651;
                            }
                            part <'C.1.1.3.3.4.2.4'> 'Part 385' {
                                attribute POIconv : String = "-";
                                attribute Ipoint : Boolean = false;
                                attribute mass : Real = 0.8813279117320199;
                                attribute 'σ_mass' : Real = 0.28909372274994966;
                                attribute Cx : Real = -53.15743167884648;
                                attribute 'σ_Cx' : Real = 28.721044428837228;
                                attribute Cy : Real = 10.442890552803874;
                                attribute 'σ_Cy' : Real = 28.23690002309109;
                                attribute Cz : Real = -68.36772146634758;
                                attribute 'σ_Cz' : Real = 29.057750463592832;
                                attribute Ixx : Real = 1.1694444186108524;
                                attribute 'σ_Ixx' : Real = 0.37074144170588635;
                                attribute Iyy : Real = 1.2350173669635875;
                                attribute 'σ_Iyy' : Real = 0.3723953238821935;
                                attribute Izz : Real = 1.221708662038103;
                                attribute 'σ_Izz' : Real = 0.37017423652493897;
                                attribute Ixy : Real = 0.03883823840806931;
                                attribute 'σ_Ixy' : Real = 0.02351283871158888;
                                attribute Ixz : Real = 0.021780530814033063;
                                attribute 'σ_Ixz' : Real = 0.022566176940390956;
                                attribute Iyz : Real = 0.03573074102659063;
                                attribute 'σ_Iyz' : Real = 0.02209918015384651;
                            }
                            part <'C.1.1.3.3.4.2.5'> 'Part 386' {
                                attribute POIconv : String = "+";
                                attribute Ipoint : Boolean = false;
                                attribute mass : Real = 0.10937700319802389;
                                attribute 'σ_mass' : Real = 0.28909372274994966;
                                attribute Cx : Real = 42.76658818125725;
                                attribute 'σ_Cx' : Real = 28.721044428837228;
                                attribute Cy : Real = 45.61534714885056;
                                attribute 'σ_Cy' : Real = 28.23690002309109;
                                attribute Cz : Real = 81.8830500356853;
                                attribute 'σ_Cz' : Real = 29.057750463592832;
                                attribute Ixx : Real = 0.13144777401524757;
                                attribute 'σ_Ixx' : Real = 0.37074144170588635;
                                attribute Iyy : Real = 0.1344541654665131;
                                attribute 'σ_Iyy' : Real = 0.3723953238821935;
                                attribute Izz : Real = 0.16944041406185276;
                                attribute 'σ_Izz' : Real = 0.37017423652493897;
                                attribute Ixy : Real = -0.004704860740521314;
                                attribute 'σ_Ixy' : Real = 0.02351283871158888;
                                attribute Ixz : Real = -0.005551590956860193;
                                attribute 'σ_Ixz' : Real = 0.022566176940390956;
                                attribute Iyz : Real = -0.004846641111376362;
                                attribute 'σ_Iyz' : Real = 0.02209918015384651;
                            }
                        }
                        part <'C.1.1.3.3.4.3'> 'Subassembly 115' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.4.3.1'> 'Part 387' {
                                attribute POIconv : String = "-";
                                attribute Ipoint : Boolean = false;
                                attribute mass : Real = 0.1324007549379021;
                                attribute 'σ_mass' : Real = 0.28909372274994966;
                                attribute Cx : Real = -75.64562722109258;
                                attribute 'σ_Cx' : Real = 28.721044428837228;
                                attribute Cy : Real = -14.837086573243141;
                                attribute 'σ_Cy' : Real = 28.23690002309109;
                                attribute Cz : Real = -84.6807558555156;
                                attribute 'σ_Cz' : Real = 29.057750463592832;
                                attribute Ixx : Real = 0.17553472010336704;
                                attribute 'σ_Ixx' : Real = 0.37074144170588635;
                                attribute Iyy : Real = 0.14803501730536697;
                                attribute 'σ_Iyy' : Real = 0.3723953238821935;
                                attribute Izz : Real = 0.16591079093823602;
                                attribute 'σ_Izz' : Real = 0.37017423652493897;
                                attribute Ixy : Real = 0.015232586893970855;
                                attribute 'σ_Ixy' : Real = 0.02351283871158888;
                                attribute Ixz : Real = -9.567312334899193e-4;
                                attribute 'σ_Ixz' : Real = 0.022566176940390956;
                                attribute Iyz : Real = -0.01238921084133365;
                                attribute 'σ_Iyz' : Real = 0.02209918015384651;
                            }
                            part <'C.1.1.3.3.4.3.2'> 'Part 388' {
                                attribute POIconv : String = "+";
                                attribute Ipoint : Boolean = false;
                                attribute mass : Real = 0.807151144518517;
                                attribute 'σ_mass' : Real = 0.28909372274994966;
                                attribute Cx : Real = 7.701417431235313;
                                attribute 'σ_Cx' : Real = 28.721044428837228;
                                attribute Cy : Real = -10.22597891278565;
                                attribute 'σ_Cy' : Real = 28.23690002309109;
                                attribute Cz : Real = 24.476659391075373;
                                attribute 'σ_Cz' : Real = 29.057750463592832;
                                attribute Ixx : Real = 0.8202455337025117;
                                attribute 'σ_Ixx' : Real = 0.37074144170588635;
                                attribute Iyy : Real = 0.8113282285181346;
                                attribute 'σ_Iyy' : Real = 0.3723953238821935;
                                attribute Izz : Real = 0.7152272549742393;
                                attribute 'σ_Izz' : Real = 0.37017423652493897;
                                attribute Ixy : Real = -0.00677213545481405;
                                attribute 'σ_Ixy' : Real = 0.02351283871158888;
                                attribute Ixz : Real = -0.005947729133492619;
                                attribute 'σ_Ixz' : Real = 0.022566176940390956;
                                attribute Iyz : Real = 0.011259169536033297;
                                attribute 'σ_Iyz' : Real = 0.02209918015384651;
                            }
                        }
                        part <'C.1.1.3.3.4.4'> 'Subassembly 116' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.4.4.1'> 'Part 389' {
                                attribute POIconv : String = "-";
                                attribute Ipoint : Boolean = false;
                                attribute mass : Real = 0.7139046251026447;
                                attribute 'σ_mass' : Real = 0.28909372274994966;
                                attribute Cx : Real = -87.40574680268764;
                                attribute 'σ_Cx' : Real = 28.721044428837228;
                                attribute Cy : Real = -17.880180245265365;
                                attribute 'σ_Cy' : Real = 28.23690002309109;
                                attribute Cz : Real = 39.53604926355183;
                                attribute 'σ_Cz' : Real = 29.057750463592832;
                                attribute Ixx : Real = 1.0309447711844637;
                                attribute 'σ_Ixx' : Real = 0.37074144170588635;
                                attribute Iyy : Real = 0.9377386227914168;
                                attribute 'σ_Iyy' : Real = 0.3723953238821935;
                                attribute Izz : Real = 1.030668584191264;
                                attribute 'σ_Izz' : Real = 0.37017423652493897;
                                attribute Ixy : Real = -0.004976498780813686;
                                attribute 'σ_Ixy' : Real = 0.02351283871158888;
                                attribute Ixz : Real = 0.003565080235109526;
                                attribute 'σ_Ixz' : Real = 0.022566176940390956;
                                attribute Iyz : Real = 0.011396028594465521;
                                attribute 'σ_Iyz' : Real = 0.02209918015384651;
                            }
                            part <'C.1.1.3.3.4.4.2'> 'Part 390' {
                                attribute POIconv : String = "-";
                                attribute Ipoint : Boolean = false;
                                attribute mass : Real = 0.295551092278678;
                                attribute 'σ_mass' : Real = 0.28909372274994966;
                                attribute Cx : Real = -33.12367140315473;
                                attribute 'σ_Cx' : Real = 28.721044428837228;
                                attribute Cy : Real = -65.27239489369094;
                                attribute 'σ_Cy' : Real = 28.23690002309109;
                                attribute Cz : Real = 51.6985178925097;
                                attribute 'σ_Cz' : Real = 29.057750463592832;
                                attribute Ixx : Real = 0.37477406366690624;
                                attribute 'σ_Ixx' : Real = 0.37074144170588635;
                                attribute Iyy : Real = 0.39944932687267626;
                                attribute 'σ_Iyy' : Real = 0.3723953238821935;
                                attribute Izz : Real = 0.31260582175360674;
                                attribute 'σ_Izz' : Real = 0.37017423652493897;
                                attribute Ixy : Real = -0.014740451163008633;
                                attribute 'σ_Ixy' : Real = 0.02351283871158888;
                                attribute Ixz : Real = 0.006089068610954781;
                                attribute 'σ_Ixz' : Real = 0.022566176940390956;
                                attribute Iyz : Real = -0.00154250272482289;
                                attribute 'σ_Iyz' : Real = 0.02209918015384651;
                            }
                            part <'C.1.1.3.3.4.4.3'> 'Part 391' {
                                attribute POIconv : String = "-";
                                attribute Ipoint : Boolean = false;
                                attribute mass : Real = 0.817310900226701;
                                attribute 'σ_mass' : Real = 0.28909372274994966;
                                attribute Cx : Real = -47.937864949926734;
                                attribute 'σ_Cx' : Real = 28.721044428837228;
                                attribute Cy : Real = -48.670189175754786;
                                attribute 'σ_Cy' : Real = 28.23690002309109;
                                attribute Cz : Real = 29.171191062778234;
                                attribute 'σ_Cz' : Real = 29.057750463592832;
                                attribute Ixx : Real = 0.8674163361629236;
                                attribute 'σ_Ixx' : Real = 0.37074144170588635;
                                attribute Iyy : Real = 0.9735490142799794;
                                attribute 'σ_Iyy' : Real = 0.3723953238821935;
                                attribute Izz : Real = 0.9580039967475;
                                attribute 'σ_Izz' : Real = 0.37017423652493897;
                                attribute Ixy : Real = -0.07595666677287743;
                                attribute 'σ_Ixy' : Real = 0.02351283871158888;
                                attribute Ixz : Real = 0.0028398898663351073;
                                attribute 'σ_Ixz' : Real = 0.022566176940390956;
                                attribute Iyz : Real = 0.0013683141854874232;
                                attribute 'σ_Iyz' : Real = 0.02209918015384651;
                            }
                        }
                        part <'C.1.1.3.3.4.5'> 'Subassembly 117' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.3.4.5.1'> 'Part 392' {
                                attribute POIconv : String = "+";
                                attribute Ipoint : Boolean = false;
                                attribute mass : Real = 0.12312743554264308;
                                attribute 'σ_mass' : Real = 0.28909372274994966;
                                attribute Cx : Real = -13.61965243704617;
                                attribute 'σ_Cx' : Real = 28.721044428837228;
                                attribute Cy : Real = -58.821651339530945;
                                attribute 'σ_Cy' : Real = 28.23690002309109;
                                attribute Cz : Real = 66.03744337335229;
                                attribute 'σ_Cz' : Real = 29.057750463592832;
                                attribute Ixx : Real = 0.11273701249619117;
                                attribute 'σ_Ixx' : Real = 0.37074144170588635;
                                attribute Iyy : Real = 0.1339467200102361;
                                attribute 'σ_Iyy' : Real = 0.3723953238821935;
                                attribute Izz : Real = 0.12687587134572648;
                                attribute 'σ_Izz' : Real = 0.37017423652493897;
                                attribute Ixy : Real = -0.0019741660899585184;
                                attribute 'σ_Ixy' : Real = 0.02351283871158888;
                                attribute Ixz : Real = -0.0029936174079168154;
                                attribute 'σ_Ixz' : Real = 0.022566176940390956;
                                attribute Iyz : Real = -0.0028560964563378696;
                                attribute 'σ_Iyz' : Real = 0.02209918015384651;
                            }
                            part <'C.1.1.3.3.4.5.2'> 'Part 393' {
                                attribute POIconv : String = "-";
                                attribute Ipoint : Boolean = false;
                                attribute mass : Real = 0.6775872212552931;
                                attribute 'σ_mass' : Real = 0.28909372274994966;
                                attribute Cx : Real = 91.47244468331337;
                                attribute 'σ_Cx' : Real = 28.721044428837228;
                                attribute Cy : Real = -54.22576982527971;
                                attribute 'σ_Cy' : Real = 28.23690002309109;
                                attribute Cz : Real = 22.372767562046647;
                                attribute 'σ_Cz' : Real = 29.057750463592832;
                                attribute Ixx : Real = 0.9057019679536699;
                                attribute 'σ_Ixx' : Real = 0.37074144170588635;
                                attribute Iyy : Real = 0.9133459686867721;
                                attribute 'σ_Iyy' : Real = 0.3723953238821935;
                                attribute Izz : Real = 0.8425530044257208;
                                attribute 'σ_Izz' : Real = 0.37017423652493897;
                                attribute Ixy : Real = 0.036452692810385504;
                                attribute 'σ_Ixy' : Real = 0.02351283871158888;
                                attribute Ixz : Real = 0.008803544887606823;
                                attribute 'σ_Ixz' : Real = 0.022566176940390956;
                                attribute Iyz : Real = 0.007259635117751276;
                                attribute 'σ_Iyz' : Real = 0.02209918015384651;
                            }
                            part <'C.1.1.3.3.4.5.3'> 'Part 394' {
                                attribute POIconv : String = "-";
                                attribute Ipoint : Boolean = false;
                                attribute mass : Real = 0.0985529834907502;
                                attribute 'σ_mass' : Real = 0.28909372274994966;
                                attribute Cx : Real = -87.99872137606144;
                                attribute 'σ_Cx' : Real = 28.721044428837228;
                                attribute Cy : Real = 89.85906043089926;
                                attribute 'σ_Cy' : Real = 28.23690002309109;
                                attribute Cz : Real = -32.657551718875766;
                                attribute 'σ_Cz' : Real = 29.057750463592832;
                                attribute Ixx : Real = 0.13685297609509237;
                                attribute 'σ_Ixx' : Real = 0.37074144170588635;
                                attribute Iyy : Real = 0.11839772132804591;
                                attribute 'σ_Iyy' : Real = 0.3723953238821935;
                                attribute Izz : Real = 0.12420754512393485;
                                attribute 'σ_Izz' : Real = 0.37017423652493897;
                                attribute Ixy : Real = -0.007056821975560023;
                                attribute 'σ_Ixy' : Real = 0.02351283871158888;
                                attribute Ixz : Real = 0.0011114850167873698;
                                attribute 'σ_Ixz' : Real = 0.022566176940390956;
                                attribute Iyz : Real = 1.008320147939265e-4;
                                attribute 'σ_Iyz' : Real = 0.02209918015384651;
                            }
                            part <'C.1.1.3.3.4.5.4'> 'Part 395' {
                                attribute POIconv : String = "+";
                                attribute Ipoint : Boolean = false;
                                attribute mass : Real = 0.8121832358497195;
                                attribute 'σ_mass' : Real = 0.28909372274994966;
                                attribute Cx : Real = -30.786744970828295;
                                attribute 'σ_Cx' : Real = 28.721044428837228;
                                attribute Cy : Real = -77.6023690123111;
                                attribute 'σ_Cy' : Real = 28.23690002309109;
                                attribute Cz : Real = -77.66235861927271;
                                attribute 'σ_Cz' : Real = 29.057750463592832;
                                attribute Ixx : Real = 1.0780461154567795;
                                attribute 'σ_Ixx' : Real = 0.37074144170588635;
                                attribute Iyy : Real = 1.078477733319452;
                                attribute 'σ_Iyy' : Real = 0.3723953238821935;
                                attribute Izz : Real = 1.1877220575344243;
                                attribute 'σ_Izz' : Real = 0.37017423652493897;
                                attribute Ixy : Real = 0.014635663293714646;
                                attribute 'σ_Ixy' : Real = 0.02351283871158888;
                                attribute Ixz : Real = 0.08743197372177619;
                                attribute 'σ_Ixz' : Real = 0.022566176940390956;
                                attribute Iyz : Real = -0.03052663406862784;
                                attribute 'σ_Iyz' : Real = 0.02209918015384651;
                            }
                            part <'C.1.1.3.3.4.5.5'> 'Part 396' {
                                attribute POIconv : String = "+";
                                attribute Ipoint : Boolean = false;
                                attribute mass : Real = 0.4214078771804925;
                                attribute 'σ_mass' : Real = 0.28909372274994966;
                                attribute Cx : Real = 92.66907656565309;
                                attribute 'σ_Cx' : Real = 28.721044428837228;
                                attribute Cy : Real = 54.915151139721274;
                                attribute 'σ_Cy' : Real = 28.23690002309109;
                                attribute Cz : Real = -37.03661574982107;
                                attribute 'σ_Cz' : Real = 29.057750463592832;
                                attribute Ixx : Real = 0.6136963861147711;
                                attribute 'σ_Ixx' : Real = 0.37074144170588635;
                                attribute Iyy : Real = 0.6108861521766994;
                                attribute 'σ_Iyy' : Real = 0.3723953238821935;
                                attribute Izz : Real = 0.617636003029593;
                                attribute 'σ_Izz' : Real = 0.37017423652493897;
                                attribute Ixy : Real = 0.009244017657946283;
                                attribute 'σ_Ixy' : Real = 0.02351283871158888;
                                attribute Ixz : Real = -0.009184020189321615;
                                attribute 'σ_Ixz' : Real = 0.022566176940390956;
                                attribute Iyz : Real = 0.0013082082895758164;
                                attribute 'σ_Iyz' : Real = 0.02209918015384651;
                            }
                        }
                    }
                }
                part <'C.1.1.3.4'> 'Subsystem 9' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.3.4.1'> 'Assembly 32' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.4.1.1'> 'Subassembly 118' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.1.1.1'> 'Part 397' {
                                attribute POIconv : String = "-";
                                attribute Ipoint : Boolean = false;
                                attribute mass : Real = 0.02372396921156906;
                                attribute 'σ_mass' : Real = 0.28909372274994966;
                                attribute Cx : Real = -89.363680081442;
                                attribute 'σ_Cx' : Real = 28.721044428837228;
                                attribute Cy : Real = 35.44211769476533;
                                attribute 'σ_Cy' : Real = 28.23690002309109;
                                attribute Cz : Real = -89.64144736528397;
                                attribute 'σ_Cz' : Real = 29.057750463592832;
                                attribute Ixx : Real = 0.033405870504254906;
                                attribute 'σ_Ixx' : Real = 0.37074144170588635;
                                attribute Iyy : Real = 0.02913846666516851;
                                attribute 'σ_Iyy' : Real = 0.3723953238821935;
                                attribute Izz : Real = 0.03283746375896864;
                                attribute 'σ_Izz' : Real = 0.37017423652493897;
                                attribute Ixy : Real = 5.528425961646448e-4;
                                attribute 'σ_Ixy' : Real = 0.02351283871158888;
                                attribute Ixz : Real = 3.479115362449733e-5;
                                attribute 'σ_Ixz' : Real = 0.022566176940390956;
                                attribute Iyz : Real = 0.0013328242043395139;
                                attribute 'σ_Iyz' : Real = 0.02209918015384651;
                            }
                            part <'C.1.1.3.4.1.1.2'> 'Part 398' {
                                attribute POIconv : String = "+";
                                attribute Ipoint : Boolean = false;
                                attribute mass : Real = 0.5919234012430534;
                                attribute 'σ_mass' : Real = 0.28909372274994966;
                                attribute Cx : Real = 75.93101593665779;
                                attribute 'σ_Cx' : Real = 28.721044428837228;
                                attribute Cy : Real = 9.600986959412694;
                                attribute 'σ_Cy' : Real = 28.23690002309109;
                                attribute Cz : Real = -26.528398552909493;
                                attribute 'σ_Cz' : Real = 29.057750463592832;
                                attribute Ixx : Real = 0.770352850091484;
                                attribute 'σ_Ixx' : Real = 0.37074144170588635;
                                attribute Iyy : Real = 0.7259125163010768;
                                attribute 'σ_Iyy' : Real = 0.3723953238821935;
                                attribute Izz : Real = 0.7313072816393326;
                                attribute 'σ_Izz' : Real = 0.37017423652493897;
                                attribute Ixy : Real = 0.032472403891672996;
                                attribute 'σ_Ixy' : Real = 0.02351283871158888;
                                attribute Ixz : Real = 0.0302403569417911;
                                attribute 'σ_Ixz' : Real = 0.022566176940390956;
                                attribute Iyz : Real = 0.06243446399647014;
                                attribute 'σ_Iyz' : Real = 0.02209918015384651;
                            }
                        }
                        part <'C.1.1.3.4.1.2'> 'Subassembly 119' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.1.2.1'> 'Part 399' {
                                attribute POIconv : String = "+";
                                attribute Ipoint : Boolean = false;
                                attribute mass : Real = 0.523581439486472;
                                attribute 'σ_mass' : Real = 0.28909372274994966;
                                attribute Cx : Real = 50.42078816331923;
                                attribute 'σ_Cx' : Real = 28.721044428837228;
                                attribute Cy : Real = 17.9677443113178;
                                attribute 'σ_Cy' : Real = 28.23690002309109;
                                attribute Cz : Real = -72.7757129818201;
                                attribute 'σ_Cz' : Real = 29.057750463592832;
                                attribute Ixx : Real = 0.6823414106800034;
                                attribute 'σ_Ixx' : Real = 0.37074144170588635;
                                attribute Iyy : Real = 0.6193806633975562;
                                attribute 'σ_Iyy' : Real = 0.3723953238821935;
                                attribute Izz : Real = 0.7157345643301456;
                                attribute 'σ_Izz' : Real = 0.37017423652493897;
                                attribute Ixy : Real = 0.009529132218344998;
                                attribute 'σ_Ixy' : Real = 0.02351283871158888;
                                attribute Ixz : Real = 0.00633316435621075;
                                attribute 'σ_Ixz' : Real = 0.022566176940390956;
                                attribute Iyz : Real = 0.03633333192775019;
                                attribute 'σ_Iyz' : Real = 0.02209918015384651;
                            }
                            part <'C.1.1.3.4.1.2.2'> 'Part 400' {
                                attribute POIconv : String = "-";
                                attribute Ipoint : Boolean = false;
                                attribute mass : Real = 0.8158563330559991;
                                attribute 'σ_mass' : Real = 0.28909372274994966;
                                attribute Cx : Real = 24.250193033367395;
                                attribute 'σ_Cx' : Real = 28.721044428837228;
                                attribute Cy : Real = 15.537180751562119;
                                attribute 'σ_Cy' : Real = 28.23690002309109;
                                attribute Cz : Real = 39.37647631391883;
                                attribute 'σ_Cz' : Real = 29.057750463592832;
                                attribute Ixx : Real = 1.0297092509290482;
                                attribute 'σ_Ixx' : Real = 0.37074144170588635;
                                attribute Iyy : Real = 0.9790000251639716;
                                attribute 'σ_Iyy' : Real = 0.3723953238821935;
                                attribute Izz : Real = 1.1612455427057145;
                                attribute 'σ_Izz' : Real = 0.37017423652493897;
                                attribute Ixy : Real = -0.008917556040880119;
                                attribute 'σ_Ixy' : Real = 0.02351283871158888;
                                attribute Ixz : Real = 0.0040147945059103;
                                attribute 'σ_Ixz' : Real = 0.022566176940390956;
                                attribute Iyz : Real = 0.04399860010379668;
                                attribute 'σ_Iyz' : Real = 0.02209918015384651;
                            }
                            part <'C.1.1.3.4.1.2.3'> 'Part 401' {
                                attribute POIconv : String = "-";
                                attribute Ipoint : Boolean = false;
                                attribute mass : Real = 0.2222717572071124;
                                attribute 'σ_mass' : Real = 0.28909372274994966;
                                attribute Cx : Real = -13.808929780498147;
                                attribute 'σ_Cx' : Real = 28.721044428837228;
                                attribute Cy : Real = 20.651404466480017;
                                attribute 'σ_Cy' : Real = 28.23690002309109;
                                attribute Cz : Real = 72.60958417318761;
                                attribute 'σ_Cz' : Real = 29.057750463592832;
                                attribute Ixx : Real = 0.2632585799068577;
                                attribute 'σ_Ixx' : Real = 0.37074144170588635;
                                attribute Iyy : Real = 0.2820702391516388;
                                attribute 'σ_Iyy' : Real = 0.3723953238821935;
                                attribute Izz : Real = 0.28973382773890394;
                                attribute 'σ_Izz' : Real = 0.37017423652493897;
                                attribute Ixy : Real = 0.02805320581064509;
                                attribute 'σ_Ixy' : Real = 0.02351283871158888;
                                attribute Ixz : Real = -0.006327180711395032;
                                attribute 'σ_Ixz' : Real = 0.022566176940390956;
                                attribute Iyz : Real = -0.02744353798096605;
                                attribute 'σ_Iyz' : Real = 0.02209918015384651;
                            }
                            part <'C.1.1.3.4.1.2.4'> 'Part 402' {
                                attribute POIconv : String = "-";
                                attribute Ipoint : Boolean = false;
                                attribute mass : Real = 0.9888013822126668;
                                attribute 'σ_mass' : Real = 0.28909372274994966;
                                attribute Cx : Real = 25.683790165930986;
                                attribute 'σ_Cx' : Real = 28.721044428837228;
                                attribute Cy : Real = 47.29431327432394;
                                attribute 'σ_Cy' : Real = 28.23690002309109;
                                attribute Cz : Real = -33.63154106773436;
                                attribute 'σ_Cz' : Real = 29.057750463592832;
                                attribute Ixx : Real = 1.0904188596546653;
                                attribute 'σ_Ixx' : Real = 0.37074144170588635;
                                attribute Iyy : Real = 1.0730393353960321;
                                attribute 'σ_Iyy' : Real = 0.3723953238821935;
                                attribute Izz : Real = 1.2771831703843701;
                                attribute 'σ_Izz' : Real = 0.37017423652493897;
                                attribute Ixy : Real = -0.031710692012962435;
                                attribute 'σ_Ixy' : Real = 0.02351283871158888;
                                attribute Ixz : Real = -0.015609301703289464;
                                attribute 'σ_Ixz' : Real = 0.022566176940390956;
                                attribute Iyz : Real = -0.018873175179580544;
                                attribute 'σ_Iyz' : Real = 0.02209918015384651;
                            }
                            part <'C.1.1.3.4.1.2.5'> 'Part 403' {
                                attribute POIconv : String = "+";
                                attribute Ipoint : Boolean = false;
                                attribute mass : Real = 0.794274276291253;
                                attribute 'σ_mass' : Real = 0.28909372274994966;
                                attribute Cx : Real = 72.8743418585509;
                                attribute 'σ_Cx' : Real = 28.721044428837228;
                                attribute Cy : Real = 39.760535676032305;
                                attribute 'σ_Cy' : Real = 28.23690002309109;
                                attribute Cz : Real = -16.46910044364631;
                                attribute 'σ_Cz' : Real = 29.057750463592832;
                                attribute Ixx : Real = 1.141200087811568;
                                attribute 'σ_Ixx' : Real = 0.37074144170588635;
                                attribute Iyy : Real = 1.0508460947210099;
                                attribute 'σ_Iyy' : Real = 0.3723953238821935;
                                attribute Izz : Real = 1.045731743840879;
                                attribute 'σ_Izz' : Real = 0.37017423652493897;
                                attribute Ixy : Real = 0.008551433170079208;
                                attribute 'σ_Ixy' : Real = 0.02351283871158888;
                                attribute Ixz : Real = -0.025862813057664028;
                                attribute 'σ_Ixz' : Real = 0.022566176940390956;
                                attribute Iyz : Real = -0.02199402020909095;
                                attribute 'σ_Iyz' : Real = 0.02209918015384651;
                            }
                        }
                        part <'C.1.1.3.4.1.3'> 'Subassembly 120' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.1.3.1'> 'Part 404' {
                                attribute POIconv : String = "-";
                                attribute Ipoint : Boolean = false;
                                attribute mass : Real = 0.9421622136284131;
                                attribute 'σ_mass' : Real = 0.28909372274994966;
                                attribute Cx : Real = -47.65594904311001;
                                attribute 'σ_Cx' : Real = 28.721044428837228;
                                attribute Cy : Real = -53.82715044543147;
                                attribute 'σ_Cy' : Real = 28.23690002309109;
                                attribute Cz : Real = 36.67666702531278;
                                attribute 'σ_Cz' : Real = 29.057750463592832;
                                attribute Ixx : Real = 1.0437591953727015;
                                attribute 'σ_Ixx' : Real = 0.37074144170588635;
                                attribute Iyy : Real = 0.9793043709895538;
                                attribute 'σ_Iyy' : Real = 0.3723953238821935;
                                attribute Izz : Real = 0.9745845104575208;
                                attribute 'σ_Izz' : Real = 0.37017423652493897;
                                attribute Ixy : Real = 0.035738875647215035;
                                attribute 'σ_Ixy' : Real = 0.02351283871158888;
                                attribute Ixz : Real = 0.021095684951311106;
                                attribute 'σ_Ixz' : Real = 0.022566176940390956;
                                attribute Iyz : Real = -0.045095875833028244;
                                attribute 'σ_Iyz' : Real = 0.02209918015384651;
                            }
                            part <'C.1.1.3.4.1.3.2'> 'Part 405' {
                                attribute POIconv : String = "-";
                                attribute Ipoint : Boolean = false;
                                attribute mass : Real = 0.648505211758893;
                                attribute 'σ_mass' : Real = 0.28909372274994966;
                                attribute Cx : Real = 31.843072921037674;
                                attribute 'σ_Cx' : Real = 28.721044428837228;
                                attribute Cy : Real = -76.02740949951112;
                                attribute 'σ_Cy' : Real = 28.23690002309109;
                                attribute Cz : Real = 67.62630278244615;
                                attribute 'σ_Cz' : Real = 29.057750463592832;
                                attribute Ixx : Real = 0.9037261117087232;
                                attribute 'σ_Ixx' : Real = 0.37074144170588635;
                                attribute Iyy : Real = 0.8829578768385948;
                                attribute 'σ_Iyy' : Real = 0.3723953238821935;
                                attribute Izz : Real = 0.8634103312708705;
                                attribute 'σ_Izz' : Real = 0.37017423652493897;
                                attribute Ixy : Real = -0.034788890906275086;
                                attribute 'σ_Ixy' : Real = 0.02351283871158888;
                                attribute Ixz : Real = 0.007737350664627605;
                                attribute 'σ_Ixz' : Real = 0.022566176940390956;
                                attribute Iyz : Real = -0.006804706602077034;
                                attribute 'σ_Iyz' : Real = 0.02209918015384651;
                            }
                            part <'C.1.1.3.4.1.3.3'> 'Part 406' {
                                attribute POIconv : String = "+";
                                attribute Ipoint : Boolean = false;
                                attribute mass : Real = 0.6997341790245846;
                                attribute 'σ_mass' : Real = 0.28909372274994966;
                                attribute Cx : Real = 79.95043797418475;
                                attribute 'σ_Cx' : Real = 28.721044428837228;
                                attribute Cy : Real = -88.08560236357152;
                                attribute 'σ_Cy' : Real = 28.23690002309109;
                                attribute Cz : Real = 85.12953044846654;
                                attribute 'σ_Cz' : Real = 29.057750463592832;
                                attribute Ixx : Real = 0.9176902665123767;
                                attribute 'σ_Ixx' : Real = 0.37074144170588635;
                                attribute Iyy : Real = 0.8563765098178954;
                                attribute 'σ_Iyy' : Real = 0.3723953238821935;
                                attribute Izz : Real = 0.9557048970472372;
                                attribute 'σ_Izz' : Real = 0.37017423652493897;
                                attribute Ixy : Real = 0.04706473445192353;
                                attribute 'σ_Ixy' : Real = 0.02351283871158888;
                                attribute Ixz : Real = -0.03542613242964024;
                                attribute 'σ_Ixz' : Real = 0.022566176940390956;
                                attribute Iyz : Real = -0.042300210842502545;
                                attribute 'σ_Iyz' : Real = 0.02209918015384651;
                            }
                            part <'C.1.1.3.4.1.3.4'> 'Part 407' {
                                attribute POIconv : String = "-";
                                attribute Ipoint : Boolean = false;
                                attribute mass : Real = 0.5625381837503519;
                                attribute 'σ_mass' : Real = 0.28909372274994966;
                                attribute Cx : Real = 89.76080897264183;
                                attribute 'σ_Cx' : Real = 28.721044428837228;
                                attribute Cy : Real = 27.479560999199748;
                                attribute 'σ_Cy' : Real = 28.23690002309109;
                                attribute Cz : Real = 75.29244753532112;
                                attribute 'σ_Cz' : Real = 29.057750463592832;
                                attribute Ixx : Real = 0.6565068204623983;
                                attribute 'σ_Ixx' : Real = 0.37074144170588635;
                                attribute Iyy : Real = 0.6586151501643953;
                                attribute 'σ_Iyy' : Real = 0.3723953238821935;
                                attribute Izz : Real = 0.5456336650326229;
                                attribute 'σ_Izz' : Real = 0.37017423652493897;
                                attribute Ixy : Real = 0.010321119441103366;
                                attribute 'σ_Ixy' : Real = 0.02351283871158888;
                                attribute Ixz : Real = -0.03817678724386985;
                                attribute 'σ_Ixz' : Real = 0.022566176940390956;
                                attribute Iyz : Real = 0.03758965539000718;
                                attribute 'σ_Iyz' : Real = 0.02209918015384651;
                            }
                        }
                    }
                    part <'C.1.1.3.4.2'> 'Assembly 33' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.4.2.1'> 'Subassembly 121' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.2.1.1'> 'Part 408' {
                                attribute POIconv : String = "+";
                                attribute Ipoint : Boolean = false;
                                attribute mass : Real = 0.18278025591745972;
                                attribute 'σ_mass' : Real = 0.28909372274994966;
                                attribute Cx : Real = 55.44453551992774;
                                attribute 'σ_Cx' : Real = 28.721044428837228;
                                attribute Cy : Real = -0.27556465938687325;
                                attribute 'σ_Cy' : Real = 28.23690002309109;
                                attribute Cz : Real = -70.84898184984922;
                                attribute 'σ_Cz' : Real = 29.057750463592832;
                                attribute Ixx : Real = 0.2230402212027222;
                                attribute 'σ_Ixx' : Real = 0.37074144170588635;
                                attribute Iyy : Real = 0.21958040602385492;
                                attribute 'σ_Iyy' : Real = 0.3723953238821935;
                                attribute Izz : Real = 0.21344178653409862;
                                attribute 'σ_Izz' : Real = 0.37017423652493897;
                                attribute Ixy : Real = 0.021819800609497612;
                                attribute 'σ_Ixy' : Real = 0.02351283871158888;
                                attribute Ixz : Real = 8.911287761991166e-4;
                                attribute 'σ_Ixz' : Real = 0.022566176940390956;
                                attribute Iyz : Real = -0.0186394999023912;
                                attribute 'σ_Iyz' : Real = 0.02209918015384651;
                            }
                            part <'C.1.1.3.4.2.1.2'> 'Part 409' {
                                attribute POIconv : String = "-";
                                attribute Ipoint : Boolean = false;
                                attribute mass : Real = 0.43897415247443133;
                                attribute 'σ_mass' : Real = 0.28909372274994966;
                                attribute Cx : Real = -18.61683363094926;
                                attribute 'σ_Cx' : Real = 28.721044428837228;
                                attribute Cy : Real = 72.86121970973909;
                                attribute 'σ_Cy' : Real = 28.23690002309109;
                                attribute Cz : Real = 23.037515114992857;
                                attribute 'σ_Cz' : Real = 29.057750463592832;
                                attribute Ixx : Real = 0.44605191823287443;
                                attribute 'σ_Ixx' : Real = 0.37074144170588635;
                                attribute Iyy : Real = 0.423119749996979;
                                attribute 'σ_Iyy' : Real = 0.3723953238821935;
                                attribute Izz : Real = 0.4591348811002982;
                                attribute 'σ_Izz' : Real = 0.37017423652493897;
                                attribute Ixy : Real = -0.009507339906636107;
                                attribute 'σ_Ixy' : Real = 0.02351283871158888;
                                attribute Ixz : Real = 0.016389828073156927;
                                attribute 'σ_Ixz' : Real = 0.022566176940390956;
                                attribute Iyz : Real = -0.005493112804234082;
                                attribute 'σ_Iyz' : Real = 0.02209918015384651;
                            }
                            part <'C.1.1.3.4.2.1.3'> 'Part 410' {
                                attribute POIconv : String = "+";
                                attribute Ipoint : Boolean = false;
                                attribute mass : Real = 0.4230969448143151;
                                attribute 'σ_mass' : Real = 0.28909372274994966;
                                attribute Cx : Real = -72.17906429432333;
                                attribute 'σ_Cx' : Real = 28.721044428837228;
                                attribute Cy : Real = 23.088056361302733;
                                attribute 'σ_Cy' : Real = 28.23690002309109;
                                attribute Cz : Real = 45.48424556851387;
                                attribute 'σ_Cz' : Real = 29.057750463592832;
                                attribute Ixx : Real = 0.47713580324547084;
                                attribute 'σ_Ixx' : Real = 0.37074144170588635;
                                attribute Iyy : Real = 0.5160729656899032;
                                attribute 'σ_Iyy' : Real = 0.3723953238821935;
                                attribute Izz : Real = 0.5112368028958486;
                                attribute 'σ_Izz' : Real = 0.37017423652493897;
                                attribute Ixy : Real = 0.005362689733715618;
                                attribute 'σ_Ixy' : Real = 0.02351283871158888;
                                attribute Ixz : Real = -0.013146447500463534;
                                attribute 'σ_Ixz' : Real = 0.022566176940390956;
                                attribute Iyz : Real = 0.024373738886708192;
                                attribute 'σ_Iyz' : Real = 0.02209918015384651;
                            }
                            part <'C.1.1.3.4.2.1.4'> 'Part 411' {
                                attribute POIconv : String = "-";
                                attribute Ipoint : Boolean = false;
                                attribute mass : Real = 0.8920250170012005;
                                attribute 'σ_mass' : Real = 0.28909372274994966;
                                attribute Cx : Real = 37.23470354452729;
                                attribute 'σ_Cx' : Real = 28.721044428837228;
                                attribute Cy : Real = -52.53887167200446;
                                attribute 'σ_Cy' : Real = 28.23690002309109;
                                attribute Cz : Real = -28.632713202387094;
                                attribute 'σ_Cz' : Real = 29.057750463592832;
                                attribute Ixx : Real = 1.0363791732454524;
                                attribute 'σ_Ixx' : Real = 0.37074144170588635;
                                attribute Iyy : Real = 1.1797234902122078;
                                attribute 'σ_Iyy' : Real = 0.3723953238821935;
                                attribute Izz : Real = 1.1593994525113964;
                                attribute 'σ_Izz' : Real = 0.37017423652493897;
                                attribute Ixy : Real = 0.016031035594379205;
                                attribute 'σ_Ixy' : Real = 0.02351283871158888;
                                attribute Ixz : Real = -0.04507704927717492;
                                attribute 'σ_Ixz' : Real = 0.022566176940390956;
                                attribute Iyz : Real = 0.02967864631956357;
                                attribute 'σ_Iyz' : Real = 0.02209918015384651;
                            }
                            part <'C.1.1.3.4.2.1.5'> 'Part 412' {
                                attribute POIconv : String = "+";
                                attribute Ipoint : Boolean = false;
                                attribute mass : Real = 0.29362692803354;
                                attribute 'σ_mass' : Real = 0.28909372274994966;
                                attribute Cx : Real = 2.241061720997095;
                                attribute 'σ_Cx' : Real = 28.721044428837228;
                                attribute Cy : Real = 78.95983019843698;
                                attribute 'σ_Cy' : Real = 28.23690002309109;
                                attribute Cz : Real = -95.49570959061384;
                                attribute 'σ_Cz' : Real = 29.057750463592832;
                                attribute Ixx : Real = 0.38827923413755033;
                                attribute 'σ_Ixx' : Real = 0.37074144170588635;
                                attribute Iyy : Real = 0.37646143764130113;
                                attribute 'σ_Iyy' : Real = 0.3723953238821935;
                                attribute Izz : Real = 0.3405159154270556;
                                attribute 'σ_Izz' : Real = 0.37017423652493897;
                                attribute Ixy : Real = -0.017483453178526016;
                                attribute 'σ_Ixy' : Real = 0.02351283871158888;
                                attribute Ixz : Real = -0.027673259923126595;
                                attribute 'σ_Ixz' : Real = 0.022566176940390956;
                                attribute Iyz : Real = -0.0037475097195479373;
                                attribute 'σ_Iyz' : Real = 0.02209918015384651;
                            }
                        }
                        part <'C.1.1.3.4.2.2'> 'Subassembly 122' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.2.2.1'> 'Part 413' {
                                attribute POIconv : String = "+";
                                attribute Ipoint : Boolean = false;
                                attribute mass : Real = 0.024139781995909288;
                                attribute 'σ_mass' : Real = 0.28909372274994966;
                                attribute Cx : Real = 36.310502188280225;
                                attribute 'σ_Cx' : Real = 28.721044428837228;
                                attribute Cy : Real = -40.669127414003015;
                                attribute 'σ_Cy' : Real = 28.23690002309109;
                                attribute Cz : Real = 62.32147407718003;
                                attribute 'σ_Cz' : Real = 29.057750463592832;
                                attribute Ixx : Real = 0.02725767100247586;
                                attribute 'σ_Ixx' : Real = 0.37074144170588635;
                                attribute Iyy : Real = 0.028449406874629875;
                                attribute 'σ_Iyy' : Real = 0.3723953238821935;
                                attribute Izz : Real = 0.029119918900478353;
                                attribute 'σ_Izz' : Real = 0.37017423652493897;
                                attribute Ixy : Real = -0.0011269054922727296;
                                attribute 'σ_Ixy' : Real = 0.02351283871158888;
                                attribute Ixz : Real = 9.569078179064694e-4;
                                attribute 'σ_Ixz' : Real = 0.022566176940390956;
                                attribute Iyz : Real = -5.473443458944047e-4;
                                attribute 'σ_Iyz' : Real = 0.02209918015384651;
                            }
                            part <'C.1.1.3.4.2.2.2'> 'Part 414' {
                                attribute POIconv : String = "-";
                                attribute Ipoint : Boolean = false;
                                attribute mass : Real = 0.14478296251338907;
                                attribute 'σ_mass' : Real = 0.28909372274994966;
                                attribute Cx : Real = -77.49893115833402;
                                attribute 'σ_Cx' : Real = 28.721044428837228;
                                attribute Cy : Real = 22.258880455046892;
                                attribute 'σ_Cy' : Real = 28.23690002309109;
                                attribute Cz : Real = 52.422992466017604;
                                attribute 'σ_Cz' : Real = 29.057750463592832;
                                attribute Ixx : Real = 0.23362975257959445;
                                attribute 'σ_Ixx' : Real = 0.37074144170588635;
                                attribute Iyy : Real = 0.23358908022952157;
                                attribute 'σ_Iyy' : Real = 0.3723953238821935;
                                attribute Izz : Real = 0.22890509317639687;
                                attribute 'σ_Izz' : Real = 0.37017423652493897;
                                attribute Ixy : Real = -0.003198497675131393;
                                attribute 'σ_Ixy' : Real = 0.02351283871158888;
                                attribute Ixz : Real = 6.681676007187626e-4;
                                attribute 'σ_Ixz' : Real = 0.022566176940390956;
                                attribute Iyz : Real = -0.0010659668910849155;
                                attribute 'σ_Iyz' : Real = 0.02209918015384651;
                            }
                        }
                        part <'C.1.1.3.4.2.3'> 'Subassembly 123' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.2.3.1'> 'Part 415' {
                                attribute POIconv : String = "+";
                                attribute Ipoint : Boolean = false;
                                attribute mass : Real = 0.06433200815482996;
                                attribute 'σ_mass' : Real = 0.28909372274994966;
                                attribute Cx : Real = -62.4487120192498;
                                attribute 'σ_Cx' : Real = 28.721044428837228;
                                attribute Cy : Real = 13.181356946006417;
                                attribute 'σ_Cy' : Real = 28.23690002309109;
                                attribute Cz : Real = -18.05400256998837;
                                attribute 'σ_Cz' : Real = 29.057750463592832;
                                attribute Ixx : Real = 0.08566464022186969;
                                attribute 'σ_Ixx' : Real = 0.37074144170588635;
                                attribute Iyy : Real = 0.07957924592555442;
                                attribute 'σ_Iyy' : Real = 0.3723953238821935;
                                attribute Izz : Real = 0.07906301086929615;
                                attribute 'σ_Izz' : Real = 0.37017423652493897;
                                attribute Ixy : Real = -3.6168274917020086e-4;
                                attribute 'σ_Ixy' : Real = 0.02351283871158888;
                                attribute Ixz : Real = 0.002018733544854123;
                                attribute 'σ_Ixz' : Real = 0.022566176940390956;
                                attribute Iyz : Real = 5.957072987563077e-4;
                                attribute 'σ_Iyz' : Real = 0.02209918015384651;
                            }
                            part <'C.1.1.3.4.2.3.2'> 'Part 416' {
                                attribute POIconv : String = "-";
                                attribute Ipoint : Boolean = false;
                                attribute mass : Real = 0.10031190048041753;
                                attribute 'σ_mass' : Real = 0.28909372274994966;
                                attribute Cx : Real = 71.95553602650762;
                                attribute 'σ_Cx' : Real = 28.721044428837228;
                                attribute Cy : Real = 82.88714457303286;
                                attribute 'σ_Cy' : Real = 28.23690002309109;
                                attribute Cz : Real = 8.078076411038637;
                                attribute 'σ_Cz' : Real = 29.057750463592832;
                                attribute Ixx : Real = 0.10514094988994091;
                                attribute 'σ_Ixx' : Real = 0.37074144170588635;
                                attribute Iyy : Real = 0.11587802145332216;
                                attribute 'σ_Iyy' : Real = 0.3723953238821935;
                                attribute Izz : Real = 0.11635948471954839;
                                attribute 'σ_Izz' : Real = 0.37017423652493897;
                                attribute Ixy : Real = 0.00845071023177046;
                                attribute 'σ_Ixy' : Real = 0.02351283871158888;
                                attribute Ixz : Real = 0.003539751587460147;
                                attribute 'σ_Ixz' : Real = 0.022566176940390956;
                                attribute Iyz : Real = -0.001929995543931993;
                                attribute 'σ_Iyz' : Real = 0.02209918015384651;
                            }
                            part <'C.1.1.3.4.2.3.3'> 'Part 417' {
                                attribute POIconv : String = "-";
                                attribute Ipoint : Boolean = false;
                                attribute mass : Real = 0.5723079992267304;
                                attribute 'σ_mass' : Real = 0.28909372274994966;
                                attribute Cx : Real = -66.13396527245641;
                                attribute 'σ_Cx' : Real = 28.721044428837228;
                                attribute Cy : Real = -49.28406924009323;
                                attribute 'σ_Cy' : Real = 28.23690002309109;
                                attribute Cz : Real = -25.011775083839893;
                                attribute 'σ_Cz' : Real = 29.057750463592832;
                                attribute Ixx : Real = 0.6609021357116578;
                                attribute 'σ_Ixx' : Real = 0.37074144170588635;
                                attribute Iyy : Real = 0.6154983600102096;
                                attribute 'σ_Iyy' : Real = 0.3723953238821935;
                                attribute Izz : Real = 0.6562060659766807;
                                attribute 'σ_Izz' : Real = 0.37017423652493897;
                                attribute Ixy : Real = 0.020567430151987084;
                                attribute 'σ_Ixy' : Real = 0.02351283871158888;
                                attribute Ixz : Real = 0.01615066952888317;
                                attribute 'σ_Ixz' : Real = 0.022566176940390956;
                                attribute Iyz : Real = -0.01762408074186115;
                                attribute 'σ_Iyz' : Real = 0.02209918015384651;
                            }
                            part <'C.1.1.3.4.2.3.4'> 'Part 418' {
                                attribute POIconv : String = "-";
                                attribute Ipoint : Boolean = false;
                                attribute mass : Real = 0.2637710998051334;
                                attribute 'σ_mass' : Real = 0.28909372274994966;
                                attribute Cx : Real = -79.26640072837472;
                                attribute 'σ_Cx' : Real = 28.721044428837228;
                                attribute Cy : Real = 64.68511871062219;
                                attribute 'σ_Cy' : Real = 28.23690002309109;
                                attribute Cz : Real = 4.939874680712819;
                                attribute 'σ_Cz' : Real = 29.057750463592832;
                                attribute Ixx : Real = 0.3782530263720684;
                                attribute 'σ_Ixx' : Real = 0.37074144170588635;
                                attribute Iyy : Real = 0.41130659593939833;
                                attribute 'σ_Iyy' : Real = 0.3723953238821935;
                                attribute Izz : Real = 0.3772507662053588;
                                attribute 'σ_Izz' : Real = 0.37017423652493897;
                                attribute Ixy : Real = 0.007664042749313265;
                                attribute 'σ_Ixy' : Real = 0.02351283871158888;
                                attribute Ixz : Real = -4.993204632608903e-4;
                                attribute 'σ_Ixz' : Real = 0.022566176940390956;
                                attribute Iyz : Real = -0.006820167317350705;
                                attribute 'σ_Iyz' : Real = 0.02209918015384651;
                            }
                        }
                    }
                    part <'C.1.1.3.4.3'> 'Assembly 34' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.4.3.1'> 'Subassembly 124' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.3.1.1'> 'Part 419' {
                                attribute POIconv : String = "-";
                                attribute Ipoint : Boolean = false;
                                attribute mass : Real = 0.9094892434936482;
                                attribute 'σ_mass' : Real = 0.28909372274994966;
                                attribute Cx : Real = 31.119699776172638;
                                attribute 'σ_Cx' : Real = 28.721044428837228;
                                attribute Cy : Real = 2.8392952401190996;
                                attribute 'σ_Cy' : Real = 28.23690002309109;
                                attribute Cz : Real = 69.49903233908117;
                                attribute 'σ_Cz' : Real = 29.057750463592832;
                                attribute Ixx : Real = 1.1504223119759562;
                                attribute 'σ_Ixx' : Real = 0.37074144170588635;
                                attribute Iyy : Real = 1.1416502130204527;
                                attribute 'σ_Iyy' : Real = 0.3723953238821935;
                                attribute Izz : Real = 1.1305561568253273;
                                attribute 'σ_Izz' : Real = 0.37017423652493897;
                                attribute Ixy : Real = 0.012050616902505026;
                                attribute 'σ_Ixy' : Real = 0.02351283871158888;
                                attribute Ixz : Real = -0.05505218775244497;
                                attribute 'σ_Ixz' : Real = 0.022566176940390956;
                                attribute Iyz : Real = 0.14646742835867904;
                                attribute 'σ_Iyz' : Real = 0.02209918015384651;
                            }
                            part <'C.1.1.3.4.3.1.2'> 'Part 420' {
                                attribute POIconv : String = "+";
                                attribute Ipoint : Boolean = false;
                                attribute mass : Real = 0.056092325994046406;
                                attribute 'σ_mass' : Real = 0.28909372274994966;
                                attribute Cx : Real = -42.156867450103164;
                                attribute 'σ_Cx' : Real = 28.721044428837228;
                                attribute Cy : Real = 56.02856012992561;
                                attribute 'σ_Cy' : Real = 28.23690002309109;
                                attribute Cz : Real = 5.715644173324108;
                                attribute 'σ_Cz' : Real = 29.057750463592832;
                                attribute Ixx : Real = 0.06504277006679979;
                                attribute 'σ_Ixx' : Real = 0.37074144170588635;
                                attribute Iyy : Real = 0.06544339871914866;
                                attribute 'σ_Iyy' : Real = 0.3723953238821935;
                                attribute Izz : Real = 0.06000423625942878;
                                attribute 'σ_Izz' : Real = 0.37017423652493897;
                                attribute Ixy : Real = -0.005251276244350761;
                                attribute 'σ_Ixy' : Real = 0.02351283871158888;
                                attribute Ixz : Real = 2.3519043571815527e-4;
                                attribute 'σ_Ixz' : Real = 0.022566176940390956;
                                attribute Iyz : Real = 3.1209772740813774e-4;
                                attribute 'σ_Iyz' : Real = 0.02209918015384651;
                            }
                            part <'C.1.1.3.4.3.1.3'> 'Part 421' {
                                attribute POIconv : String = "+";
                                attribute Ipoint : Boolean = false;
                                attribute mass : Real = 0.7712667896512431;
                                attribute 'σ_mass' : Real = 0.28909372274994966;
                                attribute Cx : Real = 50.49127829261124;
                                attribute 'σ_Cx' : Real = 28.721044428837228;
                                attribute Cy : Real = 34.31079708971083;
                                attribute 'σ_Cy' : Real = 28.23690002309109;
                                attribute Cz : Real = -74.79756544344127;
                                attribute 'σ_Cz' : Real = 29.057750463592832;
                                attribute Ixx : Real = 0.9871082772418219;
                                attribute 'σ_Ixx' : Real = 0.37074144170588635;
                                attribute Iyy : Real = 1.135314894551172;
                                attribute 'σ_Iyy' : Real = 0.3723953238821935;
                                attribute Izz : Real = 0.958963437482463;
                                attribute 'σ_Izz' : Real = 0.37017423652493897;
                                attribute Ixy : Real = -0.015573484141639272;
                                attribute 'σ_Ixy' : Real = 0.02351283871158888;
                                attribute Ixz : Real = 0.03863617195036039;
                                attribute 'σ_Ixz' : Real = 0.022566176940390956;
                                attribute Iyz : Real = 0.006372216276006405;
                                attribute 'σ_Iyz' : Real = 0.02209918015384651;
                            }
                            part <'C.1.1.3.4.3.1.4'> 'Part 422' {
                                attribute POIconv : String = "+";
                                attribute Ipoint : Boolean = false;
                                attribute mass : Real = 0.004991268917685375;
                                attribute 'σ_mass' : Real = 0.28909372274994966;
                                attribute Cx : Real = -87.43514423258603;
                                attribute 'σ_Cx' : Real = 28.721044428837228;
                                attribute Cy : Real = 54.64492975734174;
                                attribute 'σ_Cy' : Real = 28.23690002309109;
                                attribute Cz : Real = 46.778071066364646;
                                attribute 'σ_Cz' : Real = 29.057750463592832;
                                attribute Ixx : Real = 0.006088800972864968;
                                attribute 'σ_Ixx' : Real = 0.37074144170588635;
                                attribute Iyy : Real = 0.007678660092115591;
                                attribute 'σ_Iyy' : Real = 0.3723953238821935;
                                attribute Izz : Real = 0.0059435410288471505;
                                attribute 'σ_Izz' : Real = 0.37017423652493897;
                                attribute Ixy : Real = 1.31165732127468e-4;
                                attribute 'σ_Ixy' : Real = 0.02351283871158888;
                                attribute Ixz : Real = 8.949518996066784e-6;
                                attribute 'σ_Ixz' : Real = 0.022566176940390956;
                                attribute Iyz : Real = -8.833961850856149e-5;
                                attribute 'σ_Iyz' : Real = 0.02209918015384651;
                            }
                            part <'C.1.1.3.4.3.1.5'> 'Part 423' {
                                attribute POIconv : String = "+";
                                attribute Ipoint : Boolean = false;
                                attribute mass : Real = 0.20979108423204162;
                                attribute 'σ_mass' : Real = 0.28909372274994966;
                                attribute Cx : Real = -35.78577642329037;
                                attribute 'σ_Cx' : Real = 28.721044428837228;
                                attribute Cy : Real = -25.91273649595678;
                                attribute 'σ_Cy' : Real = 28.23690002309109;
                                attribute Cz : Real = 14.792789099738002;
                                attribute 'σ_Cz' : Real = 29.057750463592832;
                                attribute Ixx : Real = 0.22360810381027588;
                                attribute 'σ_Ixx' : Real = 0.37074144170588635;
                                attribute Iyy : Real = 0.27521734285092225;
                                attribute 'σ_Iyy' : Real = 0.3723953238821935;
                                attribute Izz : Real = 0.24899191416365518;
                                attribute 'σ_Izz' : Real = 0.37017423652493897;
                                attribute Ixy : Real = 0.0072782882331234805;
                                attribute 'σ_Ixy' : Real = 0.02351283871158888;
                                attribute Ixz : Real = 0.0041285929694535465;
                                attribute 'σ_Ixz' : Real = 0.022566176940390956;
                                attribute Iyz : Real = -0.013297867711905137;
                                attribute 'σ_Iyz' : Real = 0.02209918015384651;
                            }
                        }
                        part <'C.1.1.3.4.3.2'> 'Subassembly 125' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.3.2.1'> 'Part 424' {
                                attribute POIconv : String = "-";
                                attribute Ipoint : Boolean = false;
                                attribute mass : Real = 0.7085896115608048;
                                attribute 'σ_mass' : Real = 0.28909372274994966;
                                attribute Cx : Real = 50.68416763097048;
                                attribute 'σ_Cx' : Real = 28.721044428837228;
                                attribute Cy : Real = 82.89898103103042;
                                attribute 'σ_Cy' : Real = 28.23690002309109;
                                attribute Cz : Real = 71.7518663033843;
                                attribute 'σ_Cz' : Real = 29.057750463592832;
                                attribute Ixx : Real = 0.9043909380336036;
                                attribute 'σ_Ixx' : Real = 0.37074144170588635;
                                attribute Iyy : Real = 1.0121323017280928;
                                attribute 'σ_Iyy' : Real = 0.3723953238821935;
                                attribute Izz : Real = 0.8309264105436839;
                                attribute 'σ_Izz' : Real = 0.37017423652493897;
                                attribute Ixy : Real = 0.021018447601426845;
                                attribute 'σ_Ixy' : Real = 0.02351283871158888;
                                attribute Ixz : Real = 0.01599300158227033;
                                attribute 'σ_Ixz' : Real = 0.022566176940390956;
                                attribute Iyz : Real = 0.020155343136182443;
                                attribute 'σ_Iyz' : Real = 0.02209918015384651;
                            }
                            part <'C.1.1.3.4.3.2.2'> 'Part 425' {
                                attribute POIconv : String = "-";
                                attribute Ipoint : Boolean = false;
                                attribute mass : Real = 0.6071510485748295;
                                attribute 'σ_mass' : Real = 0.28909372274994966;
                                attribute Cx : Real = 51.124310214072466;
                                attribute 'σ_Cx' : Real = 28.721044428837228;
                                attribute Cy : Real = -40.69296699017286;
                                attribute 'σ_Cy' : Real = 28.23690002309109;
                                attribute Cz : Real = -34.6518465783447;
                                attribute 'σ_Cz' : Real = 29.057750463592832;
                                attribute Ixx : Real = 0.9696378865536255;
                                attribute 'σ_Ixx' : Real = 0.37074144170588635;
                                attribute Iyy : Real = 0.7297743049644179;
                                attribute 'σ_Iyy' : Real = 0.3723953238821935;
                                attribute Izz : Real = 0.7529669742050189;
                                attribute 'σ_Izz' : Real = 0.37017423652493897;
                                attribute Ixy : Real = -0.00981735626742393;
                                attribute 'σ_Ixy' : Real = 0.02351283871158888;
                                attribute Ixz : Real = -0.010655605892752287;
                                attribute 'σ_Ixz' : Real = 0.022566176940390956;
                                attribute Iyz : Real = 1.062941215031453e-4;
                                attribute 'σ_Iyz' : Real = 0.02209918015384651;
                            }
                            part <'C.1.1.3.4.3.2.3'> 'Part 426' {
                                attribute POIconv : String = "-";
                                attribute Ipoint : Boolean = false;
                                attribute mass : Real = 0.3420617082384415;
                                attribute 'σ_mass' : Real = 0.28909372274994966;
                                attribute Cx : Real = 55.06562381051481;
                                attribute 'σ_Cx' : Real = 28.721044428837228;
                                attribute Cy : Real = -19.12492853589356;
                                attribute 'σ_Cy' : Real = 28.23690002309109;
                                attribute Cz : Real = -51.139960857108235;
                                attribute 'σ_Cz' : Real = 29.057750463592832;
                                attribute Ixx : Real = 0.4226112484799215;
                                attribute 'σ_Ixx' : Real = 0.37074144170588635;
                                attribute Iyy : Real = 0.4280910250588482;
                                attribute 'σ_Iyy' : Real = 0.3723953238821935;
                                attribute Izz : Real = 0.5254632884728919;
                                attribute 'σ_Izz' : Real = 0.37017423652493897;
                                attribute Ixy : Real = 0.013279943992562025;
                                attribute 'σ_Ixy' : Real = 0.02351283871158888;
                                attribute Ixz : Real = -0.00445438574511089;
                                attribute 'σ_Ixz' : Real = 0.022566176940390956;
                                attribute Iyz : Real = -5.948309692246035e-4;
                                attribute 'σ_Iyz' : Real = 0.02209918015384651;
                            }
                        }
                        part <'C.1.1.3.4.3.3'> 'Subassembly 126' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.3.3.1'> 'Part 427' {
                                attribute POIconv : String = "+";
                                attribute Ipoint : Boolean = false;
                                attribute mass : Real = 0.1619111926262267;
                                attribute 'σ_mass' : Real = 0.28909372274994966;
                                attribute Cx : Real = 39.433434093371034;
                                attribute 'σ_Cx' : Real = 28.721044428837228;
                                attribute Cy : Real = 77.78569520451128;
                                attribute 'σ_Cy' : Real = 28.23690002309109;
                                attribute Cz : Real = 40.61036272905767;
                                attribute 'σ_Cz' : Real = 29.057750463592832;
                                attribute Ixx : Real = 0.24154281886653436;
                                attribute 'σ_Ixx' : Real = 0.37074144170588635;
                                attribute Iyy : Real = 0.22907819321482933;
                                attribute 'σ_Iyy' : Real = 0.3723953238821935;
                                attribute Izz : Real = 0.21653905545625635;
                                attribute 'σ_Izz' : Real = 0.37017423652493897;
                                attribute Ixy : Real = 0.0021217997868077194;
                                attribute 'σ_Ixy' : Real = 0.02351283871158888;
                                attribute Ixz : Real = 0.0022567388079550985;
                                attribute 'σ_Ixz' : Real = 0.022566176940390956;
                                attribute Iyz : Real = 0.006999220167089734;
                                attribute 'σ_Iyz' : Real = 0.02209918015384651;
                            }
                            part <'C.1.1.3.4.3.3.2'> 'Part 428' {
                                attribute POIconv : String = "+";
                                attribute Ipoint : Boolean = false;
                                attribute mass : Real = 0.11763801411306486;
                                attribute 'σ_mass' : Real = 0.28909372274994966;
                                attribute Cx : Real = 38.77464202232659;
                                attribute 'σ_Cx' : Real = 28.721044428837228;
                                attribute Cy : Real = 95.31572475098073;
                                attribute 'σ_Cy' : Real = 28.23690002309109;
                                attribute Cz : Real = -95.81605116836727;
                                attribute 'σ_Cz' : Real = 29.057750463592832;
                                attribute Ixx : Real = 0.1643331654313929;
                                attribute 'σ_Ixx' : Real = 0.37074144170588635;
                                attribute Iyy : Real = 0.16215992295845438;
                                attribute 'σ_Iyy' : Real = 0.3723953238821935;
                                attribute Izz : Real = 0.1714428350223776;
                                attribute 'σ_Izz' : Real = 0.37017423652493897;
                                attribute Ixy : Real = 0.010306780963460351;
                                attribute 'σ_Ixy' : Real = 0.02351283871158888;
                                attribute Ixz : Real = -0.0025066130310973473;
                                attribute 'σ_Ixz' : Real = 0.022566176940390956;
                                attribute Iyz : Real = -0.005056696363882812;
                                attribute 'σ_Iyz' : Real = 0.02209918015384651;
                            }
                        }
                        part <'C.1.1.3.4.3.4'> 'Subassembly 127' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.3.4.1'> 'Part 429' {
                                attribute POIconv : String = "-";
                                attribute Ipoint : Boolean = false;
                                attribute mass : Real = 0.029794306237716228;
                                attribute 'σ_mass' : Real = 0.28909372274994966;
                                attribute Cx : Real = 45.429380843415856;
                                attribute 'σ_Cx' : Real = 28.721044428837228;
                                attribute Cy : Real = 26.719054905697703;
                                attribute 'σ_Cy' : Real = 28.23690002309109;
                                attribute Cz : Real = -94.2824135068804;
                                attribute 'σ_Cz' : Real = 29.057750463592832;
                                attribute Ixx : Real = 0.0351440098797554;
                                attribute 'σ_Ixx' : Real = 0.37074144170588635;
                                attribute Iyy : Real = 0.03770904454056056;
                                attribute 'σ_Iyy' : Real = 0.3723953238821935;
                                attribute Izz : Real = 0.034440097297161784;
                                attribute 'σ_Izz' : Real = 0.37017423652493897;
                                attribute Ixy : Real = 1.6006458800752843e-4;
                                attribute 'σ_Ixy' : Real = 0.02351283871158888;
                                attribute Ixz : Real = 0.002924436136549487;
                                attribute 'σ_Ixz' : Real = 0.022566176940390956;
                                attribute Iyz : Real = -1.7606686273497803e-4;
                                attribute 'σ_Iyz' : Real = 0.02209918015384651;
                            }
                            part <'C.1.1.3.4.3.4.2'> 'Part 430' {
                                attribute POIconv : String = "+";
                                attribute Ipoint : Boolean = false;
                                attribute mass : Real = 0.5003303071025293;
                                attribute 'σ_mass' : Real = 0.28909372274994966;
                                attribute Cx : Real = 59.56250415183604;
                                attribute 'σ_Cx' : Real = 28.721044428837228;
                                attribute Cy : Real = -30.107643827795982;
                                attribute 'σ_Cy' : Real = 28.23690002309109;
                                attribute Cz : Real = 59.00630345568061;
                                attribute 'σ_Cz' : Real = 29.057750463592832;
                                attribute Ixx : Real = 0.6510155006328452;
                                attribute 'σ_Ixx' : Real = 0.37074144170588635;
                                attribute Iyy : Real = 0.7674421556152697;
                                attribute 'σ_Iyy' : Real = 0.3723953238821935;
                                attribute Izz : Real = 0.6215946714821855;
                                attribute 'σ_Izz' : Real = 0.37017423652493897;
                                attribute Ixy : Real = 0.03319655461440689;
                                attribute 'σ_Ixy' : Real = 0.02351283871158888;
                                attribute Ixz : Real = 0.01838404888949848;
                                attribute 'σ_Ixz' : Real = 0.022566176940390956;
                                attribute Iyz : Real = -0.03798131030457702;
                                attribute 'σ_Iyz' : Real = 0.02209918015384651;
                            }
                            part <'C.1.1.3.4.3.4.3'> 'Part 431' {
                                attribute POIconv : String = "+";
                                attribute Ipoint : Boolean = false;
                                attribute mass : Real = 0.9400139372036792;
                                attribute 'σ_mass' : Real = 0.28909372274994966;
                                attribute Cx : Real = 70.35587434656918;
                                attribute 'σ_Cx' : Real = 28.721044428837228;
                                attribute Cy : Real = -78.75907151028514;
                                attribute 'σ_Cy' : Real = 28.23690002309109;
                                attribute Cz : Real = -2.960251597687602;
                                attribute 'σ_Cz' : Real = 29.057750463592832;
                                attribute Ixx : Real = 1.1048786939949125;
                                attribute 'σ_Ixx' : Real = 0.37074144170588635;
                                attribute Iyy : Real = 1.1028865908242194;
                                attribute 'σ_Iyy' : Real = 0.3723953238821935;
                                attribute Izz : Real = 0.9030065288808734;
                                attribute 'σ_Izz' : Real = 0.37017423652493897;
                                attribute Ixy : Real = 0.056158234996003656;
                                attribute 'σ_Ixy' : Real = 0.02351283871158888;
                                attribute Ixz : Real = -0.10483425118501807;
                                attribute 'σ_Ixz' : Real = 0.022566176940390956;
                                attribute Iyz : Real = -0.08826017583415448;
                                attribute 'σ_Iyz' : Real = 0.02209918015384651;
                            }
                            part <'C.1.1.3.4.3.4.4'> 'Part 432' {
                                attribute POIconv : String = "-";
                                attribute Ipoint : Boolean = false;
                                attribute mass : Real = 0.158609783468768;
                                attribute 'σ_mass' : Real = 0.28909372274994966;
                                attribute Cx : Real = -44.00008297525346;
                                attribute 'σ_Cx' : Real = 28.721044428837228;
                                attribute Cy : Real = 40.450009098276496;
                                attribute 'σ_Cy' : Real = 28.23690002309109;
                                attribute Cz : Real = -39.13062531501055;
                                attribute 'σ_Cz' : Real = 29.057750463592832;
                                attribute Ixx : Real = 0.21768747069022196;
                                attribute 'σ_Ixx' : Real = 0.37074144170588635;
                                attribute Iyy : Real = 0.21859048473007575;
                                attribute 'σ_Iyy' : Real = 0.3723953238821935;
                                attribute Izz : Real = 0.21110189911333235;
                                attribute 'σ_Izz' : Real = 0.37017423652493897;
                                attribute Ixy : Real = -0.016849790326129516;
                                attribute 'σ_Ixy' : Real = 0.02351283871158888;
                                attribute Ixz : Real = 0.0037306280567339623;
                                attribute 'σ_Ixz' : Real = 0.022566176940390956;
                                attribute Iyz : Real = 0.007845058481487095;
                                attribute 'σ_Iyz' : Real = 0.02209918015384651;
                            }
                            part <'C.1.1.3.4.3.4.5'> 'Part 433' {
                                attribute POIconv : String = "+";
                                attribute Ipoint : Boolean = false;
                                attribute mass : Real = 0.7424533020022791;
                                attribute 'σ_mass' : Real = 0.28909372274994966;
                                attribute Cx : Real = -60.69240141659975;
                                attribute 'σ_Cx' : Real = 28.721044428837228;
                                attribute Cy : Real = 48.528230749070644;
                                attribute 'σ_Cy' : Real = 28.23690002309109;
                                attribute Cz : Real = 12.667262274771929;
                                attribute 'σ_Cz' : Real = 29.057750463592832;
                                attribute Ixx : Real = 1.1081461745810353;
                                attribute 'σ_Ixx' : Real = 0.37074144170588635;
                                attribute Iyy : Real = 0.949089420021869;
                                attribute 'σ_Iyy' : Real = 0.3723953238821935;
                                attribute Izz : Real = 0.9982687442612806;
                                attribute 'σ_Izz' : Real = 0.37017423652493897;
                                attribute Ixy : Real = -0.0056058837701114155;
                                attribute 'σ_Ixy' : Real = 0.02351283871158888;
                                attribute Ixz : Real = 0.007615769199301767;
                                attribute 'σ_Ixz' : Real = 0.022566176940390956;
                                attribute Iyz : Real = -0.03573553233987374;
                                attribute 'σ_Iyz' : Real = 0.02209918015384651;
                            }
                        }
                        part <'C.1.1.3.4.3.5'> 'Subassembly 128' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.3.5.1'> 'Part 434' {
                                attribute POIconv : String = "-";
                                attribute Ipoint : Boolean = false;
                                attribute mass : Real = 0.48597481388016606;
                                attribute 'σ_mass' : Real = 0.28909372274994966;
                                attribute Cx : Real = 53.43048204667866;
                                attribute 'σ_Cx' : Real = 28.721044428837228;
                                attribute Cy : Real = 3.8660902995616198;
                                attribute 'σ_Cy' : Real = 28.23690002309109;
                                attribute Cz : Real = -64.58254107274115;
                                attribute 'σ_Cz' : Real = 29.057750463592832;
                                attribute Ixx : Real = 0.5813709162591114;
                                attribute 'σ_Ixx' : Real = 0.37074144170588635;
                                attribute Iyy : Real = 0.5370018953907398;
                                attribute 'σ_Iyy' : Real = 0.3723953238821935;
                                attribute Izz : Real = 0.573491080162924;
                                attribute 'σ_Izz' : Real = 0.37017423652493897;
                                attribute Ixy : Real = -0.006438100087433812;
                                attribute 'σ_Ixy' : Real = 0.02351283871158888;
                                attribute Ixz : Real = -0.04174474211502744;
                                attribute 'σ_Ixz' : Real = 0.022566176940390956;
                                attribute Iyz : Real = 0.004643443325828774;
                                attribute 'σ_Iyz' : Real = 0.02209918015384651;
                            }
                            part <'C.1.1.3.4.3.5.2'> 'Part 435' {
                                attribute POIconv : String = "+";
                                attribute Ipoint : Boolean = false;
                                attribute mass : Real = 0.024395917544607074;
                                attribute 'σ_mass' : Real = 0.28909372274994966;
                                attribute Cx : Real = -59.11577641963959;
                                attribute 'σ_Cx' : Real = 28.721044428837228;
                                attribute Cy : Real = -4.303654516115785;
                                attribute 'σ_Cy' : Real = 28.23690002309109;
                                attribute Cz : Real = -57.07873138599098;
                                attribute 'σ_Cz' : Real = 29.057750463592832;
                                attribute Ixx : Real = 0.032565620792309596;
                                attribute 'σ_Ixx' : Real = 0.37074144170588635;
                                attribute Iyy : Real = 0.03232860716542206;
                                attribute 'σ_Iyy' : Real = 0.3723953238821935;
                                attribute Izz : Real = 0.030758970733119513;
                                attribute 'σ_Izz' : Real = 0.37017423652493897;
                                attribute Ixy : Real = 4.5978983486391015e-4;
                                attribute 'σ_Ixy' : Real = 0.02351283871158888;
                                attribute Ixz : Real = -0.0021135067278569243;
                                attribute 'σ_Ixz' : Real = 0.022566176940390956;
                                attribute Iyz : Real = 1.8526442473190197e-4;
                                attribute 'σ_Iyz' : Real = 0.02209918015384651;
                            }
                        }
                    }
                    part <'C.1.1.3.4.4'> 'Assembly 35' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.4.4.1'> 'Subassembly 129' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.4.1.1'> 'Part 436' {
                                attribute POIconv : String = "+";
                                attribute Ipoint : Boolean = false;
                                attribute mass : Real = 0.3480424385853112;
                                attribute 'σ_mass' : Real = 0.28909372274994966;
                                attribute Cx : Real = 57.54070375114679;
                                attribute 'σ_Cx' : Real = 28.721044428837228;
                                attribute Cy : Real = 14.480746164917946;
                                attribute 'σ_Cy' : Real = 28.23690002309109;
                                attribute Cz : Real = -30.676222499459982;
                                attribute 'σ_Cz' : Real = 29.057750463592832;
                                attribute Ixx : Real = 0.37923024432900126;
                                attribute 'σ_Ixx' : Real = 0.37074144170588635;
                                attribute Iyy : Real = 0.42781526515126506;
                                attribute 'σ_Iyy' : Real = 0.3723953238821935;
                                attribute Izz : Real = 0.4651090471883633;
                                attribute 'σ_Izz' : Real = 0.37017423652493897;
                                attribute Ixy : Real = -0.023435525630714237;
                                attribute 'σ_Ixy' : Real = 0.02351283871158888;
                                attribute Ixz : Real = 0.024135619321135737;
                                attribute 'σ_Ixz' : Real = 0.022566176940390956;
                                attribute Iyz : Real = 0.005961486876783505;
                                attribute 'σ_Iyz' : Real = 0.02209918015384651;
                            }
                            part <'C.1.1.3.4.4.1.2'> 'Part 437' {
                                attribute POIconv : String = "-";
                                attribute Ipoint : Boolean = false;
                                attribute mass : Real = 0.08925935830641538;
                                attribute 'σ_mass' : Real = 0.28909372274994966;
                                attribute Cx : Real = -94.65510570444167;
                                attribute 'σ_Cx' : Real = 28.721044428837228;
                                attribute Cy : Real = 77.24496074952185;
                                attribute 'σ_Cy' : Real = 28.23690002309109;
                                attribute Cz : Real = 93.67089378647506;
                                attribute 'σ_Cz' : Real = 29.057750463592832;
                                attribute Ixx : Real = 0.11339744422302175;
                                attribute 'σ_Ixx' : Real = 0.37074144170588635;
                                attribute Iyy : Real = 0.11186144820662926;
                                attribute 'σ_Iyy' : Real = 0.3723953238821935;
                                attribute Izz : Real = 0.10909778118314283;
                                attribute 'σ_Izz' : Real = 0.37017423652493897;
                                attribute Ixy : Real = -0.008898110007961358;
                                attribute 'σ_Ixy' : Real = 0.02351283871158888;
                                attribute Ixz : Real = -2.2610005020483852e-4;
                                attribute 'σ_Ixz' : Real = 0.022566176940390956;
                                attribute Iyz : Real = -6.522884395466499e-4;
                                attribute 'σ_Iyz' : Real = 0.02209918015384651;
                            }
                            part <'C.1.1.3.4.4.1.3'> 'Part 438' {
                                attribute POIconv : String = "-";
                                attribute Ipoint : Boolean = false;
                                attribute mass : Real = 0.9642336119981483;
                                attribute 'σ_mass' : Real = 0.28909372274994966;
                                attribute Cx : Real = -0.4992638248950243;
                                attribute 'σ_Cx' : Real = 28.721044428837228;
                                attribute Cy : Real = 1.2513617053627968;
                                attribute 'σ_Cy' : Real = 28.23690002309109;
                                attribute Cz : Real = -85.95239333808422;
                                attribute 'σ_Cz' : Real = 29.057750463592832;
                                attribute Ixx : Real = 0.9699863062211797;
                                attribute 'σ_Ixx' : Real = 0.37074144170588635;
                                attribute Iyy : Real = 1.2079574364458971;
                                attribute 'σ_Iyy' : Real = 0.3723953238821935;
                                attribute Izz : Real = 1.2376753762277009;
                                attribute 'σ_Izz' : Real = 0.37017423652493897;
                                attribute Ixy : Real = -0.1174213643025402;
                                attribute 'σ_Ixy' : Real = 0.02351283871158888;
                                attribute Ixz : Real = -0.026273893843116708;
                                attribute 'σ_Ixz' : Real = 0.022566176940390956;
                                attribute Iyz : Real = -0.009570120433749545;
                                attribute 'σ_Iyz' : Real = 0.02209918015384651;
                            }
                        }
                        part <'C.1.1.3.4.4.2'> 'Subassembly 130' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.4.2.1'> 'Part 439' {
                                attribute POIconv : String = "-";
                                attribute Ipoint : Boolean = false;
                                attribute mass : Real = 0.3171077902994584;
                                attribute 'σ_mass' : Real = 0.28909372274994966;
                                attribute Cx : Real = 11.465211166068912;
                                attribute 'σ_Cx' : Real = 28.721044428837228;
                                attribute Cy : Real = 96.86811096034944;
                                attribute 'σ_Cy' : Real = 28.23690002309109;
                                attribute Cz : Real = -73.75914030708373;
                                attribute 'σ_Cz' : Real = 29.057750463592832;
                                attribute Ixx : Real = 0.45994550420763664;
                                attribute 'σ_Ixx' : Real = 0.37074144170588635;
                                attribute Iyy : Real = 0.44076294215537776;
                                attribute 'σ_Iyy' : Real = 0.3723953238821935;
                                attribute Izz : Real = 0.4131652531219322;
                                attribute 'σ_Izz' : Real = 0.37017423652493897;
                                attribute Ixy : Real = 5.199851554080533e-4;
                                attribute 'σ_Ixy' : Real = 0.02351283871158888;
                                attribute Ixz : Real = 0.02852347871642939;
                                attribute 'σ_Ixz' : Real = 0.022566176940390956;
                                attribute Iyz : Real = 0.002980288698795897;
                                attribute 'σ_Iyz' : Real = 0.02209918015384651;
                            }
                            part <'C.1.1.3.4.4.2.2'> 'Part 440' {
                                attribute POIconv : String = "+";
                                attribute Ipoint : Boolean = false;
                                attribute mass : Real = 0.5156767961001024;
                                attribute 'σ_mass' : Real = 0.28909372274994966;
                                attribute Cx : Real = -40.47277043573558;
                                attribute 'σ_Cx' : Real = 28.721044428837228;
                                attribute Cy : Real = 89.64092768728733;
                                attribute 'σ_Cy' : Real = 28.23690002309109;
                                attribute Cz : Real = -10.617992747575045;
                                attribute 'σ_Cz' : Real = 29.057750463592832;
                                attribute Ixx : Real = 0.7028248822518219;
                                attribute 'σ_Ixx' : Real = 0.37074144170588635;
                                attribute Iyy : Real = 0.7517963562676144;
                                attribute 'σ_Iyy' : Real = 0.3723953238821935;
                                attribute Izz : Real = 0.6639416659528959;
                                attribute 'σ_Izz' : Real = 0.37017423652493897;
                                attribute Ixy : Real = 0.01839627751161948;
                                attribute 'σ_Ixy' : Real = 0.02351283871158888;
                                attribute Ixz : Real = 0.0070630304703299274;
                                attribute 'σ_Ixz' : Real = 0.022566176940390956;
                                attribute Iyz : Real = -0.046866808845210245;
                                attribute 'σ_Iyz' : Real = 0.02209918015384651;
                            }
                            part <'C.1.1.3.4.4.2.3'> 'Part 441' {
                                attribute POIconv : String = "-";
                                attribute Ipoint : Boolean = false;
                                attribute mass : Real = 0.5690418751575053;
                                attribute 'σ_mass' : Real = 0.28909372274994966;
                                attribute Cx : Real = -52.35967915505171;
                                attribute 'σ_Cx' : Real = 28.721044428837228;
                                attribute Cy : Real = -54.447084898129106;
                                attribute 'σ_Cy' : Real = 28.23690002309109;
                                attribute Cz : Real = 67.87704508751631;
                                attribute 'σ_Cz' : Real = 29.057750463592832;
                                attribute Ixx : Real = 0.7701473592136892;
                                attribute 'σ_Ixx' : Real = 0.37074144170588635;
                                attribute Iyy : Real = 0.8540617134153161;
                                attribute 'σ_Iyy' : Real = 0.3723953238821935;
                                attribute Izz : Real = 0.8592896575430501;
                                attribute 'σ_Izz' : Real = 0.37017423652493897;
                                attribute Ixy : Real = -0.001201587182770149;
                                attribute 'σ_Ixy' : Real = 0.02351283871158888;
                                attribute Ixz : Real = 0.006131234676026237;
                                attribute 'σ_Ixz' : Real = 0.022566176940390956;
                                attribute Iyz : Real = 0.0017456708924400858;
                                attribute 'σ_Iyz' : Real = 0.02209918015384651;
                            }
                            part <'C.1.1.3.4.4.2.4'> 'Part 442' {
                                attribute POIconv : String = "+";
                                attribute Ipoint : Boolean = false;
                                attribute mass : Real = 0.1152762261540629;
                                attribute 'σ_mass' : Real = 0.28909372274994966;
                                attribute Cx : Real = 16.47229455411434;
                                attribute 'σ_Cx' : Real = 28.721044428837228;
                                attribute Cy : Real = -3.7976374849677086;
                                attribute 'σ_Cy' : Real = 28.23690002309109;
                                attribute Cz : Real = 22.08794029429555;
                                attribute 'σ_Cz' : Real = 29.057750463592832;
                                attribute Ixx : Real = 0.11423274068471265;
                                attribute 'σ_Ixx' : Real = 0.37074144170588635;
                                attribute Iyy : Real = 0.13817641051214025;
                                attribute 'σ_Iyy' : Real = 0.3723953238821935;
                                attribute Izz : Real = 0.1327594593317718;
                                attribute 'σ_Izz' : Real = 0.37017423652493897;
                                attribute Ixy : Real = -1.1505759661113631e-4;
                                attribute 'σ_Ixy' : Real = 0.02351283871158888;
                                attribute Ixz : Real = 0.013558168601432892;
                                attribute 'σ_Ixz' : Real = 0.022566176940390956;
                                attribute Iyz : Real = 0.0020041304356723266;
                                attribute 'σ_Iyz' : Real = 0.02209918015384651;
                            }
                            part <'C.1.1.3.4.4.2.5'> 'Part 443' {
                                attribute POIconv : String = "+";
                                attribute Ipoint : Boolean = false;
                                attribute mass : Real = 0.2899878854730632;
                                attribute 'σ_mass' : Real = 0.28909372274994966;
                                attribute Cx : Real = -45.86069555953145;
                                attribute 'σ_Cx' : Real = 28.721044428837228;
                                attribute Cy : Real = 34.7590456251055;
                                attribute 'σ_Cy' : Real = 28.23690002309109;
                                attribute Cz : Real = 3.96183580160141;
                                attribute 'σ_Cz' : Real = 29.057750463592832;
                                attribute Ixx : Real = 0.34044218780609325;
                                attribute 'σ_Ixx' : Real = 0.37074144170588635;
                                attribute Iyy : Real = 0.34216827779801307;
                                attribute 'σ_Iyy' : Real = 0.3723953238821935;
                                attribute Izz : Real = 0.35013035150955424;
                                attribute 'σ_Izz' : Real = 0.37017423652493897;
                                attribute Ixy : Real = 0.005067793697219284;
                                attribute 'σ_Ixy' : Real = 0.02351283871158888;
                                attribute Ixz : Real = -0.018874089907912697;
                                attribute 'σ_Ixz' : Real = 0.022566176940390956;
                                attribute Iyz : Real = -6.734550510073482e-4;
                                attribute 'σ_Iyz' : Real = 0.02209918015384651;
                            }
                        }
                    }
                    part <'C.1.1.3.4.5'> 'Assembly 36' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.4.5.1'> 'Subassembly 131' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.5.1.1'> 'Part 444' {
                                attribute POIconv : String = "+";
                                attribute Ipoint : Boolean = false;
                                attribute mass : Real = 0.31187800780683755;
                                attribute 'σ_mass' : Real = 0.28909372274994966;
                                attribute Cx : Real = 78.36190196685493;
                                attribute 'σ_Cx' : Real = 28.721044428837228;
                                attribute Cy : Real = 2.548074722290039;
                                attribute 'σ_Cy' : Real = 28.23690002309109;
                                attribute Cz : Real = -71.03986721485853;
                                attribute 'σ_Cz' : Real = 29.057750463592832;
                                attribute Ixx : Real = 0.358766294052545;
                                attribute 'σ_Ixx' : Real = 0.37074144170588635;
                                attribute Iyy : Real = 0.45850768320580665;
                                attribute 'σ_Iyy' : Real = 0.3723953238821935;
                                attribute Izz : Real = 0.40571701567283897;
                                attribute 'σ_Izz' : Real = 0.37017423652493897;
                                attribute Ixy : Real = -0.002981333229521103;
                                attribute 'σ_Ixy' : Real = 0.02351283871158888;
                                attribute Ixz : Real = 0.018479235800641595;
                                attribute 'σ_Ixz' : Real = 0.022566176940390956;
                                attribute Iyz : Real = 0.009529533846192696;
                                attribute 'σ_Iyz' : Real = 0.02209918015384651;
                            }
                            part <'C.1.1.3.4.5.1.2'> 'Part 445' {
                                attribute POIconv : String = "-";
                                attribute Ipoint : Boolean = false;
                                attribute mass : Real = 0.5814956205163617;
                                attribute 'σ_mass' : Real = 0.28909372274994966;
                                attribute Cx : Real = -36.133529618382454;
                                attribute 'σ_Cx' : Real = 28.721044428837228;
                                attribute Cy : Real = 29.13050758652389;
                                attribute 'σ_Cy' : Real = 28.23690002309109;
                                attribute Cz : Real = -6.6150621976703405;
                                attribute 'σ_Cz' : Real = 29.057750463592832;
                                attribute Ixx : Real = 0.8092511598099693;
                                attribute 'σ_Ixx' : Real = 0.37074144170588635;
                                attribute Iyy : Real = 0.7007570977343255;
                                attribute 'σ_Iyy' : Real = 0.3723953238821935;
                                attribute Izz : Real = 0.7050345016199404;
                                attribute 'σ_Izz' : Real = 0.37017423652493897;
                                attribute Ixy : Real = -0.016192925273277113;
                                attribute 'σ_Ixy' : Real = 0.02351283871158888;
                                attribute Ixz : Real = 0.04886802956799248;
                                attribute 'σ_Ixz' : Real = 0.022566176940390956;
                                attribute Iyz : Real = -0.01641922366939069;
                                attribute 'σ_Iyz' : Real = 0.02209918015384651;
                            }
                        }
                        part <'C.1.1.3.4.5.2'> 'Subassembly 132' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.5.2.1'> 'Part 446' {
                                attribute POIconv : String = "-";
                                attribute Ipoint : Boolean = false;
                                attribute mass : Real = 0.5228137397051323;
                                attribute 'σ_mass' : Real = 0.28909372274994966;
                                attribute Cx : Real = -60.0142742972821;
                                attribute 'σ_Cx' : Real = 28.721044428837228;
                                attribute Cy : Real = -16.18464714847505;
                                attribute 'σ_Cy' : Real = 28.23690002309109;
                                attribute Cz : Real = 9.75523549132049;
                                attribute 'σ_Cz' : Real = 29.057750463592832;
                                attribute Ixx : Real = 0.6790532206009162;
                                attribute 'σ_Ixx' : Real = 0.37074144170588635;
                                attribute Iyy : Real = 0.607793780746232;
                                attribute 'σ_Iyy' : Real = 0.3723953238821935;
                                attribute Izz : Real = 0.676490130055023;
                                attribute 'σ_Izz' : Real = 0.37017423652493897;
                                attribute Ixy : Real = -0.023595526019412574;
                                attribute 'σ_Ixy' : Real = 0.02351283871158888;
                                attribute Ixz : Real = 0.0196178674439043;
                                attribute 'σ_Ixz' : Real = 0.022566176940390956;
                                attribute Iyz : Real = 0.030465135507161373;
                                attribute 'σ_Iyz' : Real = 0.02209918015384651;
                            }
                            part <'C.1.1.3.4.5.2.2'> 'Part 447' {
                                attribute POIconv : String = "+";
                                attribute Ipoint : Boolean = false;
                                attribute mass : Real = 0.22894971508253364;
                                attribute 'σ_mass' : Real = 0.28909372274994966;
                                attribute Cx : Real = 5.651916330680251;
                                attribute 'σ_Cx' : Real = 28.721044428837228;
                                attribute Cy : Real = 83.51241177879274;
                                attribute 'σ_Cy' : Real = 28.23690002309109;
                                attribute Cz : Real = 71.98789604008198;
                                attribute 'σ_Cz' : Real = 29.057750463592832;
                                attribute Ixx : Real = 0.29055284631210637;
                                attribute 'σ_Ixx' : Real = 0.37074144170588635;
                                attribute Iyy : Real = 0.27634499498260595;
                                attribute 'σ_Iyy' : Real = 0.3723953238821935;
                                attribute Izz : Real = 0.294995404497698;
                                attribute 'σ_Izz' : Real = 0.37017423652493897;
                                attribute Ixy : Real = 0.01634544882887808;
                                attribute 'σ_Ixy' : Real = 0.02351283871158888;
                                attribute Ixz : Real = 0.007249188140548639;
                                attribute 'σ_Ixz' : Real = 0.022566176940390956;
                                attribute Iyz : Real = 0.014629235826602624;
                                attribute 'σ_Iyz' : Real = 0.02209918015384651;
                            }
                            part <'C.1.1.3.4.5.2.3'> 'Part 448' {
                                attribute POIconv : String = "+";
                                attribute Ipoint : Boolean = false;
                                attribute mass : Real = 0.6893118706266396;
                                attribute 'σ_mass' : Real = 0.28909372274994966;
                                attribute Cx : Real = -1.1883747298270464;
                                attribute 'σ_Cx' : Real = 28.721044428837228;
                                attribute Cy : Real = 24.5611316524446;
                                attribute 'σ_Cy' : Real = 28.23690002309109;
                                attribute Cz : Real = 12.492801202461123;
                                attribute 'σ_Cz' : Real = 29.057750463592832;
                                attribute Ixx : Real = 0.831046085691071;
                                attribute 'σ_Ixx' : Real = 0.37074144170588635;
                                attribute Iyy : Real = 0.8274859558897861;
                                attribute 'σ_Iyy' : Real = 0.3723953238821935;
                                attribute Izz : Real = 1.0029565028532625;
                                attribute 'σ_Izz' : Real = 0.37017423652493897;
                                attribute Ixy : Real = 0.009048756782681747;
                                attribute 'σ_Ixy' : Real = 0.02351283871158888;
                                attribute Ixz : Real = 0.053072462305126036;
                                attribute 'σ_Ixz' : Real = 0.022566176940390956;
                                attribute Iyz : Real = -0.006702095873235189;
                                attribute 'σ_Iyz' : Real = 0.02209918015384651;
                            }
                            part <'C.1.1.3.4.5.2.4'> 'Part 449' {
                                attribute POIconv : String = "+";
                                attribute Ipoint : Boolean = false;
                                attribute mass : Real = 0.9115084869794082;
                                attribute 'σ_mass' : Real = 0.28909372274994966;
                                attribute Cx : Real = 85.71678870357573;
                                attribute 'σ_Cx' : Real = 28.721044428837228;
                                attribute Cy : Real = -94.70810191705823;
                                attribute 'σ_Cy' : Real = 28.23690002309109;
                                attribute Cz : Real = 64.41936157643795;
                                attribute 'σ_Cz' : Real = 29.057750463592832;
                                attribute Ixx : Real = 1.2669812039375097;
                                attribute 'σ_Ixx' : Real = 0.37074144170588635;
                                attribute Iyy : Real = 1.3069677950158685;
                                attribute 'σ_Iyy' : Real = 0.3723953238821935;
                                attribute Izz : Real = 1.148769429126702;
                                attribute 'σ_Izz' : Real = 0.37017423652493897;
                                attribute Ixy : Real = 0.004238102117325041;
                                attribute 'σ_Ixy' : Real = 0.02351283871158888;
                                attribute Ixz : Real = 0.08339448320902551;
                                attribute 'σ_Ixz' : Real = 0.022566176940390956;
                                attribute Iyz : Real = 0.014340104925734794;
                                attribute 'σ_Iyz' : Real = 0.02209918015384651;
                            }
                            part <'C.1.1.3.4.5.2.5'> 'Part 450' {
                                attribute POIconv : String = "-";
                                attribute Ipoint : Boolean = false;
                                attribute mass : Real = 0.10621902362117544;
                                attribute 'σ_mass' : Real = 0.28909372274994966;
                                attribute Cx : Real = 67.53291697241366;
                                attribute 'σ_Cx' : Real = 28.721044428837228;
                                attribute Cy : Real = -80.77259813435376;
                                attribute 'σ_Cy' : Real = 28.23690002309109;
                                attribute Cz : Real = -33.73766173608601;
                                attribute 'σ_Cz' : Real = 29.057750463592832;
                                attribute Ixx : Real = 0.16656362489037033;
                                attribute 'σ_Ixx' : Real = 0.37074144170588635;
                                attribute Iyy : Real = 0.16463505561182337;
                                attribute 'σ_Iyy' : Real = 0.3723953238821935;
                                attribute Izz : Real = 0.17058897977468665;
                                attribute 'σ_Izz' : Real = 0.37017423652493897;
                                attribute Ixy : Real = 9.354398285409536e-4;
                                attribute 'σ_Ixy' : Real = 0.02351283871158888;
                                attribute Ixz : Real = -6.876906624152896e-5;
                                attribute 'σ_Ixz' : Real = 0.022566176940390956;
                                attribute Iyz : Real = -8.291113670801317e-4;
                                attribute 'σ_Iyz' : Real = 0.02209918015384651;
                            }
                        }
                        part <'C.1.1.3.4.5.3'> 'Subassembly 133' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.5.3.1'> 'Part 451' {
                                attribute POIconv : String = "-";
                                attribute Ipoint : Boolean = false;
                                attribute mass : Real = 0.24806270349677653;
                                attribute 'σ_mass' : Real = 0.28909372274994966;
                                attribute Cx : Real = 38.488904014229774;
                                attribute 'σ_Cx' : Real = 28.721044428837228;
                                attribute Cy : Real = 1.7818327993154526;
                                attribute 'σ_Cy' : Real = 28.23690002309109;
                                attribute Cz : Real = -5.157064041122794;
                                attribute 'σ_Cz' : Real = 29.057750463592832;
                                attribute Ixx : Real = 0.3199103766104747;
                                attribute 'σ_Ixx' : Real = 0.37074144170588635;
                                attribute Iyy : Real = 0.3451475932042683;
                                attribute 'σ_Iyy' : Real = 0.3723953238821935;
                                attribute Izz : Real = 0.3430850202777122;
                                attribute 'σ_Izz' : Real = 0.37017423652493897;
                                attribute Ixy : Real = 0.008357385415948465;
                                attribute 'σ_Ixy' : Real = 0.02351283871158888;
                                attribute Ixz : Real = 0.021948817821131273;
                                attribute 'σ_Ixz' : Real = 0.022566176940390956;
                                attribute Iyz : Real = 0.009556949759083316;
                                attribute 'σ_Iyz' : Real = 0.02209918015384651;
                            }
                            part <'C.1.1.3.4.5.3.2'> 'Part 452' {
                                attribute POIconv : String = "+";
                                attribute Ipoint : Boolean = false;
                                attribute mass : Real = 0.6117523147936444;
                                attribute 'σ_mass' : Real = 0.28909372274994966;
                                attribute Cx : Real = 65.18396865576506;
                                attribute 'σ_Cx' : Real = 28.721044428837228;
                                attribute Cy : Real = -89.62902100756764;
                                attribute 'σ_Cy' : Real = 28.23690002309109;
                                attribute Cz : Real = -73.56894188560545;
                                attribute 'σ_Cz' : Real = 29.057750463592832;
                                attribute Ixx : Real = 0.7836475243013408;
                                attribute 'σ_Ixx' : Real = 0.37074144170588635;
                                attribute Iyy : Real = 0.7817376337627282;
                                attribute 'σ_Iyy' : Real = 0.3723953238821935;
                                attribute Izz : Real = 0.936314847512146;
                                attribute 'σ_Izz' : Real = 0.37017423652493897;
                                attribute Ixy : Real = -0.002231534834657638;
                                attribute 'σ_Ixy' : Real = 0.02351283871158888;
                                attribute Ixz : Real = -0.010654113709594425;
                                attribute 'σ_Ixz' : Real = 0.022566176940390956;
                                attribute Iyz : Real = -0.018593174876273544;
                                attribute 'σ_Iyz' : Real = 0.02209918015384651;
                            }
                            part <'C.1.1.3.4.5.3.3'> 'Part 453' {
                                attribute POIconv : String = "-";
                                attribute Ipoint : Boolean = false;
                                attribute mass : Real = 0.9453501234266442;
                                attribute 'σ_mass' : Real = 0.28909372274994966;
                                attribute Cx : Real = 9.240136854350567;
                                attribute 'σ_Cx' : Real = 28.721044428837228;
                                attribute Cy : Real = 84.18410453014076;
                                attribute 'σ_Cy' : Real = 28.23690002309109;
                                attribute Cz : Real = 71.61254864186049;
                                attribute 'σ_Cz' : Real = 29.057750463592832;
                                attribute Ixx : Real = 1.0073219362129149;
                                attribute 'σ_Ixx' : Real = 0.37074144170588635;
                                attribute Iyy : Real = 1.012171959304027;
                                attribute 'σ_Iyy' : Real = 0.3723953238821935;
                                attribute Izz : Real = 1.1000265940111011;
                                attribute 'σ_Izz' : Real = 0.37017423652493897;
                                attribute Ixy : Real = 0.08542130311730473;
                                attribute 'σ_Ixy' : Real = 0.02351283871158888;
                                attribute Ixz : Real = 0.012987189307802322;
                                attribute 'σ_Ixz' : Real = 0.022566176940390956;
                                attribute Iyz : Real = 0.004717362666225057;
                                attribute 'σ_Iyz' : Real = 0.02209918015384651;
                            }
                            part <'C.1.1.3.4.5.3.4'> 'Part 454' {
                                attribute POIconv : String = "+";
                                attribute Ipoint : Boolean = false;
                                attribute mass : Real = 0.26768360412539915;
                                attribute 'σ_mass' : Real = 0.28909372274994966;
                                attribute Cx : Real = -36.51109477505088;
                                attribute 'σ_Cx' : Real = 28.721044428837228;
                                attribute Cy : Real = 40.45621561817825;
                                attribute 'σ_Cy' : Real = 28.23690002309109;
                                attribute Cz : Real = 8.196037355810404;
                                attribute 'σ_Cz' : Real = 29.057750463592832;
                                attribute Ixx : Real = 0.32781616604180586;
                                attribute 'σ_Ixx' : Real = 0.37074144170588635;
                                attribute Iyy : Real = 0.3053052767812128;
                                attribute 'σ_Iyy' : Real = 0.3723953238821935;
                                attribute Izz : Real = 0.33856274027143235;
                                attribute 'σ_Izz' : Real = 0.37017423652493897;
                                attribute Ixy : Real = -0.007622666768213576;
                                attribute 'σ_Ixy' : Real = 0.02351283871158888;
                                attribute Ixz : Real = -0.0045914575573862745;
                                attribute 'σ_Ixz' : Real = 0.022566176940390956;
                                attribute Iyz : Real = 0.007794474606989081;
                                attribute 'σ_Iyz' : Real = 0.02209918015384651;
                            }
                        }
                        part <'C.1.1.3.4.5.4'> 'Subassembly 134' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.4.5.4.1'> 'Part 455' {
                                attribute POIconv : String = "+";
                                attribute Ipoint : Boolean = false;
                                attribute mass : Real = 0.06650748666119762;
                                attribute 'σ_mass' : Real = 0.28909372274994966;
                                attribute Cx : Real = -61.92862228490412;
                                attribute 'σ_Cx' : Real = 28.721044428837228;
                                attribute Cy : Real = 78.5804741550237;
                                attribute 'σ_Cy' : Real = 28.23690002309109;
                                attribute Cz : Real = -86.9897248223424;
                                attribute 'σ_Cz' : Real = 29.057750463592832;
                                attribute Ixx : Real = 0.06838749864555303;
                                attribute 'σ_Ixx' : Real = 0.37074144170588635;
                                attribute Iyy : Real = 0.06293185525826493;
                                attribute 'σ_Iyy' : Real = 0.3723953238821935;
                                attribute Izz : Real = 0.06802642825942584;
                                attribute 'σ_Izz' : Real = 0.37017423652493897;
                                attribute Ixy : Real = 0.002605432892014207;
                                attribute 'σ_Ixy' : Real = 0.02351283871158888;
                                attribute Ixz : Real = 0.001118479906078592;
                                attribute 'σ_Ixz' : Real = 0.022566176940390956;
                                attribute Iyz : Real = 0.0012674500604080187;
                                attribute 'σ_Iyz' : Real = 0.02209918015384651;
                            }
                            part <'C.1.1.3.4.5.4.2'> 'Part 456' {
                                attribute POIconv : String = "+";
                                attribute Ipoint : Boolean = false;
                                attribute mass : Real = 0.4733419907672796;
                                attribute 'σ_mass' : Real = 0.28909372274994966;
                                attribute Cx : Real = 30.664983857423067;
                                attribute 'σ_Cx' : Real = 28.721044428837228;
                                attribute Cy : Real = 57.449891325086355;
                                attribute 'σ_Cy' : Real = 28.23690002309109;
                                attribute Cz : Real = 40.5304794665426;
                                attribute 'σ_Cz' : Real = 29.057750463592832;
                                attribute Ixx : Real = 0.556845090183731;
                                attribute 'σ_Ixx' : Real = 0.37074144170588635;
                                attribute Iyy : Real = 0.5164760257118595;
                                attribute 'σ_Iyy' : Real = 0.3723953238821935;
                                attribute Izz : Real = 0.6222203837491571;
                                attribute 'σ_Izz' : Real = 0.37017423652493897;
                                attribute Ixy : Real = -0.054850706093484684;
                                attribute 'σ_Ixy' : Real = 0.02351283871158888;
                                attribute Ixz : Real = 0.0328379128277422;
                                attribute 'σ_Ixz' : Real = 0.022566176940390956;
                                attribute Iyz : Real = -0.03399197839457565;
                                attribute 'σ_Iyz' : Real = 0.02209918015384651;
                            }
                            part <'C.1.1.3.4.5.4.3'> 'Part 457' {
                                attribute POIconv : String = "+";
                                attribute Ipoint : Boolean = false;
                                attribute mass : Real = 0.24055804438097403;
                                attribute 'σ_mass' : Real = 0.28909372274994966;
                                attribute Cx : Real = 77.79106409288943;
                                attribute 'σ_Cx' : Real = 28.721044428837228;
                                attribute Cy : Real = 43.82191188633442;
                                attribute 'σ_Cy' : Real = 28.23690002309109;
                                attribute Cz : Real = -59.58506497554481;
                                attribute 'σ_Cz' : Real = 29.057750463592832;
                                attribute Ixx : Real = 0.3306170994872622;
                                attribute 'σ_Ixx' : Real = 0.37074144170588635;
                                attribute Iyy : Real = 0.30516438737166784;
                                attribute 'σ_Iyy' : Real = 0.3723953238821935;
                                attribute Izz : Real = 0.32654242627407176;
                                attribute 'σ_Izz' : Real = 0.37017423652493897;
                                attribute Ixy : Real = -0.015590895501857945;
                                attribute 'σ_Ixy' : Real = 0.02351283871158888;
                                attribute Ixz : Real = 0.00918350599806595;
                                attribute 'σ_Ixz' : Real = 0.022566176940390956;
                                attribute Iyz : Real = -0.01889154217104471;
                                attribute 'σ_Iyz' : Real = 0.02209918015384651;
                            }
                        }
                    }
                }
                part <'C.1.1.3.5'> 'Subsystem 10' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.3.5.1'> 'Assembly 37' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.5.1.1'> 'Subassembly 135' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.5.1.1.1'> 'Part 458' {
                                attribute POIconv : String = "+";
                                attribute Ipoint : Boolean = false;
                                attribute mass : Real = 0.852228607890429;
                                attribute 'σ_mass' : Real = 0.28909372274994966;
                                attribute Cx : Real = 11.89677082002163;
                                attribute 'σ_Cx' : Real = 28.721044428837228;
                                attribute Cy : Real = 78.33172748796642;
                                attribute 'σ_Cy' : Real = 28.23690002309109;
                                attribute Cz : Real = 78.24640246108174;
                                attribute 'σ_Cz' : Real = 29.057750463592832;
                                attribute Ixx : Real = 1.0191807238627326;
                                attribute 'σ_Ixx' : Real = 0.37074144170588635;
                                attribute Iyy : Real = 0.9027187720533281;
                                attribute 'σ_Iyy' : Real = 0.3723953238821935;
                                attribute Izz : Real = 1.0860216896509165;
                                attribute 'σ_Izz' : Real = 0.37017423652493897;
                                attribute Ixy : Real = 0.0816520581507543;
                                attribute 'σ_Ixy' : Real = 0.02351283871158888;
                                attribute Ixz : Real = 0.013254648772264083;
                                attribute 'σ_Ixz' : Real = 0.022566176940390956;
                                attribute Iyz : Real = 0.01379489756306939;
                                attribute 'σ_Iyz' : Real = 0.02209918015384651;
                            }
                            part <'C.1.1.3.5.1.1.2'> 'Part 459' {
                                attribute POIconv : String = "+";
                                attribute Ipoint : Boolean = false;
                                attribute mass : Real = 0.9781517378294374;
                                attribute 'σ_mass' : Real = 0.28909372274994966;
                                attribute Cx : Real = -85.21695537492633;
                                attribute 'σ_Cx' : Real = 28.721044428837228;
                                attribute Cy : Real = -35.638842917978764;
                                attribute 'σ_Cy' : Real = 28.23690002309109;
                                attribute Cz : Real = 96.02976464666426;
                                attribute 'σ_Cz' : Real = 29.057750463592832;
                                attribute Ixx : Real = 1.1894279637885954;
                                attribute 'σ_Ixx' : Real = 0.37074144170588635;
                                attribute Iyy : Real = 1.133324540379323;
                                attribute 'σ_Iyy' : Real = 0.3723953238821935;
                                attribute Izz : Real = 1.2133297388067426;
                                attribute 'σ_Izz' : Real = 0.37017423652493897;
                                attribute Ixy : Real = 0.023528587805677785;
                                attribute 'σ_Ixy' : Real = 0.02351283871158888;
                                attribute Ixz : Real = -0.0757935796150287;
                                attribute 'σ_Ixz' : Real = 0.022566176940390956;
                                attribute Iyz : Real = 0.020193049044117204;
                                attribute 'σ_Iyz' : Real = 0.02209918015384651;
                            }
                            part <'C.1.1.3.5.1.1.3'> 'Part 460' {
                                attribute POIconv : String = "+";
                                attribute Ipoint : Boolean = false;
                                attribute mass : Real = 0.7059542618249544;
                                attribute 'σ_mass' : Real = 0.28909372274994966;
                                attribute Cx : Real = -95.21634955890477;
                                attribute 'σ_Cx' : Real = 28.721044428837228;
                                attribute Cy : Real = 19.21276869252324;
                                attribute 'σ_Cy' : Real = 28.23690002309109;
                                attribute Cz : Real = 86.51930494233966;
                                attribute 'σ_Cz' : Real = 29.057750463592832;
                                attribute Ixx : Real = 0.7967217870028317;
                                attribute 'σ_Ixx' : Real = 0.37074144170588635;
                                attribute Iyy : Real = 0.7171490701438248;
                                attribute 'σ_Iyy' : Real = 0.3723953238821935;
                                attribute Izz : Real = 0.7711234643088769;
                                attribute 'σ_Izz' : Real = 0.37017423652493897;
                                attribute Ixy : Real = 0.016859116287476;
                                attribute 'σ_Ixy' : Real = 0.02351283871158888;
                                attribute Ixz : Real = 0.00723925450695739;
                                attribute 'σ_Ixz' : Real = 0.022566176940390956;
                                attribute Iyz : Real = -0.017748259546424717;
                                attribute 'σ_Iyz' : Real = 0.02209918015384651;
                            }
                            part <'C.1.1.3.5.1.1.4'> 'Part 461' {
                                attribute POIconv : String = "-";
                                attribute Ipoint : Boolean = false;
                                attribute mass : Real = 0.1611299698406365;
                                attribute 'σ_mass' : Real = 0.28909372274994966;
                                attribute Cx : Real = -44.13274098187685;
                                attribute 'σ_Cx' : Real = 28.721044428837228;
                                attribute Cy : Real = 29.771981993690133;
                                attribute 'σ_Cy' : Real = 28.23690002309109;
                                attribute Cz : Real = 22.40537218749523;
                                attribute 'σ_Cz' : Real = 29.057750463592832;
                                attribute Ixx : Real = 0.16725321386047218;
                                attribute 'σ_Ixx' : Real = 0.37074144170588635;
                                attribute Iyy : Real = 0.1686967579328828;
                                attribute 'σ_Iyy' : Real = 0.3723953238821935;
                                attribute Izz : Real = 0.17814873261443437;
                                attribute 'σ_Izz' : Real = 0.37017423652493897;
                                attribute Ixy : Real = -0.010627065479733437;
                                attribute 'σ_Ixy' : Real = 0.02351283871158888;
                                attribute Ixz : Real = -0.008583138368446852;
                                attribute 'σ_Ixz' : Real = 0.022566176940390956;
                                attribute Iyz : Real = -0.0069019785610489335;
                                attribute 'σ_Iyz' : Real = 0.02209918015384651;
                            }
                            part <'C.1.1.3.5.1.1.5'> 'Part 462' {
                                attribute POIconv : String = "+";
                                attribute Ipoint : Boolean = false;
                                attribute mass : Real = 0.5686922087718267;
                                attribute 'σ_mass' : Real = 0.28909372274994966;
                                attribute Cx : Real = 92.41948639973998;
                                attribute 'σ_Cx' : Real = 28.721044428837228;
                                attribute Cy : Real = -13.74738677404821;
                                attribute 'σ_Cy' : Real = 28.23690002309109;
                                attribute Cz : Real = -23.76479711383581;
                                attribute 'σ_Cz' : Real = 29.057750463592832;
                                attribute Ixx : Real = 0.7716076793871112;
                                attribute 'σ_Ixx' : Real = 0.37074144170588635;
                                attribute Iyy : Real = 0.7763645387377982;
                                attribute 'σ_Iyy' : Real = 0.3723953238821935;
                                attribute Izz : Real = 0.8898418486430881;
                                attribute 'σ_Izz' : Real = 0.37017423652493897;
                                attribute Ixy : Real = 8.876595156627811e-4;
                                attribute 'σ_Ixy' : Real = 0.02351283871158888;
                                attribute Ixz : Real = -7.235803758987441e-4;
                                attribute 'σ_Ixz' : Real = 0.022566176940390956;
                                attribute Iyz : Real = 2.0708640397413224e-4;
                                attribute 'σ_Iyz' : Real = 0.02209918015384651;
                            }
                        }
                        part <'C.1.1.3.5.1.2'> 'Subassembly 136' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.5.1.2.1'> 'Part 463' {
                                attribute POIconv : String = "+";
                                attribute Ipoint : Boolean = false;
                                attribute mass : Real = 0.24279296651482582;
                                attribute 'σ_mass' : Real = 0.28909372274994966;
                                attribute Cx : Real = -33.822951605543494;
                                attribute 'σ_Cx' : Real = 28.721044428837228;
                                attribute Cy : Real = 65.04495250992477;
                                attribute 'σ_Cy' : Real = 28.23690002309109;
                                attribute Cz : Real = 72.46500812470913;
                                attribute 'σ_Cz' : Real = 29.057750463592832;
                                attribute Ixx : Real = 0.31572226114769975;
                                attribute 'σ_Ixx' : Real = 0.37074144170588635;
                                attribute Iyy : Real = 0.29345039114185656;
                                attribute 'σ_Iyy' : Real = 0.3723953238821935;
                                attribute Izz : Real = 0.311584443280575;
                                attribute 'σ_Izz' : Real = 0.37017423652493897;
                                attribute Ixy : Real = 0.02740623490253343;
                                attribute 'σ_Ixy' : Real = 0.02351283871158888;
                                attribute Ixz : Real = 0.01565162285770408;
                                attribute 'σ_Ixz' : Real = 0.022566176940390956;
                                attribute Iyz : Real = 0.02542376696352857;
                                attribute 'σ_Iyz' : Real = 0.02209918015384651;
                            }
                            part <'C.1.1.3.5.1.2.2'> 'Part 464' {
                                attribute POIconv : String = "-";
                                attribute Ipoint : Boolean = false;
                                attribute mass : Real = 0.6697904606887605;
                                attribute 'σ_mass' : Real = 0.28909372274994966;
                                attribute Cx : Real = -66.57535820268095;
                                attribute 'σ_Cx' : Real = 28.721044428837228;
                                attribute Cy : Real = -64.48161150328815;
                                attribute 'σ_Cy' : Real = 28.23690002309109;
                                attribute Cz : Real = -45.590148493647575;
                                attribute 'σ_Cz' : Real = 29.057750463592832;
                                attribute Ixx : Real = 0.9672626224717293;
                                attribute 'σ_Ixx' : Real = 0.37074144170588635;
                                attribute Iyy : Real = 0.9701426491373292;
                                attribute 'σ_Iyy' : Real = 0.3723953238821935;
                                attribute Izz : Real = 0.893705853556378;
                                attribute 'σ_Izz' : Real = 0.37017423652493897;
                                attribute Ixy : Real = 0.0456289932356362;
                                attribute 'σ_Ixy' : Real = 0.02351283871158888;
                                attribute Ixz : Real = 0.02610961099341013;
                                attribute 'σ_Ixz' : Real = 0.022566176940390956;
                                attribute Iyz : Real = -0.01801196703694679;
                                attribute 'σ_Iyz' : Real = 0.02209918015384651;
                            }
                            part <'C.1.1.3.5.1.2.3'> 'Part 465' {
                                attribute POIconv : String = "-";
                                attribute Ipoint : Boolean = false;
                                attribute mass : Real = 0.2393716145735234;
                                attribute 'σ_mass' : Real = 0.28909372274994966;
                                attribute Cx : Real = -51.6263282392174;
                                attribute 'σ_Cx' : Real = 28.721044428837228;
                                attribute Cy : Real = -46.496111154556274;
                                attribute 'σ_Cy' : Real = 28.23690002309109;
                                attribute Cz : Real = -58.52593225426972;
                                attribute 'σ_Cz' : Real = 29.057750463592832;
                                attribute Ixx : Real = 0.2845513937057712;
                                attribute 'σ_Ixx' : Real = 0.37074144170588635;
                                attribute Iyy : Real = 0.28235374934067803;
                                attribute 'σ_Iyy' : Real = 0.3723953238821935;
                                attribute Izz : Real = 0.2431978331049264;
                                attribute 'σ_Izz' : Real = 0.37017423652493897;
                                attribute Ixy : Real = 0.017268125739333035;
                                attribute 'σ_Ixy' : Real = 0.02351283871158888;
                                attribute Ixz : Real = -8.433170627217269e-4;
                                attribute 'σ_Ixz' : Real = 0.022566176940390956;
                                attribute Iyz : Real = -8.812957676617741e-4;
                                attribute 'σ_Iyz' : Real = 0.02209918015384651;
                            }
                        }
                        part <'C.1.1.3.5.1.3'> 'Subassembly 137' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.5.1.3.1'> 'Part 466' {
                                attribute POIconv : String = "+";
                                attribute Ipoint : Boolean = false;
                                attribute mass : Real = 0.7402364585334436;
                                attribute 'σ_mass' : Real = 0.28909372274994966;
                                attribute Cx : Real = -44.25944513641298;
                                attribute 'σ_Cx' : Real = 28.721044428837228;
                                attribute Cy : Real = -48.235469264909625;
                                attribute 'σ_Cy' : Real = 28.23690002309109;
                                attribute Cz : Real = -18.56502965092659;
                                attribute 'σ_Cz' : Real = 29.057750463592832;
                                attribute Ixx : Real = 0.938604890194411;
                                attribute 'σ_Ixx' : Real = 0.37074144170588635;
                                attribute Iyy : Real = 0.961304647707503;
                                attribute 'σ_Iyy' : Real = 0.3723953238821935;
                                attribute Izz : Real = 0.6908370035330155;
                                attribute 'σ_Izz' : Real = 0.37017423652493897;
                                attribute Ixy : Real = 0.0025464797714238735;
                                attribute 'σ_Ixy' : Real = 0.02351283871158888;
                                attribute Ixz : Real = -0.02604349214569731;
                                attribute 'σ_Ixz' : Real = 0.022566176940390956;
                                attribute Iyz : Real = 0.0040440490153330465;
                                attribute 'σ_Iyz' : Real = 0.02209918015384651;
                            }
                            part <'C.1.1.3.5.1.3.2'> 'Part 467' {
                                attribute POIconv : String = "+";
                                attribute Ipoint : Boolean = false;
                                attribute mass : Real = 0.43324308657250366;
                                attribute 'σ_mass' : Real = 0.28909372274994966;
                                attribute Cx : Real = -55.33792055211961;
                                attribute 'σ_Cx' : Real = 28.721044428837228;
                                attribute Cy : Real = -58.96467235870659;
                                attribute 'σ_Cy' : Real = 28.23690002309109;
                                attribute Cz : Real = -30.408555176109076;
                                attribute 'σ_Cz' : Real = 29.057750463592832;
                                attribute Ixx : Real = 0.5624938775724406;
                                attribute 'σ_Ixx' : Real = 0.37074144170588635;
                                attribute Iyy : Real = 0.5999818993347447;
                                attribute 'σ_Iyy' : Real = 0.3723953238821935;
                                attribute Izz : Real = 0.6101723224944161;
                                attribute 'σ_Izz' : Real = 0.37017423652493897;
                                attribute Ixy : Real = 0.003481346388634529;
                                attribute 'σ_Ixy' : Real = 0.02351283871158888;
                                attribute Ixz : Real = -0.005472061181803927;
                                attribute 'σ_Ixz' : Real = 0.022566176940390956;
                                attribute Iyz : Real = 0.05298425613091419;
                                attribute 'σ_Iyz' : Real = 0.02209918015384651;
                            }
                            part <'C.1.1.3.5.1.3.3'> 'Part 468' {
                                attribute POIconv : String = "-";
                                attribute Ipoint : Boolean = false;
                                attribute mass : Real = 0.7111286660346668;
                                attribute 'σ_mass' : Real = 0.28909372274994966;
                                attribute Cx : Real = 88.6565619148314;
                                attribute 'σ_Cx' : Real = 28.721044428837228;
                                attribute Cy : Real = -60.5176470708102;
                                attribute 'σ_Cy' : Real = 28.23690002309109;
                                attribute Cz : Real = -52.8477877844125;
                                attribute 'σ_Cz' : Real = 29.057750463592832;
                                attribute Ixx : Real = 0.976328887157829;
                                attribute 'σ_Ixx' : Real = 0.37074144170588635;
                                attribute Iyy : Real = 0.9515660805855486;
                                attribute 'σ_Iyy' : Real = 0.3723953238821935;
                                attribute Izz : Real = 1.0701742767975397;
                                attribute 'σ_Izz' : Real = 0.37017423652493897;
                                attribute Ixy : Real = 0.0013663381044850594;
                                attribute 'σ_Ixy' : Real = 0.02351283871158888;
                                attribute Ixz : Real = -0.012915727076441598;
                                attribute 'σ_Ixz' : Real = 0.022566176940390956;
                                attribute Iyz : Real = -0.011604368292494206;
                                attribute 'σ_Iyz' : Real = 0.02209918015384651;
                            }
                            part <'C.1.1.3.5.1.3.4'> 'Part 469' {
                                attribute POIconv : String = "-";
                                attribute Ipoint : Boolean = false;
                                attribute mass : Real = 0.2665399281219579;
                                attribute 'σ_mass' : Real = 0.28909372274994966;
                                attribute Cx : Real = -39.35285075567663;
                                attribute 'σ_Cx' : Real = 28.721044428837228;
                                attribute Cy : Real = 79.23190207220614;
                                attribute 'σ_Cy' : Real = 28.23690002309109;
                                attribute Cz : Real = -98.87194382026792;
                                attribute 'σ_Cz' : Real = 29.057750463592832;
                                attribute Ixx : Real = 0.36533245129072295;
                                attribute 'σ_Ixx' : Real = 0.37074144170588635;
                                attribute Iyy : Real = 0.38399999003229224;
                                attribute 'σ_Iyy' : Real = 0.3723953238821935;
                                attribute Izz : Real = 0.3304229946885984;
                                attribute 'σ_Izz' : Real = 0.37017423652493897;
                                attribute Ixy : Real = -0.014928380362488308;
                                attribute 'σ_Ixy' : Real = 0.02351283871158888;
                                attribute Ixz : Real = -3.4931409991713184e-4;
                                attribute 'σ_Ixz' : Real = 0.022566176940390956;
                                attribute Iyz : Real = 6.385616678204783e-4;
                                attribute 'σ_Iyz' : Real = 0.02209918015384651;
                            }
                        }
                        part <'C.1.1.3.5.1.4'> 'Subassembly 138' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.5.1.4.1'> 'Part 470' {
                                attribute POIconv : String = "+";
                                attribute Ipoint : Boolean = false;
                                attribute mass : Real = 0.05379393326677382;
                                attribute 'σ_mass' : Real = 0.28909372274994966;
                                attribute Cx : Real = 3.362171445041895;
                                attribute 'σ_Cx' : Real = 28.721044428837228;
                                attribute Cy : Real = -19.867231836542487;
                                attribute 'σ_Cy' : Real = 28.23690002309109;
                                attribute Cz : Real = 78.27592073008418;
                                attribute 'σ_Cz' : Real = 29.057750463592832;
                                attribute Ixx : Real = 0.059512283110862194;
                                attribute 'σ_Ixx' : Real = 0.37074144170588635;
                                attribute Iyy : Real = 0.057284198431538993;
                                attribute 'σ_Iyy' : Real = 0.3723953238821935;
                                attribute Izz : Real = 0.06422225600541613;
                                attribute 'σ_Izz' : Real = 0.37017423652493897;
                                attribute Ixy : Real = 0.0021444276580470847;
                                attribute 'σ_Ixy' : Real = 0.02351283871158888;
                                attribute Ixz : Real = -0.0018989226702066705;
                                attribute 'σ_Ixz' : Real = 0.022566176940390956;
                                attribute Iyz : Real = -0.0025391449245142925;
                                attribute 'σ_Iyz' : Real = 0.02209918015384651;
                            }
                            part <'C.1.1.3.5.1.4.2'> 'Part 471' {
                                attribute POIconv : String = "-";
                                attribute Ipoint : Boolean = false;
                                attribute mass : Real = 0.2673411031479482;
                                attribute 'σ_mass' : Real = 0.28909372274994966;
                                attribute Cx : Real = 63.81350485607982;
                                attribute 'σ_Cx' : Real = 28.721044428837228;
                                attribute Cy : Real = -45.22587857209146;
                                attribute 'σ_Cy' : Real = 28.23690002309109;
                                attribute Cz : Real = 28.4212589263916;
                                attribute 'σ_Cz' : Real = 29.057750463592832;
                                attribute Ixx : Real = 0.3347281847176712;
                                attribute 'σ_Ixx' : Real = 0.37074144170588635;
                                attribute Iyy : Real = 0.31812458275417416;
                                attribute 'σ_Iyy' : Real = 0.3723953238821935;
                                attribute Izz : Real = 0.3747686086436962;
                                attribute 'σ_Izz' : Real = 0.37017423652493897;
                                attribute Ixy : Real = 0.01267528623893561;
                                attribute 'σ_Ixy' : Real = 0.02351283871158888;
                                attribute Ixz : Real = -0.024089665931105612;
                                attribute 'σ_Ixz' : Real = 0.022566176940390956;
                                attribute Iyz : Real = 0.006258429926214659;
                                attribute 'σ_Iyz' : Real = 0.02209918015384651;
                            }
                            part <'C.1.1.3.5.1.4.3'> 'Part 472' {
                                attribute POIconv : String = "+";
                                attribute Ipoint : Boolean = false;
                                attribute mass : Real = 0.4736474926432129;
                                attribute 'σ_mass' : Real = 0.28909372274994966;
                                attribute Cx : Real = -17.277435772120953;
                                attribute 'σ_Cx' : Real = 28.721044428837228;
                                attribute Cy : Real = 0.4694958683103323;
                                attribute 'σ_Cy' : Real = 28.23690002309109;
                                attribute Cz : Real = 24.28442914970219;
                                attribute 'σ_Cz' : Real = 29.057750463592832;
                                attribute Ixx : Real = 0.6336127418221724;
                                attribute 'σ_Ixx' : Real = 0.37074144170588635;
                                attribute Iyy : Real = 0.6260988087031966;
                                attribute 'σ_Iyy' : Real = 0.3723953238821935;
                                attribute Izz : Real = 0.5526634153011218;
                                attribute 'σ_Izz' : Real = 0.37017423652493897;
                                attribute Ixy : Real = 0.005648930516605661;
                                attribute 'σ_Ixy' : Real = 0.02351283871158888;
                                attribute Ixz : Real = 0.025454765069569403;
                                attribute 'σ_Ixz' : Real = 0.022566176940390956;
                                attribute Iyz : Real = 0.049651689126243986;
                                attribute 'σ_Iyz' : Real = 0.02209918015384651;
                            }
                            part <'C.1.1.3.5.1.4.4'> 'Part 473' {
                                attribute POIconv : String = "-";
                                attribute Ipoint : Boolean = false;
                                attribute mass : Real = 0.5239523157689254;
                                attribute 'σ_mass' : Real = 0.28909372274994966;
                                attribute Cx : Real = -74.857531581074;
                                attribute 'σ_Cx' : Real = 28.721044428837228;
                                attribute Cy : Real = 29.496061708778143;
                                attribute 'σ_Cy' : Real = 28.23690002309109;
                                attribute Cz : Real = 32.513055205345154;
                                attribute 'σ_Cz' : Real = 29.057750463592832;
                                attribute Ixx : Real = 0.6408368683918888;
                                attribute 'σ_Ixx' : Real = 0.37074144170588635;
                                attribute Iyy : Real = 0.6260877703208927;
                                attribute 'σ_Iyy' : Real = 0.3723953238821935;
                                attribute Izz : Real = 0.7139552121810759;
                                attribute 'σ_Izz' : Real = 0.37017423652493897;
                                attribute Ixy : Real = 0.010740171506611605;
                                attribute 'σ_Ixy' : Real = 0.02351283871158888;
                                attribute Ixz : Real = -0.0326633502036774;
                                attribute 'σ_Ixz' : Real = 0.022566176940390956;
                                attribute Iyz : Real = 0.030185392793024807;
                                attribute 'σ_Iyz' : Real = 0.02209918015384651;
                            }
                        }
                        part <'C.1.1.3.5.1.5'> 'Subassembly 139' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.5.1.5.1'> 'Part 474' {
                                attribute POIconv : String = "+";
                                attribute Ipoint : Boolean = false;
                                attribute mass : Real = 0.4162971959328279;
                                attribute 'σ_mass' : Real = 0.28909372274994966;
                                attribute Cx : Real = -67.05261403694749;
                                attribute 'σ_Cx' : Real = 28.721044428837228;
                                attribute Cy : Real = -83.46742051653564;
                                attribute 'σ_Cy' : Real = 28.23690002309109;
                                attribute Cz : Real = -78.02020902745426;
                                attribute 'σ_Cz' : Real = 29.057750463592832;
                                attribute Ixx : Real = 0.5308111760083822;
                                attribute 'σ_Ixx' : Real = 0.37074144170588635;
                                attribute Iyy : Real = 0.43273314828348447;
                                attribute 'σ_Iyy' : Real = 0.3723953238821935;
                                attribute Izz : Real = 0.5073523344840073;
                                attribute 'σ_Izz' : Real = 0.37017423652493897;
                                attribute Ixy : Real = -0.02496227537438398;
                                attribute 'σ_Ixy' : Real = 0.02351283871158888;
                                attribute Ixz : Real = -0.013729279060180961;
                                attribute 'σ_Ixz' : Real = 0.022566176940390956;
                                attribute Iyz : Real = 0.05013582958418038;
                                attribute 'σ_Iyz' : Real = 0.02209918015384651;
                            }
                            part <'C.1.1.3.5.1.5.2'> 'Part 475' {
                                attribute POIconv : String = "-";
                                attribute Ipoint : Boolean = false;
                                attribute mass : Real = 0.9462330949625466;
                                attribute 'σ_mass' : Real = 0.28909372274994966;
                                attribute Cx : Real = 1.4871512539684772;
                                attribute 'σ_Cx' : Real = 28.721044428837228;
                                attribute Cy : Real = 24.242468737065792;
                                attribute 'σ_Cy' : Real = 28.23690002309109;
                                attribute Cz : Real = 38.80391982384026;
                                attribute 'σ_Cz' : Real = 29.057750463592832;
                                attribute Ixx : Real = 1.316600994963291;
                                attribute 'σ_Ixx' : Real = 0.37074144170588635;
                                attribute Iyy : Real = 1.0914832897109266;
                                attribute 'σ_Iyy' : Real = 0.3723953238821935;
                                attribute Izz : Real = 1.2902879760838417;
                                attribute 'σ_Izz' : Real = 0.37017423652493897;
                                attribute Ixy : Real = -0.007844296853939715;
                                attribute 'σ_Ixy' : Real = 0.02351283871158888;
                                attribute Ixz : Real = 0.01978579195004356;
                                attribute 'σ_Ixz' : Real = 0.022566176940390956;
                                attribute Iyz : Real = -0.08401086901832105;
                                attribute 'σ_Iyz' : Real = 0.02209918015384651;
                            }
                        }
                    }
                    part <'C.1.1.3.5.2'> 'Assembly 38' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.5.2.1'> 'Subassembly 140' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.5.2.1.1'> 'Part 476' {
                                attribute POIconv : String = "+";
                                attribute Ipoint : Boolean = false;
                                attribute mass : Real = 0.2124007968043443;
                                attribute 'σ_mass' : Real = 0.28909372274994966;
                                attribute Cx : Real = -25.68104132078588;
                                attribute 'σ_Cx' : Real = 28.721044428837228;
                                attribute Cy : Real = 54.07387805171311;
                                attribute 'σ_Cy' : Real = 28.23690002309109;
                                attribute Cz : Real = -76.66985411196947;
                                attribute 'σ_Cz' : Real = 29.057750463592832;
                                attribute Ixx : Real = 0.2732004462099619;
                                attribute 'σ_Ixx' : Real = 0.37074144170588635;
                                attribute Iyy : Real = 0.24200968129454017;
                                attribute 'σ_Iyy' : Real = 0.3723953238821935;
                                attribute Izz : Real = 0.2720603545976912;
                                attribute 'σ_Izz' : Real = 0.37017423652493897;
                                attribute Ixy : Real = -0.011968646694734547;
                                attribute 'σ_Ixy' : Real = 0.02351283871158888;
                                attribute Ixz : Real = -0.016712456410657356;
                                attribute 'σ_Ixz' : Real = 0.022566176940390956;
                                attribute Iyz : Real = -0.002182925168597428;
                                attribute 'σ_Iyz' : Real = 0.02209918015384651;
                            }
                            part <'C.1.1.3.5.2.1.2'> 'Part 477' {
                                attribute POIconv : String = "-";
                                attribute Ipoint : Boolean = false;
                                attribute mass : Real = 0.8352115565084387;
                                attribute 'σ_mass' : Real = 0.28909372274994966;
                                attribute Cx : Real = 34.49557917192578;
                                attribute 'σ_Cx' : Real = 28.721044428837228;
                                attribute Cy : Real = -26.44871873781085;
                                attribute 'σ_Cy' : Real = 28.23690002309109;
                                attribute Cz : Real = 25.456016091629863;
                                attribute 'σ_Cz' : Real = 29.057750463592832;
                                attribute Ixx : Real = 0.7302139381672937;
                                attribute 'σ_Ixx' : Real = 0.37074144170588635;
                                attribute Iyy : Real = 0.9761035480191154;
                                attribute 'σ_Iyy' : Real = 0.3723953238821935;
                                attribute Izz : Real = 0.9920480510142249;
                                attribute 'σ_Izz' : Real = 0.37017423652493897;
                                attribute Ixy : Real = -0.05799103773509501;
                                attribute 'σ_Ixy' : Real = 0.02351283871158888;
                                attribute Ixz : Real = 0.009734387723880848;
                                attribute 'σ_Ixz' : Real = 0.022566176940390956;
                                attribute Iyz : Real = 0.009602784364827175;
                                attribute 'σ_Iyz' : Real = 0.02209918015384651;
                            }
                            part <'C.1.1.3.5.2.1.3'> 'Part 478' {
                                attribute POIconv : String = "-";
                                attribute Ipoint : Boolean = false;
                                attribute mass : Real = 0.24205635552457533;
                                attribute 'σ_mass' : Real = 0.28909372274994966;
                                attribute Cx : Real = 76.53168644756079;
                                attribute 'σ_Cx' : Real = 28.721044428837228;
                                attribute Cy : Real = 70.73780265636742;
                                attribute 'σ_Cy' : Real = 28.23690002309109;
                                attribute Cz : Real = 30.486800195649266;
                                attribute 'σ_Cz' : Real = 29.057750463592832;
                                attribute Ixx : Real = 0.32464668902420013;
                                attribute 'σ_Ixx' : Real = 0.37074144170588635;
                                attribute Iyy : Real = 0.27978398643442925;
                                attribute 'σ_Iyy' : Real = 0.3723953238821935;
                                attribute Izz : Real = 0.263055836639231;
                                attribute 'σ_Izz' : Real = 0.37017423652493897;
                                attribute Ixy : Real = 0.016614713241331548;
                                attribute 'σ_Ixy' : Real = 0.02351283871158888;
                                attribute Ixz : Real = 0.01399782298102264;
                                attribute 'σ_Ixz' : Real = 0.022566176940390956;
                                attribute Iyz : Real = -0.018957547240597266;
                                attribute 'σ_Iyz' : Real = 0.02209918015384651;
                            }
                            part <'C.1.1.3.5.2.1.4'> 'Part 479' {
                                attribute POIconv : String = "-";
                                attribute Ipoint : Boolean = false;
                                attribute mass : Real = 0.5823844344441313;
                                attribute 'σ_mass' : Real = 0.28909372274994966;
                                attribute Cx : Real = 58.873468451201916;
                                attribute 'σ_Cx' : Real = 28.721044428837228;
                                attribute Cy : Real = -71.7826466076076;
                                attribute 'σ_Cy' : Real = 28.23690002309109;
                                attribute Cz : Real = -11.469634529203176;
                                attribute 'σ_Cz' : Real = 29.057750463592832;
                                attribute Ixx : Real = 0.6441668946195129;
                                attribute 'σ_Ixx' : Real = 0.37074144170588635;
                                attribute Iyy : Real = 0.7186646275515615;
                                attribute 'σ_Iyy' : Real = 0.3723953238821935;
                                attribute Izz : Real = 0.7793213298717644;
                                attribute 'σ_Izz' : Real = 0.37017423652493897;
                                attribute Ixy : Real = 0.05129219420828757;
                                attribute 'σ_Ixy' : Real = 0.02351283871158888;
                                attribute Ixz : Real = -0.0067679140619685395;
                                attribute 'σ_Ixz' : Real = 0.022566176940390956;
                                attribute Iyz : Real = 0.020065684329194835;
                                attribute 'σ_Iyz' : Real = 0.02209918015384651;
                            }
                            part <'C.1.1.3.5.2.1.5'> 'Part 480' {
                                attribute POIconv : String = "+";
                                attribute Ipoint : Boolean = false;
                                attribute mass : Real = 0.08522757619945333;
                                attribute 'σ_mass' : Real = 0.28909372274994966;
                                attribute Cx : Real = 29.49779937043786;
                                attribute 'σ_Cx' : Real = 28.721044428837228;
                                attribute Cy : Real = -25.121706956997514;
                                attribute 'σ_Cy' : Real = 28.23690002309109;
                                attribute Cz : Real = -98.24852924793959;
                                attribute 'σ_Cz' : Real = 29.057750463592832;
                                attribute Ixx : Real = 0.09295107987150189;
                                attribute 'σ_Ixx' : Real = 0.37074144170588635;
                                attribute Iyy : Real = 0.09363749449332734;
                                attribute 'σ_Iyy' : Real = 0.3723953238821935;
                                attribute Izz : Real = 0.09665229984110107;
                                attribute 'σ_Izz' : Real = 0.37017423652493897;
                                attribute Ixy : Real = 3.1482721439296025e-4;
                                attribute 'σ_Ixy' : Real = 0.02351283871158888;
                                attribute Ixz : Real = -7.078397963966121e-4;
                                attribute 'σ_Ixz' : Real = 0.022566176940390956;
                                attribute Iyz : Real = -0.0013766801883652617;
                                attribute 'σ_Iyz' : Real = 0.02209918015384651;
                            }
                        }
                        part <'C.1.1.3.5.2.2'> 'Subassembly 141' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.5.2.2.1'> 'Part 481' {
                                attribute POIconv : String = "+";
                                attribute Ipoint : Boolean = false;
                                attribute mass : Real = 0.16374995881691576;
                                attribute 'σ_mass' : Real = 0.28909372274994966;
                                attribute Cx : Real = -67.04862541519105;
                                attribute 'σ_Cx' : Real = 28.721044428837228;
                                attribute Cy : Real = -67.478201771155;
                                attribute 'σ_Cy' : Real = 28.23690002309109;
                                attribute Cz : Real = -82.33389533124864;
                                attribute 'σ_Cz' : Real = 29.057750463592832;
                                attribute Ixx : Real = 0.1898077490849003;
                                attribute 'σ_Ixx' : Real = 0.37074144170588635;
                                attribute Iyy : Real = 0.20152880244461618;
                                attribute 'σ_Iyy' : Real = 0.3723953238821935;
                                attribute Izz : Real = 0.16429627004527667;
                                attribute 'σ_Izz' : Real = 0.37017423652493897;
                                attribute Ixy : Real = 0.00561605382337779;
                                attribute 'σ_Ixy' : Real = 0.02351283871158888;
                                attribute Ixz : Real = 0.02384162093817892;
                                attribute 'σ_Ixz' : Real = 0.022566176940390956;
                                attribute Iyz : Real = 0.010141324329997838;
                                attribute 'σ_Iyz' : Real = 0.02209918015384651;
                            }
                            part <'C.1.1.3.5.2.2.2'> 'Part 482' {
                                attribute POIconv : String = "-";
                                attribute Ipoint : Boolean = false;
                                attribute mass : Real = 0.4507169040031731;
                                attribute 'σ_mass' : Real = 0.28909372274994966;
                                attribute Cx : Real = -83.87389783747494;
                                attribute 'σ_Cx' : Real = 28.721044428837228;
                                attribute Cy : Real = -81.38862894847989;
                                attribute 'σ_Cy' : Real = 28.23690002309109;
                                attribute Cz : Real = 12.456491077318788;
                                attribute 'σ_Cz' : Real = 29.057750463592832;
                                attribute Ixx : Real = 0.6158056778280808;
                                attribute 'σ_Ixx' : Real = 0.37074144170588635;
                                attribute Iyy : Real = 0.5796172556689609;
                                attribute 'σ_Iyy' : Real = 0.3723953238821935;
                                attribute Izz : Real = 0.5051401470904547;
                                attribute 'σ_Izz' : Real = 0.37017423652493897;
                                attribute Ixy : Real = 0.009343448528794547;
                                attribute 'σ_Ixy' : Real = 0.02351283871158888;
                                attribute Ixz : Real = 0.005082597909516647;
                                attribute 'σ_Ixz' : Real = 0.022566176940390956;
                                attribute Iyz : Real = 0.04005551617207841;
                                attribute 'σ_Iyz' : Real = 0.02209918015384651;
                            }
                            part <'C.1.1.3.5.2.2.3'> 'Part 483' {
                                attribute POIconv : String = "+";
                                attribute Ipoint : Boolean = false;
                                attribute mass : Real = 0.4128554402787704;
                                attribute 'σ_mass' : Real = 0.28909372274994966;
                                attribute Cx : Real = 56.88019213266671;
                                attribute 'σ_Cx' : Real = 28.721044428837228;
                                attribute Cy : Real = 41.18983414955437;
                                attribute 'σ_Cy' : Real = 28.23690002309109;
                                attribute Cz : Real = -27.11042449809611;
                                attribute 'σ_Cz' : Real = 29.057750463592832;
                                attribute Ixx : Real = 0.5251657863510354;
                                attribute 'σ_Ixx' : Real = 0.37074144170588635;
                                attribute Iyy : Real = 0.5873546373931822;
                                attribute 'σ_Iyy' : Real = 0.3723953238821935;
                                attribute Izz : Real = 0.5157196977397867;
                                attribute 'σ_Izz' : Real = 0.37017423652493897;
                                attribute Ixy : Real = -0.005497476757732408;
                                attribute 'σ_Ixy' : Real = 0.02351283871158888;
                                attribute Ixz : Real = -0.029968072992941602;
                                attribute 'σ_Ixz' : Real = 0.022566176940390956;
                                attribute Iyz : Real = -2.7002658520572744e-4;
                                attribute 'σ_Iyz' : Real = 0.02209918015384651;
                            }
                        }
                        part <'C.1.1.3.5.2.3'> 'Subassembly 142' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.5.2.3.1'> 'Part 484' {
                                attribute POIconv : String = "+";
                                attribute Ipoint : Boolean = false;
                                attribute mass : Real = 0.16437632891070098;
                                attribute 'σ_mass' : Real = 0.28909372274994966;
                                attribute Cx : Real = -87.94091385789216;
                                attribute 'σ_Cx' : Real = 28.721044428837228;
                                attribute Cy : Real = 8.840931532904506;
                                attribute 'σ_Cy' : Real = 28.23690002309109;
                                attribute Cz : Real = -3.924263082444668;
                                attribute 'σ_Cz' : Real = 29.057750463592832;
                                attribute Ixx : Real = 0.19322989172315935;
                                attribute 'σ_Ixx' : Real = 0.37074144170588635;
                                attribute Iyy : Real = 0.18117497347683426;
                                attribute 'σ_Iyy' : Real = 0.3723953238821935;
                                attribute Izz : Real = 0.1639870371480213;
                                attribute 'σ_Izz' : Real = 0.37017423652493897;
                                attribute Ixy : Real = -0.005156382773976093;
                                attribute 'σ_Ixy' : Real = 0.02351283871158888;
                                attribute Ixz : Real = -0.010925383719903361;
                                attribute 'σ_Ixz' : Real = 0.022566176940390956;
                                attribute Iyz : Real = 0.02123519131864228;
                                attribute 'σ_Iyz' : Real = 0.02209918015384651;
                            }
                            part <'C.1.1.3.5.2.3.2'> 'Part 485' {
                                attribute POIconv : String = "+";
                                attribute Ipoint : Boolean = false;
                                attribute mass : Real = 0.24464886306924746;
                                attribute 'σ_mass' : Real = 0.28909372274994966;
                                attribute Cx : Real = 51.770894788205624;
                                attribute 'σ_Cx' : Real = 28.721044428837228;
                                attribute Cy : Real = -38.410535361617804;
                                attribute 'σ_Cy' : Real = 28.23690002309109;
                                attribute Cz : Real = 81.0674368403852;
                                attribute 'σ_Cz' : Real = 29.057750463592832;
                                attribute Ixx : Real = 0.35059562263245053;
                                attribute 'σ_Ixx' : Real = 0.37074144170588635;
                                attribute Iyy : Real = 0.35202187162961696;
                                attribute 'σ_Iyy' : Real = 0.3723953238821935;
                                attribute Izz : Real = 0.3586053470740151;
                                attribute 'σ_Izz' : Real = 0.37017423652493897;
                                attribute Ixy : Real = -0.008559046326059546;
                                attribute 'σ_Ixy' : Real = 0.02351283871158888;
                                attribute Ixz : Real = 0.0021574451421087866;
                                attribute 'σ_Ixz' : Real = 0.022566176940390956;
                                attribute Iyz : Real = -0.0018875008007492736;
                                attribute 'σ_Iyz' : Real = 0.02209918015384651;
                            }
                            part <'C.1.1.3.5.2.3.3'> 'Part 486' {
                                attribute POIconv : String = "-";
                                attribute Ipoint : Boolean = false;
                                attribute mass : Real = 0.4945702078763861;
                                attribute 'σ_mass' : Real = 0.28909372274994966;
                                attribute Cx : Real = -45.98975325934589;
                                attribute 'σ_Cx' : Real = 28.721044428837228;
                                attribute Cy : Real = 19.607096491381526;
                                attribute 'σ_Cy' : Real = 28.23690002309109;
                                attribute Cz : Real = 57.24931266158819;
                                attribute 'σ_Cz' : Real = 29.057750463592832;
                                attribute Ixx : Real = 0.6302831230563763;
                                attribute 'σ_Ixx' : Real = 0.37074144170588635;
                                attribute Iyy : Real = 0.5453448119334797;
                                attribute 'σ_Iyy' : Real = 0.3723953238821935;
                                attribute Izz : Real = 0.7254060587094954;
                                attribute 'σ_Izz' : Real = 0.37017423652493897;
                                attribute Ixy : Real = -0.008412597573371964;
                                attribute 'σ_Ixy' : Real = 0.02351283871158888;
                                attribute Ixz : Real = 0.0027969856382327298;
                                attribute 'σ_Ixz' : Real = 0.022566176940390956;
                                attribute Iyz : Real = 0.03360699727518125;
                                attribute 'σ_Iyz' : Real = 0.02209918015384651;
                            }
                            part <'C.1.1.3.5.2.3.4'> 'Part 487' {
                                attribute POIconv : String = "-";
                                attribute Ipoint : Boolean = false;
                                attribute mass : Real = 0.11192142649460585;
                                attribute 'σ_mass' : Real = 0.28909372274994966;
                                attribute Cx : Real = 84.71009056083858;
                                attribute 'σ_Cx' : Real = 28.721044428837228;
                                attribute Cy : Real = -47.43609852157533;
                                attribute 'σ_Cy' : Real = 28.23690002309109;
                                attribute Cz : Real = -23.268806701526046;
                                attribute 'σ_Cz' : Real = 29.057750463592832;
                                attribute Ixx : Real = 0.1373412624547402;
                                attribute 'σ_Ixx' : Real = 0.37074144170588635;
                                attribute Iyy : Real = 0.13942781677990032;
                                attribute 'σ_Iyy' : Real = 0.3723953238821935;
                                attribute Izz : Real = 0.11985992298820253;
                                attribute 'σ_Izz' : Real = 0.37017423652493897;
                                attribute Ixy : Real = 0.006348304676403214;
                                attribute 'σ_Ixy' : Real = 0.02351283871158888;
                                attribute Ixz : Real = -0.002555814129702577;
                                attribute 'σ_Ixz' : Real = 0.022566176940390956;
                                attribute Iyz : Real = 7.607875565043727e-4;
                                attribute 'σ_Iyz' : Real = 0.02209918015384651;
                            }
                            part <'C.1.1.3.5.2.3.5'> 'Part 488' {
                                attribute POIconv : String = "+";
                                attribute Ipoint : Boolean = false;
                                attribute mass : Real = 0.21789468341413887;
                                attribute 'σ_mass' : Real = 0.28909372274994966;
                                attribute Cx : Real = -96.10573016107082;
                                attribute 'σ_Cx' : Real = 28.721044428837228;
                                attribute Cy : Real = -69.69127939082682;
                                attribute 'σ_Cy' : Real = 28.23690002309109;
                                attribute Cz : Real = -59.55826546996832;
                                attribute 'σ_Cz' : Real = 29.057750463592832;
                                attribute Ixx : Real = 0.2775584631756365;
                                attribute 'σ_Ixx' : Real = 0.37074144170588635;
                                attribute Iyy : Real = 0.2794096157926723;
                                attribute 'σ_Iyy' : Real = 0.3723953238821935;
                                attribute Izz : Real = 0.3019541112248354;
                                attribute 'σ_Izz' : Real = 0.37017423652493897;
                                attribute Ixy : Real = -8.468145558568571e-4;
                                attribute 'σ_Ixy' : Real = 0.02351283871158888;
                                attribute Ixz : Real = -0.0026579386579302193;
                                attribute 'σ_Ixz' : Real = 0.022566176940390956;
                                attribute Iyz : Real = -0.007667960070206363;
                                attribute 'σ_Iyz' : Real = 0.02209918015384651;
                            }
                        }
                        part <'C.1.1.3.5.2.4'> 'Subassembly 143' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.5.2.4.1'> 'Part 489' {
                                attribute POIconv : String = "+";
                                attribute Ipoint : Boolean = false;
                                attribute mass : Real = 0.9797311544348486;
                                attribute 'σ_mass' : Real = 0.28909372274994966;
                                attribute Cx : Real = 24.184934701770544;
                                attribute 'σ_Cx' : Real = 28.721044428837228;
                                attribute Cy : Real = 99.54050313681364;
                                attribute 'σ_Cy' : Real = 28.23690002309109;
                                attribute Cz : Real = 43.70176154188812;
                                attribute 'σ_Cz' : Real = 29.057750463592832;
                                attribute Ixx : Real = 1.2733607291849118;
                                attribute 'σ_Ixx' : Real = 0.37074144170588635;
                                attribute Iyy : Real = 1.1688262813881496;
                                attribute 'σ_Iyy' : Real = 0.3723953238821935;
                                attribute Izz : Real = 1.3946195222107354;
                                attribute 'σ_Izz' : Real = 0.37017423652493897;
                                attribute Ixy : Real = 0.015571141618372022;
                                attribute 'σ_Ixy' : Real = 0.02351283871158888;
                                attribute Ixz : Real = -0.019751431039975308;
                                attribute 'σ_Ixz' : Real = 0.022566176940390956;
                                attribute Iyz : Real = 0.09809058418986746;
                                attribute 'σ_Iyz' : Real = 0.02209918015384651;
                            }
                            part <'C.1.1.3.5.2.4.2'> 'Part 490' {
                                attribute POIconv : String = "+";
                                attribute Ipoint : Boolean = false;
                                attribute mass : Real = 0.10377336461236701;
                                attribute 'σ_mass' : Real = 0.28909372274994966;
                                attribute Cx : Real = -14.816736988723278;
                                attribute 'σ_Cx' : Real = 28.721044428837228;
                                attribute Cy : Real = -10.649866750463843;
                                attribute 'σ_Cy' : Real = 28.23690002309109;
                                attribute Cz : Real = -99.30578176863492;
                                attribute 'σ_Cz' : Real = 29.057750463592832;
                                attribute Ixx : Real = 0.15507165814899845;
                                attribute 'σ_Ixx' : Real = 0.37074144170588635;
                                attribute Iyy : Real = 0.1568864109492887;
                                attribute 'σ_Iyy' : Real = 0.3723953238821935;
                                attribute Izz : Real = 0.15828423479637294;
                                attribute 'σ_Izz' : Real = 0.37017423652493897;
                                attribute Ixy : Real = 0.006754056841802575;
                                attribute 'σ_Ixy' : Real = 0.02351283871158888;
                                attribute Ixz : Real = 1.9768165558448663e-4;
                                attribute 'σ_Ixz' : Real = 0.022566176940390956;
                                attribute Iyz : Real = -1.8422986073554073e-4;
                                attribute 'σ_Iyz' : Real = 0.02209918015384651;
                            }
                            part <'C.1.1.3.5.2.4.3'> 'Part 491' {
                                attribute POIconv : String = "+";
                                attribute Ipoint : Boolean = false;
                                attribute mass : Real = 0.8821552607573103;
                                attribute 'σ_mass' : Real = 0.28909372274994966;
                                attribute Cx : Real = -31.448619114235044;
                                attribute 'σ_Cx' : Real = 28.721044428837228;
                                attribute Cy : Real = 61.20740743353963;
                                attribute 'σ_Cy' : Real = 28.23690002309109;
                                attribute Cz : Real = -10.734829911962152;
                                attribute 'σ_Cz' : Real = 29.057750463592832;
                                attribute Ixx : Real = 1.0604167900272277;
                                attribute 'σ_Ixx' : Real = 0.37074144170588635;
                                attribute Iyy : Real = 1.0755883193522682;
                                attribute 'σ_Iyy' : Real = 0.3723953238821935;
                                attribute Izz : Real = 1.0431785297335203;
                                attribute 'σ_Izz' : Real = 0.37017423652493897;
                                attribute Ixy : Real = -0.014324567936260912;
                                attribute 'σ_Ixy' : Real = 0.02351283871158888;
                                attribute Ixz : Real = -0.012068091469857777;
                                attribute 'σ_Ixz' : Real = 0.022566176940390956;
                                attribute Iyz : Real = 0.004789550252911379;
                                attribute 'σ_Iyz' : Real = 0.02209918015384651;
                            }
                        }
                    }
                    part <'C.1.1.3.5.3'> 'Assembly 39' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.3.5.3.1'> 'Subassembly 144' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.5.3.1.1'> 'Part 492' {
                                attribute POIconv : String = "-";
                                attribute Ipoint : Boolean = false;
                                attribute mass : Real = 0.456779734400101;
                                attribute 'σ_mass' : Real = 0.28909372274994966;
                                attribute Cx : Real = -65.07756817154586;
                                attribute 'σ_Cx' : Real = 28.721044428837228;
                                attribute Cy : Real = -20.718311425298452;
                                attribute 'σ_Cy' : Real = 28.23690002309109;
                                attribute Cz : Real = 66.25896566547453;
                                attribute 'σ_Cz' : Real = 29.057750463592832;
                                attribute Ixx : Real = 0.5219499861603093;
                                attribute 'σ_Ixx' : Real = 0.37074144170588635;
                                attribute Iyy : Real = 0.5240345911279958;
                                attribute 'σ_Iyy' : Real = 0.3723953238821935;
                                attribute Izz : Real = 0.6072828593849432;
                                attribute 'σ_Izz' : Real = 0.37017423652493897;
                                attribute Ixy : Real = 0.003379810394848723;
                                attribute 'σ_Ixy' : Real = 0.02351283871158888;
                                attribute Ixz : Real = -0.0015570557014130606;
                                attribute 'σ_Ixz' : Real = 0.022566176940390956;
                                attribute Iyz : Real = -0.013852493918282666;
                                attribute 'σ_Iyz' : Real = 0.02209918015384651;
                            }
                            part <'C.1.1.3.5.3.1.2'> 'Part 493' {
                                attribute POIconv : String = "-";
                                attribute Ipoint : Boolean = false;
                                attribute mass : Real = 0.8545161055035424;
                                attribute 'σ_mass' : Real = 0.28909372274994966;
                                attribute Cx : Real = 14.27876208908856;
                                attribute 'σ_Cx' : Real = 28.721044428837228;
                                attribute Cy : Real = -52.957221725955606;
                                attribute 'σ_Cy' : Real = 28.23690002309109;
                                attribute Cz : Real = 37.10089614614844;
                                attribute 'σ_Cz' : Real = 29.057750463592832;
                                attribute Ixx : Real = 1.1733830730280859;
                                attribute 'σ_Ixx' : Real = 0.37074144170588635;
                                attribute Iyy : Real = 1.1396127012612223;
                                attribute 'σ_Iyy' : Real = 0.3723953238821935;
                                attribute Izz : Real = 1.1478849656533123;
                                attribute 'σ_Izz' : Real = 0.37017423652493897;
                                attribute Ixy : Real = -0.022730525926512812;
                                attribute 'σ_Ixy' : Real = 0.02351283871158888;
                                attribute Ixz : Real = 0.0068739508055629985;
                                attribute 'σ_Ixz' : Real = 0.022566176940390956;
                                attribute Iyz : Real = 0.02347491269355722;
                                attribute 'σ_Iyz' : Real = 0.02209918015384651;
                            }
                            part <'C.1.1.3.5.3.1.3'> 'Part 494' {
                                attribute POIconv : String = "-";
                                attribute Ipoint : Boolean = false;
                                attribute mass : Real = 0.5874680392129812;
                                attribute 'σ_mass' : Real = 0.28909372274994966;
                                attribute Cx : Real = 22.739250352606177;
                                attribute 'σ_Cx' : Real = 28.721044428837228;
                                attribute Cy : Real = 83.20324965752661;
                                attribute 'σ_Cy' : Real = 28.23690002309109;
                                attribute Cz : Real = 11.894957395270467;
                                attribute 'σ_Cz' : Real = 29.057750463592832;
                                attribute Ixx : Real = 0.6274487930061973;
                                attribute 'σ_Ixx' : Real = 0.37074144170588635;
                                attribute Iyy : Real = 0.7727533694797315;
                                attribute 'σ_Iyy' : Real = 0.3723953238821935;
                                attribute Izz : Real = 0.7970727530554764;
                                attribute 'σ_Izz' : Real = 0.37017423652493897;
                                attribute Ixy : Real = -0.0432451684166896;
                                attribute 'σ_Ixy' : Real = 0.02351283871158888;
                                attribute Ixz : Real = 0.029962829448293787;
                                attribute 'σ_Ixz' : Real = 0.022566176940390956;
                                attribute Iyz : Real = 0.005769132986700421;
                                attribute 'σ_Iyz' : Real = 0.02209918015384651;
                            }
                        }
                        part <'C.1.1.3.5.3.2'> 'Subassembly 145' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.3.5.3.2.1'> 'Part 495' {
                                attribute POIconv : String = "-";
                                attribute Ipoint : Boolean = false;
                                attribute mass : Real = 0.7315342742293142;
                                attribute 'σ_mass' : Real = 0.28909372274994966;
                                attribute Cx : Real = -27.083597285673022;
                                attribute 'σ_Cx' : Real = 28.721044428837228;
                                attribute Cy : Real = 59.81912002898753;
                                attribute 'σ_Cy' : Real = 28.23690002309109;
                                attribute Cz : Real = 54.87254145555198;
                                attribute 'σ_Cz' : Real = 29.057750463592832;
                                attribute Ixx : Real = 0.9046982971158939;
                                attribute 'σ_Ixx' : Real = 0.37074144170588635;
                                attribute Iyy : Real = 0.9475187028309325;
                                attribute 'σ_Iyy' : Real = 0.3723953238821935;
                                attribute Izz : Real = 0.7458865510366658;
                                attribute 'σ_Izz' : Real = 0.37017423652493897;
                                attribute Ixy : Real = -0.01280273458091544;
                                attribute 'σ_Ixy' : Real = 0.02351283871158888;
                                attribute Ixz : Real = 0.004567230542952156;
                                attribute 'σ_Ixz' : Real = 0.022566176940390956;
                                attribute Iyz : Real = 0.005248098682998648;
                                attribute 'σ_Iyz' : Real = 0.02209918015384651;
                            }
                            part <'C.1.1.3.5.3.2.2'> 'Part 496' {
                                attribute POIconv : String = "-";
                                attribute Ipoint : Boolean = false;
                                attribute mass : Real = 0.9129071567088831;
                                attribute 'σ_mass' : Real = 0.28909372274994966;
                                attribute Cx : Real = -8.936004992574453;
                                attribute 'σ_Cx' : Real = 28.721044428837228;
                                attribute Cy : Real = -19.17416276410222;
                                attribute 'σ_Cy' : Real = 28.23690002309109;
                                attribute Cz : Real = -72.87885313853621;
                                attribute 'σ_Cz' : Real = 29.057750463592832;
                                attribute Ixx : Real = 1.1025994208789753;
                                attribute 'σ_Ixx' : Real = 0.37074144170588635;
                                attribute Iyy : Real = 1.12154690615921;
                                attribute 'σ_Iyy' : Real = 0.3723953238821935;
                                attribute Izz : Real = 0.9919616068567793;
                                attribute 'σ_Izz' : Real = 0.37017423652493897;
                                attribute Ixy : Real = -0.0908055245648895;
                                attribute 'σ_Ixy' : Real = 0.02351283871158888;
                                attribute Ixz : Real = -0.06132027589368768;
                                attribute 'σ_Ixz' : Real = 0.022566176940390956;
                                attribute Iyz : Real = -0.026988278481022074;
                                attribute 'σ_Iyz' : Real = 0.02209918015384651;
                            }
                            part <'C.1.1.3.5.3.2.3'> 'Part 497' {
                                attribute POIconv : String = "+";
                                attribute Ipoint : Boolean = false;
                                attribute mass : Real = 0.33162104671006093;
                                attribute 'σ_mass' : Real = 0.28909372274994966;
                                attribute Cx : Real = 36.28541943617165;
                                attribute 'σ_Cx' : Real = 28.721044428837228;
                                attribute Cy : Real = 58.1856410484761;
                                attribute 'σ_Cy' : Real = 28.23690002309109;
                                attribute Cz : Real = 12.509159417822957;
                                attribute 'σ_Cz' : Real = 29.057750463592832;
                                attribute Ixx : Real = 0.4775281663408432;
                                attribute 'σ_Ixx' : Real = 0.37074144170588635;
                                attribute Iyy : Real = 0.42359904073673266;
                                attribute 'σ_Iyy' : Real = 0.3723953238821935;
                                attribute Izz : Real = 0.462655986295135;
                                attribute 'σ_Izz' : Real = 0.37017423652493897;
                                attribute Ixy : Real = -0.028136388917012176;
                                attribute 'σ_Ixy' : Real = 0.02351283871158888;
                                attribute Ixz : Real = 0.02027832792366263;
                                attribute 'σ_Ixz' : Real = 0.022566176940390956;
                                attribute Iyz : Real = 0.001679733290880705;
                                attribute 'σ_Iyz' : Real = 0.02209918015384651;
                            }
                            part <'C.1.1.3.5.3.2.4'> 'Part 498' {
                                attribute POIconv : String = "+";
                                attribute Ipoint : Boolean = false;
                                attribute mass : Real = 0.924418632277986;
                                attribute 'σ_mass' : Real = 0.28909372274994966;
                                attribute Cx : Real = -40.1994860265404;
                                attribute 'σ_Cx' : Real = 28.721044428837228;
                                attribute Cy : Real = -32.75319938547909;
                                attribute 'σ_Cy' : Real = 28.23690002309109;
                                attribute Cz : Real = -2.436229260638356;
                                attribute 'σ_Cz' : Real = 29.057750463592832;
                                attribute Ixx : Real = 1.4455758152316664;
                                attribute 'σ_Ixx' : Real = 0.37074144170588635;
                                attribute Iyy : Real = 1.4260410003644974;
                                attribute 'σ_Iyy' : Real = 0.3723953238821935;
                                attribute Izz : Real = 1.4127503014989167;
                                attribute 'σ_Izz' : Real = 0.37017423652493897;
                                attribute Ixy : Real = 0.020105404962665264;
                                attribute 'σ_Ixy' : Real = 0.02351283871158888;
                                attribute Ixz : Real = 0.01913291002739733;
                                attribute 'σ_Ixz' : Real = 0.022566176940390956;
                                attribute Iyz : Real = 0.02229040833634502;
                                attribute 'σ_Iyz' : Real = 0.02209918015384651;
                            }
                        }
                    }
                }
            }
            part <'C.1.1.4'> 'Element 4' {
                attribute POIconv : String = "-";
                attribute Ipoint : Boolean;
                attribute mass : Real;
                attribute 'σ_mass' : Real;
                attribute Cx : Real;
                attribute 'σ_Cx' : Real;
                attribute Cy : Real;
                attribute 'σ_Cy' : Real;
                attribute Cz : Real;
                attribute 'σ_Cz' : Real;
                attribute Ixx : Real;
                attribute 'σ_Ixx' : Real;
                attribute Iyy : Real;
                attribute 'σ_Iyy' : Real;
                attribute Izz : Real;
                attribute 'σ_Izz' : Real;
                attribute Ixy : Real;
                attribute 'σ_Ixy' : Real;
                attribute Ixz : Real;
                attribute 'σ_Ixz' : Real;
                attribute Iyz : Real;
                attribute 'σ_Iyz' : Real;
                part <'C.1.1.4.1'> 'Subsystem 11' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.4.1.1'> 'Assembly 40' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.1.1.1'> 'Subassembly 146' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.1.1.1.1'> 'Part 499' {
                                attribute POIconv : String = "-";
                                attribute Ipoint : Boolean = false;
                                attribute mass : Real = 0.10599838715069927;
                                attribute 'σ_mass' : Real = 0.28909372274994966;
                                attribute Cx : Real = -84.07895197160542;
                                attribute 'σ_Cx' : Real = 28.721044428837228;
                                attribute Cy : Real = -47.38326636143029;
                                attribute 'σ_Cy' : Real = 28.23690002309109;
                                attribute Cz : Real = 6.345878820866346;
                                attribute 'σ_Cz' : Real = 29.057750463592832;
                                attribute Ixx : Real = 0.15278704907736385;
                                attribute 'σ_Ixx' : Real = 0.37074144170588635;
                                attribute Iyy : Real = 0.15308000367046964;
                                attribute 'σ_Iyy' : Real = 0.3723953238821935;
                                attribute Izz : Real = 0.15540248025267547;
                                attribute 'σ_Izz' : Real = 0.37017423652493897;
                                attribute Ixy : Real = 0.00398034431935545;
                                attribute 'σ_Ixy' : Real = 0.02351283871158888;
                                attribute Ixz : Real = 0.0052492795259989795;
                                attribute 'σ_Ixz' : Real = 0.022566176940390956;
                                attribute Iyz : Real = 0.0026196613458009067;
                                attribute 'σ_Iyz' : Real = 0.02209918015384651;
                            }
                            part <'C.1.1.4.1.1.1.2'> 'Part 500' {
                                attribute POIconv : String = "-";
                                attribute Ipoint : Boolean = false;
                                attribute mass : Real = 0.6371688674567267;
                                attribute 'σ_mass' : Real = 0.28909372274994966;
                                attribute Cx : Real = 19.163903687149286;
                                attribute 'σ_Cx' : Real = 28.721044428837228;
                                attribute Cy : Real = 37.46871817857027;
                                attribute 'σ_Cy' : Real = 28.23690002309109;
                                attribute Cz : Real = -88.84721449576318;
                                attribute 'σ_Cz' : Real = 29.057750463592832;
                                attribute Ixx : Real = 0.9004757441134695;
                                attribute 'σ_Ixx' : Real = 0.37074144170588635;
                                attribute Iyy : Real = 0.9801932116768823;
                                attribute 'σ_Iyy' : Real = 0.3723953238821935;
                                attribute Izz : Real = 0.8920301554460848;
                                attribute 'σ_Izz' : Real = 0.37017423652493897;
                                attribute Ixy : Real = -0.012147946118455318;
                                attribute 'σ_Ixy' : Real = 0.02351283871158888;
                                attribute Ixz : Real = -0.0075942226184956794;
                                attribute 'σ_Ixz' : Real = 0.022566176940390956;
                                attribute Iyz : Real = -0.007629964553041381;
                                attribute 'σ_Iyz' : Real = 0.02209918015384651;
                            }
                            part <'C.1.1.4.1.1.1.3'> 'Part 501' {
                                attribute POIconv : String = "+";
                                attribute Ipoint : Boolean = false;
                                attribute mass : Real = 0.8959677613631356;
                                attribute 'σ_mass' : Real = 0.28909372274994966;
                                attribute Cx : Real = -42.340896278619766;
                                attribute 'σ_Cx' : Real = 28.721044428837228;
                                attribute Cy : Real = 59.6509097609669;
                                attribute 'σ_Cy' : Real = 28.23690002309109;
                                attribute Cz : Real = -28.858464350923896;
                                attribute 'σ_Cz' : Real = 29.057750463592832;
                                attribute Ixx : Real = 1.259001407422434;
                                attribute 'σ_Ixx' : Real = 0.37074144170588635;
                                attribute Iyy : Real = 1.1515209076494384;
                                attribute 'σ_Iyy' : Real = 0.3723953238821935;
                                attribute Izz : Real = 1.3046469321727268;
                                attribute 'σ_Izz' : Real = 0.37017423652493897;
                                attribute Ixy : Real = 0.027184001078134335;
                                attribute 'σ_Ixy' : Real = 0.02351283871158888;
                                attribute Ixz : Real = 0.049499085633612785;
                                attribute 'σ_Ixz' : Real = 0.022566176940390956;
                                attribute Iyz : Real = 0.0470255881304107;
                                attribute 'σ_Iyz' : Real = 0.02209918015384651;
                            }
                            part <'C.1.1.4.1.1.1.4'> 'Part 502' {
                                attribute POIconv : String = "-";
                                attribute Ipoint : Boolean = false;
                                attribute mass : Real = 0.5450401575393043;
                                attribute 'σ_mass' : Real = 0.28909372274994966;
                                attribute Cx : Real = -93.46640505827963;
                                attribute 'σ_Cx' : Real = 28.721044428837228;
                                attribute Cy : Real = -38.00572855398059;
                                attribute 'σ_Cy' : Real = 28.23690002309109;
                                attribute Cz : Real = -38.63285589031875;
                                attribute 'σ_Cz' : Real = 29.057750463592832;
                                attribute Ixx : Real = 0.6172863254542152;
                                attribute 'σ_Ixx' : Real = 0.37074144170588635;
                                attribute Iyy : Real = 0.6575374937140223;
                                attribute 'σ_Iyy' : Real = 0.3723953238821935;
                                attribute Izz : Real = 0.5697219682827084;
                                attribute 'σ_Izz' : Real = 0.37017423652493897;
                                attribute Ixy : Real = -0.038603057131318154;
                                attribute 'σ_Ixy' : Real = 0.02351283871158888;
                                attribute Ixz : Real = -0.032253717968582854;
                                attribute 'σ_Ixz' : Real = 0.022566176940390956;
                                attribute Iyz : Real = -0.025629205204220074;
                                attribute 'σ_Iyz' : Real = 0.02209918015384651;
                            }
                        }
                        part <'C.1.1.4.1.1.2'> 'Subassembly 147' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.1.1.2.1'> 'Part 503' {
                                attribute POIconv : String = "+";
                                attribute Ipoint : Boolean = false;
                                attribute mass : Real = 0.2985605688514188;
                                attribute 'σ_mass' : Real = 0.28909372274994966;
                                attribute Cx : Real = 42.47858445160091;
                                attribute 'σ_Cx' : Real = 28.721044428837228;
                                attribute Cy : Real = -72.608512500301;
                                attribute 'σ_Cy' : Real = 28.23690002309109;
                                attribute Cz : Real = -14.873924944549799;
                                attribute 'σ_Cz' : Real = 29.057750463592832;
                                attribute Ixx : Real = 0.39686811994325477;
                                attribute 'σ_Ixx' : Real = 0.37074144170588635;
                                attribute Iyy : Real = 0.4186613130472625;
                                attribute 'σ_Iyy' : Real = 0.3723953238821935;
                                attribute Izz : Real = 0.41960603939966684;
                                attribute 'σ_Izz' : Real = 0.37017423652493897;
                                attribute Ixy : Real = 0.008888219400596102;
                                attribute 'σ_Ixy' : Real = 0.02351283871158888;
                                attribute Ixz : Real = -0.0070280152672081014;
                                attribute 'σ_Ixz' : Real = 0.022566176940390956;
                                attribute Iyz : Real = -0.004296165015230066;
                                attribute 'σ_Iyz' : Real = 0.02209918015384651;
                            }
                            part <'C.1.1.4.1.1.2.2'> 'Part 504' {
                                attribute POIconv : String = "+";
                                attribute Ipoint : Boolean = false;
                                attribute mass : Real = 0.37265111112524757;
                                attribute 'σ_mass' : Real = 0.28909372274994966;
                                attribute Cx : Real = -54.33716285042465;
                                attribute 'σ_Cx' : Real = 28.721044428837228;
                                attribute Cy : Real = -96.24383323825896;
                                attribute 'σ_Cy' : Real = 28.23690002309109;
                                attribute Cz : Real = -84.89596317522228;
                                attribute 'σ_Cz' : Real = 29.057750463592832;
                                attribute Ixx : Real = 0.48709901323801563;
                                attribute 'σ_Ixx' : Real = 0.37074144170588635;
                                attribute Iyy : Real = 0.520270368495399;
                                attribute 'σ_Iyy' : Real = 0.3723953238821935;
                                attribute Izz : Real = 0.4647380356074044;
                                attribute 'σ_Izz' : Real = 0.37017423652493897;
                                attribute Ixy : Real = -0.05488208152097072;
                                attribute 'σ_Ixy' : Real = 0.02351283871158888;
                                attribute Ixz : Real = -0.023222607450379754;
                                attribute 'σ_Ixz' : Real = 0.022566176940390956;
                                attribute Iyz : Real = -0.022944397091971838;
                                attribute 'σ_Iyz' : Real = 0.02209918015384651;
                            }
                            part <'C.1.1.4.1.1.2.3'> 'Part 505' {
                                attribute POIconv : String = "+";
                                attribute Ipoint : Boolean = false;
                                attribute mass : Real = 0.7397677671948913;
                                attribute 'σ_mass' : Real = 0.28909372274994966;
                                attribute Cx : Real = 23.455810546875;
                                attribute 'σ_Cx' : Real = 28.721044428837228;
                                attribute Cy : Real = -45.0782778672874;
                                attribute 'σ_Cy' : Real = 28.23690002309109;
                                attribute Cz : Real = 73.02248226478696;
                                attribute 'σ_Cz' : Real = 29.057750463592832;
                                attribute Ixx : Real = 1.0063665260534227;
                                attribute 'σ_Ixx' : Real = 0.37074144170588635;
                                attribute Iyy : Real = 0.8706827870985145;
                                attribute 'σ_Iyy' : Real = 0.3723953238821935;
                                attribute Izz : Real = 0.9042224637998537;
                                attribute 'σ_Izz' : Real = 0.37017423652493897;
                                attribute Ixy : Real = -0.0070543235260011865;
                                attribute 'σ_Ixy' : Real = 0.02351283871158888;
                                attribute Ixz : Real = 0.06793677252515268;
                                attribute 'σ_Ixz' : Real = 0.022566176940390956;
                                attribute Iyz : Real = 0.0035243387354903333;
                                attribute 'σ_Iyz' : Real = 0.02209918015384651;
                            }
                            part <'C.1.1.4.1.1.2.4'> 'Part 506' {
                                attribute POIconv : String = "-";
                                attribute Ipoint : Boolean = false;
                                attribute mass : Real = 0.2884733271396253;
                                attribute 'σ_mass' : Real = 0.28909372274994966;
                                attribute Cx : Real = -50.3648157697171;
                                attribute 'σ_Cx' : Real = 28.721044428837228;
                                attribute Cy : Real = -88.31648114137352;
                                attribute 'σ_Cy' : Real = 28.23690002309109;
                                attribute Cz : Real = 90.19211665727198;
                                attribute 'σ_Cz' : Real = 29.057750463592832;
                                attribute Ixx : Real = 0.36546593879405004;
                                attribute 'σ_Ixx' : Real = 0.37074144170588635;
                                attribute Iyy : Real = 0.3823836746117036;
                                attribute 'σ_Iyy' : Real = 0.3723953238821935;
                                attribute Izz : Real = 0.35777025923503464;
                                attribute 'σ_Izz' : Real = 0.37017423652493897;
                                attribute Ixy : Real = 0.03321225145191976;
                                attribute 'σ_Ixy' : Real = 0.02351283871158888;
                                attribute Ixz : Real = -9.27428305742713e-6;
                                attribute 'σ_Ixz' : Real = 0.022566176940390956;
                                attribute Iyz : Real = -3.258799532586333e-5;
                                attribute 'σ_Iyz' : Real = 0.02209918015384651;
                            }
                        }
                        part <'C.1.1.4.1.1.3'> 'Subassembly 148' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.1.1.3.1'> 'Part 507' {
                                attribute POIconv : String = "-";
                                attribute Ipoint : Boolean = false;
                                attribute mass : Real = 0.6799589239286724;
                                attribute 'σ_mass' : Real = 0.28909372274994966;
                                attribute Cx : Real = -23.37936842814088;
                                attribute 'σ_Cx' : Real = 28.721044428837228;
                                attribute Cy : Real = 71.64420271292329;
                                attribute 'σ_Cy' : Real = 28.23690002309109;
                                attribute Cz : Real = 19.454904785379767;
                                attribute 'σ_Cz' : Real = 29.057750463592832;
                                attribute Ixx : Real = 0.9396641733695398;
                                attribute 'σ_Ixx' : Real = 0.37074144170588635;
                                attribute Iyy : Real = 0.8836162410866945;
                                attribute 'σ_Iyy' : Real = 0.3723953238821935;
                                attribute Izz : Real = 0.9031940903405005;
                                attribute 'σ_Izz' : Real = 0.37017423652493897;
                                attribute Ixy : Real = 0.05485065543238274;
                                attribute 'σ_Ixy' : Real = 0.02351283871158888;
                                attribute Ixz : Real = -0.03919145476472046;
                                attribute 'σ_Ixz' : Real = 0.022566176940390956;
                                attribute Iyz : Real = 0.002945385441951963;
                                attribute 'σ_Iyz' : Real = 0.02209918015384651;
                            }
                            part <'C.1.1.4.1.1.3.2'> 'Part 508' {
                                attribute POIconv : String = "-";
                                attribute Ipoint : Boolean = false;
                                attribute mass : Real = 0.34927724362071605;
                                attribute 'σ_mass' : Real = 0.28909372274994966;
                                attribute Cx : Real = -55.54687618277967;
                                attribute 'σ_Cx' : Real = 28.721044428837228;
                                attribute Cy : Real = -34.929734002798796;
                                attribute 'σ_Cy' : Real = 28.23690002309109;
                                attribute Cz : Real = 56.43384549766779;
                                attribute 'σ_Cz' : Real = 29.057750463592832;
                                attribute Ixx : Real = 0.45713847653811635;
                                attribute 'σ_Ixx' : Real = 0.37074144170588635;
                                attribute Iyy : Real = 0.42781133169479196;
                                attribute 'σ_Iyy' : Real = 0.3723953238821935;
                                attribute Izz : Real = 0.4328969177629292;
                                attribute 'σ_Izz' : Real = 0.37017423652493897;
                                attribute Ixy : Real = -0.01961816360575059;
                                attribute 'σ_Ixy' : Real = 0.02351283871158888;
                                attribute Ixz : Real = 0.014412363623219269;
                                attribute 'σ_Ixz' : Real = 0.022566176940390956;
                                attribute Iyz : Real = 0.025370042095948682;
                                attribute 'σ_Iyz' : Real = 0.02209918015384651;
                            }
                        }
                        part <'C.1.1.4.1.1.4'> 'Subassembly 149' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.1.1.4.1'> 'Part 509' {
                                attribute POIconv : String = "+";
                                attribute Ipoint : Boolean = false;
                                attribute mass : Real = 0.8177969777865801;
                                attribute 'σ_mass' : Real = 0.28909372274994966;
                                attribute Cx : Real = 63.316851714625955;
                                attribute 'σ_Cx' : Real = 28.721044428837228;
                                attribute Cy : Real = -93.38567056693137;
                                attribute 'σ_Cy' : Real = 28.23690002309109;
                                attribute Cz : Real = -99.15952100418508;
                                attribute 'σ_Cz' : Real = 29.057750463592832;
                                attribute Ixx : Real = 0.9374087253379887;
                                attribute 'σ_Ixx' : Real = 0.37074144170588635;
                                attribute Iyy : Real = 0.9514757553391375;
                                attribute 'σ_Iyy' : Real = 0.3723953238821935;
                                attribute Izz : Real = 0.8685434771771978;
                                attribute 'σ_Izz' : Real = 0.37017423652493897;
                                attribute Ixy : Real = 0.0643372036197539;
                                attribute 'σ_Ixy' : Real = 0.02351283871158888;
                                attribute Ixz : Real = -0.04455661814485534;
                                attribute 'σ_Ixz' : Real = 0.022566176940390956;
                                attribute Iyz : Real = 0.01916930260284995;
                                attribute 'σ_Iyz' : Real = 0.02209918015384651;
                            }
                            part <'C.1.1.4.1.1.4.2'> 'Part 510' {
                                attribute POIconv : String = "+";
                                attribute Ipoint : Boolean = false;
                                attribute mass : Real = 0.9193144191103056;
                                attribute 'σ_mass' : Real = 0.28909372274994966;
                                attribute Cx : Real = -81.98665287345648;
                                attribute 'σ_Cx' : Real = 28.721044428837228;
                                attribute Cy : Real = 45.633562095463276;
                                attribute 'σ_Cy' : Real = 28.23690002309109;
                                attribute Cz : Real = -91.58319300040603;
                                attribute 'σ_Cz' : Real = 29.057750463592832;
                                attribute Ixx : Real = 0.9433558125814777;
                                attribute 'σ_Ixx' : Real = 0.37074144170588635;
                                attribute Iyy : Real = 1.195947309742223;
                                attribute 'σ_Iyy' : Real = 0.3723953238821935;
                                attribute Izz : Real = 1.2085314562068112;
                                attribute 'σ_Izz' : Real = 0.37017423652493897;
                                attribute Ixy : Real = -0.1005473448582731;
                                attribute 'σ_Ixy' : Real = 0.02351283871158888;
                                attribute Ixz : Real = -0.0029584935395142887;
                                attribute 'σ_Ixz' : Real = 0.022566176940390956;
                                attribute Iyz : Real = 0.003047434934544749;
                                attribute 'σ_Iyz' : Real = 0.02209918015384651;
                            }
                            part <'C.1.1.4.1.1.4.3'> 'Part 511' {
                                attribute POIconv : String = "+";
                                attribute Ipoint : Boolean = false;
                                attribute mass : Real = 0.7343257454780396;
                                attribute 'σ_mass' : Real = 0.28909372274994966;
                                attribute Cx : Real = -60.674673644825816;
                                attribute 'σ_Cx' : Real = 28.721044428837228;
                                attribute Cy : Real = -71.01439191028476;
                                attribute 'σ_Cy' : Real = 28.23690002309109;
                                attribute Cz : Real = -43.64943685941398;
                                attribute 'σ_Cz' : Real = 29.057750463592832;
                                attribute Ixx : Real = 0.9768430900978795;
                                attribute 'σ_Ixx' : Real = 0.37074144170588635;
                                attribute Iyy : Real = 0.9807778606629555;
                                attribute 'σ_Iyy' : Real = 0.3723953238821935;
                                attribute Izz : Real = 1.0248103057913742;
                                attribute 'σ_Izz' : Real = 0.37017423652493897;
                                attribute Ixy : Real = -0.02571439581950459;
                                attribute 'σ_Ixy' : Real = 0.02351283871158888;
                                attribute Ixz : Real = 0.05819663789954853;
                                attribute 'σ_Ixz' : Real = 0.022566176940390956;
                                attribute Iyz : Real = 0.06701639868147345;
                                attribute 'σ_Iyz' : Real = 0.02209918015384651;
                            }
                        }
                        part <'C.1.1.4.1.1.5'> 'Subassembly 150' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.1.1.5.1'> 'Part 512' {
                                attribute POIconv : String = "+";
                                attribute Ipoint : Boolean = false;
                                attribute mass : Real = 0.9244312414054293;
                                attribute 'σ_mass' : Real = 0.28909372274994966;
                                attribute Cx : Real = -89.39456627704203;
                                attribute 'σ_Cx' : Real = 28.721044428837228;
                                attribute Cy : Real = -72.10332262329757;
                                attribute 'σ_Cy' : Real = 28.23690002309109;
                                attribute Cz : Real = -11.877620220184326;
                                attribute 'σ_Cz' : Real = 29.057750463592832;
                                attribute Ixx : Real = 0.9625880694857643;
                                attribute 'σ_Ixx' : Real = 0.37074144170588635;
                                attribute Iyy : Real = 0.9995136022350133;
                                attribute 'σ_Iyy' : Real = 0.3723953238821935;
                                attribute Izz : Real = 0.931533633211416;
                                attribute 'σ_Izz' : Real = 0.37017423652493897;
                                attribute Ixy : Real = 0.0319529691275307;
                                attribute 'σ_Ixy' : Real = 0.02351283871158888;
                                attribute Ixz : Real = -7.976356947282433e-4;
                                attribute 'σ_Ixz' : Real = 0.022566176940390956;
                                attribute Iyz : Real = 0.0019611538758315767;
                                attribute 'σ_Iyz' : Real = 0.02209918015384651;
                            }
                            part <'C.1.1.4.1.1.5.2'> 'Part 513' {
                                attribute POIconv : String = "+";
                                attribute Ipoint : Boolean = false;
                                attribute mass : Real = 0.9096533798619639;
                                attribute 'σ_mass' : Real = 0.28909372274994966;
                                attribute Cx : Real = 14.317942783236504;
                                attribute 'σ_Cx' : Real = 28.721044428837228;
                                attribute Cy : Real = 23.003308288753033;
                                attribute 'σ_Cy' : Real = 28.23690002309109;
                                attribute Cz : Real = 11.833685915917158;
                                attribute 'σ_Cz' : Real = 29.057750463592832;
                                attribute Ixx : Real = 1.1503000977823834;
                                attribute 'σ_Ixx' : Real = 0.37074144170588635;
                                attribute Iyy : Real = 1.352556402018026;
                                attribute 'σ_Iyy' : Real = 0.3723953238821935;
                                attribute Izz : Real = 1.1871868457136197;
                                attribute 'σ_Izz' : Real = 0.37017423652493897;
                                attribute Ixy : Real = 0.06340178962361812;
                                attribute 'σ_Ixy' : Real = 0.02351283871158888;
                                attribute Ixz : Real = -0.03235343579978285;
                                attribute 'σ_Ixz' : Real = 0.022566176940390956;
                                attribute Iyz : Real = 0.024507867845197238;
                                attribute 'σ_Iyz' : Real = 0.02209918015384651;
                            }
                            part <'C.1.1.4.1.1.5.3'> 'Part 514' {
                                attribute POIconv : String = "+";
                                attribute Ipoint : Boolean = false;
                                attribute mass : Real = 0.6854223290602677;
                                attribute 'σ_mass' : Real = 0.28909372274994966;
                                attribute Cx : Real = -81.22497540898621;
                                attribute 'σ_Cx' : Real = 28.721044428837228;
                                attribute Cy : Real = 61.280407942831516;
                                attribute 'σ_Cy' : Real = 28.23690002309109;
                                attribute Cz : Real = 91.70466652140021;
                                attribute 'σ_Cz' : Real = 29.057750463592832;
                                attribute Ixx : Real = 0.840288786584783;
                                attribute 'σ_Ixx' : Real = 0.37074144170588635;
                                attribute Iyy : Real = 0.765126331573571;
                                attribute 'σ_Iyy' : Real = 0.3723953238821935;
                                attribute Izz : Real = 0.9136166916816478;
                                attribute 'σ_Izz' : Real = 0.37017423652493897;
                                attribute Ixy : Real = -0.031214598633100672;
                                attribute 'σ_Ixy' : Real = 0.02351283871158888;
                                attribute Ixz : Real = -0.06336153824575526;
                                attribute 'σ_Ixz' : Real = 0.022566176940390956;
                                attribute Iyz : Real = 0.01069291073437795;
                                attribute 'σ_Iyz' : Real = 0.02209918015384651;
                            }
                            part <'C.1.1.4.1.1.5.4'> 'Part 515' {
                                attribute POIconv : String = "-";
                                attribute Ipoint : Boolean = false;
                                attribute mass : Real = 0.49952153636235747;
                                attribute 'σ_mass' : Real = 0.28909372274994966;
                                attribute Cx : Real = 72.25212324410677;
                                attribute 'σ_Cx' : Real = 28.721044428837228;
                                attribute Cy : Real = -92.67154415138066;
                                attribute 'σ_Cy' : Real = 28.23690002309109;
                                attribute Cz : Real = 62.323373928666115;
                                attribute 'σ_Cz' : Real = 29.057750463592832;
                                attribute Ixx : Real = 0.5346172155904334;
                                attribute 'σ_Ixx' : Real = 0.37074144170588635;
                                attribute Iyy : Real = 0.5911417852422811;
                                attribute 'σ_Iyy' : Real = 0.3723953238821935;
                                attribute Izz : Real = 0.6126056555355612;
                                attribute 'σ_Izz' : Real = 0.37017423652493897;
                                attribute Ixy : Real = -0.03708017841672464;
                                attribute 'σ_Ixy' : Real = 0.02351283871158888;
                                attribute Ixz : Real = 0.020139354272028558;
                                attribute 'σ_Ixz' : Real = 0.022566176940390956;
                                attribute Iyz : Real = 0.010303087585634347;
                                attribute 'σ_Iyz' : Real = 0.02209918015384651;
                            }
                            part <'C.1.1.4.1.1.5.5'> 'Part 516' {
                                attribute POIconv : String = "-";
                                attribute Ipoint : Boolean = false;
                                attribute mass : Real = 0.6596559043950401;
                                attribute 'σ_mass' : Real = 0.28909372274994966;
                                attribute Cx : Real = 96.07480685226619;
                                attribute 'σ_Cx' : Real = 28.721044428837228;
                                attribute Cy : Real = -32.71956550888717;
                                attribute 'σ_Cy' : Real = 28.23690002309109;
                                attribute Cz : Real = -23.496990418061614;
                                attribute 'σ_Cz' : Real = 29.057750463592832;
                                attribute Ixx : Real = 1.0029103028587736;
                                attribute 'σ_Ixx' : Real = 0.37074144170588635;
                                attribute Iyy : Real = 0.8145827853681636;
                                attribute 'σ_Iyy' : Real = 0.3723953238821935;
                                attribute Izz : Real = 0.7839846645719909;
                                attribute 'σ_Izz' : Real = 0.37017423652493897;
                                attribute Ixy : Real = -0.015701094904586873;
                                attribute 'σ_Ixy' : Real = 0.02351283871158888;
                                attribute Ixz : Real = 0.05128851210941665;
                                attribute 'σ_Ixz' : Real = 0.022566176940390956;
                                attribute Iyz : Real = 0.018949446427329923;
                                attribute 'σ_Iyz' : Real = 0.02209918015384651;
                            }
                        }
                    }
                    part <'C.1.1.4.1.2'> 'Assembly 41' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.1.2.1'> 'Subassembly 151' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.1.2.1.1'> 'Part 517' {
                                attribute POIconv : String = "-";
                                attribute Ipoint : Boolean = false;
                                attribute mass : Real = 0.41000311004486867;
                                attribute 'σ_mass' : Real = 0.28909372274994966;
                                attribute Cx : Real = 16.853980906307697;
                                attribute 'σ_Cx' : Real = 28.721044428837228;
                                attribute Cy : Real = -6.128946784883738;
                                attribute 'σ_Cy' : Real = 28.23690002309109;
                                attribute Cz : Real = 14.10215892829001;
                                attribute 'σ_Cz' : Real = 29.057750463592832;
                                attribute Ixx : Real = 0.47778954938366125;
                                attribute 'σ_Ixx' : Real = 0.37074144170588635;
                                attribute Iyy : Real = 0.5714028656326395;
                                attribute 'σ_Iyy' : Real = 0.3723953238821935;
                                attribute Izz : Real = 0.48031025401157584;
                                attribute 'σ_Izz' : Real = 0.37017423652493897;
                                attribute Ixy : Real = -0.004502894132199777;
                                attribute 'σ_Ixy' : Real = 0.02351283871158888;
                                attribute Ixz : Real = -0.018596824840074997;
                                attribute 'σ_Ixz' : Real = 0.022566176940390956;
                                attribute Iyz : Real = -0.02018899642869716;
                                attribute 'σ_Iyz' : Real = 0.02209918015384651;
                            }
                            part <'C.1.1.4.1.2.1.2'> 'Part 518' {
                                attribute POIconv : String = "+";
                                attribute Ipoint : Boolean = false;
                                attribute mass : Real = 0.8653529129733797;
                                attribute 'σ_mass' : Real = 0.28909372274994966;
                                attribute Cx : Real = 99.6475457213819;
                                attribute 'σ_Cx' : Real = 28.721044428837228;
                                attribute Cy : Real = 17.19916225410998;
                                attribute 'σ_Cy' : Real = 28.23690002309109;
                                attribute Cz : Real = -21.90756555646658;
                                attribute 'σ_Cz' : Real = 29.057750463592832;
                                attribute Ixx : Real = 0.9645578906122143;
                                attribute 'σ_Ixx' : Real = 0.37074144170588635;
                                attribute Iyy : Real = 0.8943157698886668;
                                attribute 'σ_Iyy' : Real = 0.3723953238821935;
                                attribute Izz : Real = 0.9146077309781221;
                                attribute 'σ_Izz' : Real = 0.37017423652493897;
                                attribute Ixy : Real = -0.04379352077068726;
                                attribute 'σ_Ixy' : Real = 0.02351283871158888;
                                attribute Ixz : Real = 0.021122798752214622;
                                attribute 'σ_Ixz' : Real = 0.022566176940390956;
                                attribute Iyz : Real = 0.024274443940810565;
                                attribute 'σ_Iyz' : Real = 0.02209918015384651;
                            }
                        }
                        part <'C.1.1.4.1.2.2'> 'Subassembly 152' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.1.2.2.1'> 'Part 519' {
                                attribute POIconv : String = "+";
                                attribute Ipoint : Boolean = false;
                                attribute mass : Real = 0.6837532957738731;
                                attribute 'σ_mass' : Real = 0.28909372274994966;
                                attribute Cx : Real = -56.20675147511065;
                                attribute 'σ_Cx' : Real = 28.721044428837228;
                                attribute Cy : Real = 55.573108745738864;
                                attribute 'σ_Cy' : Real = 28.23690002309109;
                                attribute Cz : Real = 66.8166727758944;
                                attribute 'σ_Cz' : Real = 29.057750463592832;
                                attribute Ixx : Real = 0.8410994866521762;
                                attribute 'σ_Ixx' : Real = 0.37074144170588635;
                                attribute Iyy : Real = 0.8097497730051931;
                                attribute 'σ_Iyy' : Real = 0.3723953238821935;
                                attribute Izz : Real = 0.718105479632145;
                                attribute 'σ_Izz' : Real = 0.37017423652493897;
                                attribute Ixy : Real = 0.021607717832973276;
                                attribute 'σ_Ixy' : Real = 0.02351283871158888;
                                attribute Ixz : Real = -0.028564621897542386;
                                attribute 'σ_Ixz' : Real = 0.022566176940390956;
                                attribute Iyz : Real = 0.003961467486292775;
                                attribute 'σ_Iyz' : Real = 0.02209918015384651;
                            }
                            part <'C.1.1.4.1.2.2.2'> 'Part 520' {
                                attribute POIconv : String = "-";
                                attribute Ipoint : Boolean = false;
                                attribute mass : Real = 0.39166785358823836;
                                attribute 'σ_mass' : Real = 0.28909372274994966;
                                attribute Cx : Real = 94.9291265103966;
                                attribute 'σ_Cx' : Real = 28.721044428837228;
                                attribute Cy : Real = -66.76699281670153;
                                attribute 'σ_Cy' : Real = 28.23690002309109;
                                attribute Cz : Real = -53.59317106194794;
                                attribute 'σ_Cz' : Real = 29.057750463592832;
                                attribute Ixx : Real = 0.43534843491940195;
                                attribute 'σ_Ixx' : Real = 0.37074144170588635;
                                attribute Iyy : Real = 0.380285334329808;
                                attribute 'σ_Iyy' : Real = 0.3723953238821935;
                                attribute Izz : Real = 0.4248309822193187;
                                attribute 'σ_Izz' : Real = 0.37017423652493897;
                                attribute Ixy : Real = 0.007679311515031858;
                                attribute 'σ_Ixy' : Real = 0.02351283871158888;
                                attribute Ixz : Real = 0.003376428021013025;
                                attribute 'σ_Ixz' : Real = 0.022566176940390956;
                                attribute Iyz : Real = -0.011841042450287682;
                                attribute 'σ_Iyz' : Real = 0.02209918015384651;
                            }
                            part <'C.1.1.4.1.2.2.3'> 'Part 521' {
                                attribute POIconv : String = "-";
                                attribute Ipoint : Boolean = false;
                                attribute mass : Real = 0.3471679254688788;
                                attribute 'σ_mass' : Real = 0.28909372274994966;
                                attribute Cx : Real = -46.54039852321148;
                                attribute 'σ_Cx' : Real = 28.721044428837228;
                                attribute Cy : Real = 97.59303494356573;
                                attribute 'σ_Cy' : Real = 28.23690002309109;
                                attribute Cz : Real = -0.3798075020313263;
                                attribute 'σ_Cz' : Real = 29.057750463592832;
                                attribute Ixx : Real = 0.38467490654491604;
                                attribute 'σ_Ixx' : Real = 0.37074144170588635;
                                attribute Iyy : Real = 0.4135284416805727;
                                attribute 'σ_Iyy' : Real = 0.3723953238821935;
                                attribute Izz : Real = 0.42745379410190576;
                                attribute 'σ_Izz' : Real = 0.37017423652493897;
                                attribute Ixy : Real = 0.01747201067888183;
                                attribute 'σ_Ixy' : Real = 0.02351283871158888;
                                attribute Ixz : Real = 0.004078329259058244;
                                attribute 'σ_Ixz' : Real = 0.022566176940390956;
                                attribute Iyz : Real = -0.003093103025726222;
                                attribute 'σ_Iyz' : Real = 0.02209918015384651;
                            }
                            part <'C.1.1.4.1.2.2.4'> 'Part 522' {
                                attribute POIconv : String = "+";
                                attribute Ipoint : Boolean = false;
                                attribute mass : Real = 0.18107663277769462;
                                attribute 'σ_mass' : Real = 0.28909372274994966;
                                attribute Cx : Real = -48.79382927902043;
                                attribute 'σ_Cx' : Real = 28.721044428837228;
                                attribute Cy : Real = -37.45818850584328;
                                attribute 'σ_Cy' : Real = 28.23690002309109;
                                attribute Cz : Real = 5.572905112057924;
                                attribute 'σ_Cz' : Real = 29.057750463592832;
                                attribute Ixx : Real = 0.2328714827508313;
                                attribute 'σ_Ixx' : Real = 0.37074144170588635;
                                attribute Iyy : Real = 0.2604739659824552;
                                attribute 'σ_Iyy' : Real = 0.3723953238821935;
                                attribute Izz : Real = 0.23155667554441034;
                                attribute 'σ_Izz' : Real = 0.37017423652493897;
                                attribute Ixy : Real = -0.01654653336893626;
                                attribute 'σ_Ixy' : Real = 0.02351283871158888;
                                attribute Ixz : Real = 0.012686905446272614;
                                attribute 'σ_Ixz' : Real = 0.022566176940390956;
                                attribute Iyz : Real = -0.006469262526130462;
                                attribute 'σ_Iyz' : Real = 0.02209918015384651;
                            }
                            part <'C.1.1.4.1.2.2.5'> 'Part 523' {
                                attribute POIconv : String = "+";
                                attribute Ipoint : Boolean = false;
                                attribute mass : Real = 0.3826614941461012;
                                attribute 'σ_mass' : Real = 0.28909372274994966;
                                attribute Cx : Real = -64.55197799950838;
                                attribute 'σ_Cx' : Real = 28.721044428837228;
                                attribute Cy : Real = -44.15359911508858;
                                attribute 'σ_Cy' : Real = 28.23690002309109;
                                attribute Cz : Real = -27.46795155107975;
                                attribute 'σ_Cz' : Real = 29.057750463592832;
                                attribute Ixx : Real = 0.5602413092688002;
                                attribute 'σ_Ixx' : Real = 0.37074144170588635;
                                attribute Iyy : Real = 0.5295045602444619;
                                attribute 'σ_Iyy' : Real = 0.3723953238821935;
                                attribute Izz : Real = 0.5264923557380612;
                                attribute 'σ_Izz' : Real = 0.37017423652493897;
                                attribute Ixy : Real = 0.03884203471140327;
                                attribute 'σ_Ixy' : Real = 0.02351283871158888;
                                attribute Ixz : Real = 0.026965996211844034;
                                attribute 'σ_Ixz' : Real = 0.022566176940390956;
                                attribute Iyz : Real = -0.01463950706222535;
                                attribute 'σ_Iyz' : Real = 0.02209918015384651;
                            }
                        }
                        part <'C.1.1.4.1.2.3'> 'Subassembly 153' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.1.2.3.1'> 'Part 524' {
                                attribute POIconv : String = "+";
                                attribute Ipoint : Boolean = false;
                                attribute mass : Real = 0.6760756892520003;
                                attribute 'σ_mass' : Real = 0.28909372274994966;
                                attribute Cx : Real = -48.60744355246425;
                                attribute 'σ_Cx' : Real = 28.721044428837228;
                                attribute Cy : Real = 1.9151626620441675;
                                attribute 'σ_Cy' : Real = 28.23690002309109;
                                attribute Cz : Real = -81.41932506114244;
                                attribute 'σ_Cz' : Real = 29.057750463592832;
                                attribute Ixx : Real = 0.7201907668695394;
                                attribute 'σ_Ixx' : Real = 0.37074144170588635;
                                attribute Iyy : Real = 0.922481063063426;
                                attribute 'σ_Iyy' : Real = 0.3723953238821935;
                                attribute Izz : Real = 0.8243393060295088;
                                attribute 'σ_Izz' : Real = 0.37017423652493897;
                                attribute Ixy : Real = -0.005033514329887098;
                                attribute 'σ_Ixy' : Real = 0.02351283871158888;
                                attribute Ixz : Real = 0.00998159031917946;
                                attribute 'σ_Ixz' : Real = 0.022566176940390956;
                                attribute Iyz : Real = 0.002482970801378602;
                                attribute 'σ_Iyz' : Real = 0.02209918015384651;
                            }
                            part <'C.1.1.4.1.2.3.2'> 'Part 525' {
                                attribute POIconv : String = "+";
                                attribute Ipoint : Boolean = false;
                                attribute mass : Real = 0.7991010712103452;
                                attribute 'σ_mass' : Real = 0.28909372274994966;
                                attribute Cx : Real = 33.9585923589766;
                                attribute 'σ_Cx' : Real = 28.721044428837228;
                                attribute Cy : Real = 17.71317757666111;
                                attribute 'σ_Cy' : Real = 28.23690002309109;
                                attribute Cz : Real = 22.58733408525586;
                                attribute 'σ_Cz' : Real = 29.057750463592832;
                                attribute Ixx : Real = 0.9998229199778262;
                                attribute 'σ_Ixx' : Real = 0.37074144170588635;
                                attribute Iyy : Real = 0.8945321315626844;
                                attribute 'σ_Iyy' : Real = 0.3723953238821935;
                                attribute Izz : Real = 0.8637840937328598;
                                attribute 'σ_Izz' : Real = 0.37017423652493897;
                                attribute Ixy : Real = 0.009636668893692189;
                                attribute 'σ_Ixy' : Real = 0.02351283871158888;
                                attribute Ixz : Real = -0.05779031517671056;
                                attribute 'σ_Ixz' : Real = 0.022566176940390956;
                                attribute Iyz : Real = -0.018506995438087405;
                                attribute 'σ_Iyz' : Real = 0.02209918015384651;
                            }
                            part <'C.1.1.4.1.2.3.3'> 'Part 526' {
                                attribute POIconv : String = "-";
                                attribute Ipoint : Boolean = false;
                                attribute mass : Real = 0.9110064355321229;
                                attribute 'σ_mass' : Real = 0.28909372274994966;
                                attribute Cx : Real = -94.47562443092465;
                                attribute 'σ_Cx' : Real = 28.721044428837228;
                                attribute Cy : Real = -90.03030015155673;
                                attribute 'σ_Cy' : Real = 28.23690002309109;
                                attribute Cz : Real = -1.1231498327106237;
                                attribute 'σ_Cz' : Real = 29.057750463592832;
                                attribute Ixx : Real = 1.096439154251778;
                                attribute 'σ_Ixx' : Real = 0.37074144170588635;
                                attribute Iyy : Real = 0.8712155216492115;
                                attribute 'σ_Iyy' : Real = 0.3723953238821935;
                                attribute Izz : Real = 1.0668016034817485;
                                attribute 'σ_Izz' : Real = 0.37017423652493897;
                                attribute Ixy : Real = -0.038325947877435616;
                                attribute 'σ_Ixy' : Real = 0.02351283871158888;
                                attribute Ixz : Real = -0.03377123354790197;
                                attribute 'σ_Ixz' : Real = 0.022566176940390956;
                                attribute Iyz : Real = -0.08827234052661215;
                                attribute 'σ_Iyz' : Real = 0.02209918015384651;
                            }
                            part <'C.1.1.4.1.2.3.4'> 'Part 527' {
                                attribute POIconv : String = "+";
                                attribute Ipoint : Boolean = false;
                                attribute mass : Real = 0.8071762318208348;
                                attribute 'σ_mass' : Real = 0.28909372274994966;
                                attribute Cx : Real = -37.0194410905242;
                                attribute 'σ_Cx' : Real = 28.721044428837228;
                                attribute Cy : Real = 76.13122160546482;
                                attribute 'σ_Cy' : Real = 28.23690002309109;
                                attribute Cz : Real = 0.8116914425045252;
                                attribute 'σ_Cz' : Real = 29.057750463592832;
                                attribute Ixx : Real = 1.1201184169649436;
                                attribute 'σ_Ixx' : Real = 0.37074144170588635;
                                attribute Iyy : Real = 1.1614061531548077;
                                attribute 'σ_Iyy' : Real = 0.3723953238821935;
                                attribute Izz : Real = 1.1666480153913994;
                                attribute 'σ_Izz' : Real = 0.37017423652493897;
                                attribute Ixy : Real = -0.036721524236853285;
                                attribute 'σ_Ixy' : Real = 0.02351283871158888;
                                attribute Ixz : Real = 0.024626946470446755;
                                attribute 'σ_Ixz' : Real = 0.022566176940390956;
                                attribute Iyz : Real = 0.03349693345283089;
                                attribute 'σ_Iyz' : Real = 0.02209918015384651;
                            }
                            part <'C.1.1.4.1.2.3.5'> 'Part 528' {
                                attribute POIconv : String = "+";
                                attribute Ipoint : Boolean = false;
                                attribute mass : Real = 0.7612705053142272;
                                attribute 'σ_mass' : Real = 0.28909372274994966;
                                attribute Cx : Real = 2.145552961155772;
                                attribute 'σ_Cx' : Real = 28.721044428837228;
                                attribute Cy : Real = -39.47928776033223;
                                attribute 'σ_Cy' : Real = 28.23690002309109;
                                attribute Cz : Real = -83.39385520666838;
                                attribute 'σ_Cz' : Real = 29.057750463592832;
                                attribute Ixx : Real = 1.1552668000444546;
                                attribute 'σ_Ixx' : Real = 0.37074144170588635;
                                attribute Iyy : Real = 1.206785808894924;
                                attribute 'σ_Iyy' : Real = 0.3723953238821935;
                                attribute Izz : Real = 1.1756614795846687;
                                attribute 'σ_Izz' : Real = 0.37017423652493897;
                                attribute Ixy : Real = 0.01825743615970654;
                                attribute 'σ_Ixy' : Real = 0.02351283871158888;
                                attribute Ixz : Real = -0.007411964907153561;
                                attribute 'σ_Ixz' : Real = 0.022566176940390956;
                                attribute Iyz : Real = 0.007563782476518617;
                                attribute 'σ_Iyz' : Real = 0.02209918015384651;
                            }
                        }
                    }
                }
                part <'C.1.1.4.2'> 'Subsystem 12' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.4.2.1'> 'Assembly 42' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.2.1.1'> 'Subassembly 154' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.2.1.1.1'> 'Part 529' {
                                attribute POIconv : String = "+";
                                attribute Ipoint : Boolean = false;
                                attribute mass : Real = 0.6284591646608897;
                                attribute 'σ_mass' : Real = 0.28909372274994966;
                                attribute Cx : Real = -83.70220358483493;
                                attribute 'σ_Cx' : Real = 28.721044428837228;
                                attribute Cy : Real = 22.98341770656407;
                                attribute 'σ_Cy' : Real = 28.23690002309109;
                                attribute Cz : Real = -77.08602547645569;
                                attribute 'σ_Cz' : Real = 29.057750463592832;
                                attribute Ixx : Real = 0.7289515272536714;
                                attribute 'σ_Ixx' : Real = 0.37074144170588635;
                                attribute Iyy : Real = 0.8334239015420141;
                                attribute 'σ_Iyy' : Real = 0.3723953238821935;
                                attribute Izz : Real = 0.7199228073363848;
                                attribute 'σ_Izz' : Real = 0.37017423652493897;
                                attribute Ixy : Real = 0.07553193767996923;
                                attribute 'σ_Ixy' : Real = 0.02351283871158888;
                                attribute Ixz : Real = 0.001305894580315578;
                                attribute 'σ_Ixz' : Real = 0.022566176940390956;
                                attribute Iyz : Real = -0.014377140353095685;
                                attribute 'σ_Iyz' : Real = 0.02209918015384651;
                            }
                            part <'C.1.1.4.2.1.1.2'> 'Part 530' {
                                attribute POIconv : String = "-";
                                attribute Ipoint : Boolean = false;
                                attribute mass : Real = 0.9020827550760004;
                                attribute 'σ_mass' : Real = 0.28909372274994966;
                                attribute Cx : Real = -20.45930097810924;
                                attribute 'σ_Cx' : Real = 28.721044428837228;
                                attribute Cy : Real = 68.3692891150713;
                                attribute 'σ_Cy' : Real = 28.23690002309109;
                                attribute Cz : Real = -39.147092029452324;
                                attribute 'σ_Cz' : Real = 29.057750463592832;
                                attribute Ixx : Real = 1.046361233998187;
                                attribute 'σ_Ixx' : Real = 0.37074144170588635;
                                attribute Iyy : Real = 1.0315495523945122;
                                attribute 'σ_Iyy' : Real = 0.3723953238821935;
                                attribute Izz : Real = 0.9627952470400111;
                                attribute 'σ_Izz' : Real = 0.37017423652493897;
                                attribute Ixy : Real = 0.010770943595708456;
                                attribute 'σ_Ixy' : Real = 0.02351283871158888;
                                attribute Ixz : Real = 0.05680548400965103;
                                attribute 'σ_Ixz' : Real = 0.022566176940390956;
                                attribute Iyz : Real = 0.04825170812887449;
                                attribute 'σ_Iyz' : Real = 0.02209918015384651;
                            }
                            part <'C.1.1.4.2.1.1.3'> 'Part 531' {
                                attribute POIconv : String = "+";
                                attribute Ipoint : Boolean = false;
                                attribute mass : Real = 0.6377317892864812;
                                attribute 'σ_mass' : Real = 0.28909372274994966;
                                attribute Cx : Real = -38.39931106194854;
                                attribute 'σ_Cx' : Real = 28.721044428837228;
                                attribute Cy : Real = 91.98016212321818;
                                attribute 'σ_Cy' : Real = 28.23690002309109;
                                attribute Cz : Real = 57.15541415847838;
                                attribute 'σ_Cz' : Real = 29.057750463592832;
                                attribute Ixx : Real = 0.9075033494396808;
                                attribute 'σ_Ixx' : Real = 0.37074144170588635;
                                attribute Iyy : Real = 0.9017053980353069;
                                attribute 'σ_Iyy' : Real = 0.3723953238821935;
                                attribute Izz : Real = 0.8867787444231682;
                                attribute 'σ_Izz' : Real = 0.37017423652493897;
                                attribute Ixy : Real = 0.002319907716101171;
                                attribute 'σ_Ixy' : Real = 0.02351283871158888;
                                attribute Ixz : Real = 0.0016200842797732954;
                                attribute 'σ_Ixz' : Real = 0.022566176940390956;
                                attribute Iyz : Real = 0.003408526271620471;
                                attribute 'σ_Iyz' : Real = 0.02209918015384651;
                            }
                            part <'C.1.1.4.2.1.1.4'> 'Part 532' {
                                attribute POIconv : String = "+";
                                attribute Ipoint : Boolean = false;
                                attribute mass : Real = 0.462340191899566;
                                attribute 'σ_mass' : Real = 0.28909372274994966;
                                attribute Cx : Real = 22.843413753435016;
                                attribute 'σ_Cx' : Real = 28.721044428837228;
                                attribute Cy : Real = -74.99502301216125;
                                attribute 'σ_Cy' : Real = 28.23690002309109;
                                attribute Cz : Real = 63.385929726064205;
                                attribute 'σ_Cz' : Real = 29.057750463592832;
                                attribute Ixx : Real = 0.6094834430086261;
                                attribute 'σ_Ixx' : Real = 0.37074144170588635;
                                attribute Iyy : Real = 0.6522789903461221;
                                attribute 'σ_Iyy' : Real = 0.3723953238821935;
                                attribute Izz : Real = 0.6532951422963912;
                                attribute 'σ_Izz' : Real = 0.37017423652493897;
                                attribute Ixy : Real = -6.806878436304592e-4;
                                attribute 'σ_Ixy' : Real = 0.02351283871158888;
                                attribute Ixz : Real = 0.016704705983983804;
                                attribute 'σ_Ixz' : Real = 0.022566176940390956;
                                attribute Iyz : Real = 0.02231075947651505;
                                attribute 'σ_Iyz' : Real = 0.02209918015384651;
                            }
                            part <'C.1.1.4.2.1.1.5'> 'Part 533' {
                                attribute POIconv : String = "+";
                                attribute Ipoint : Boolean = false;
                                attribute mass : Real = 0.1210092596008908;
                                attribute 'σ_mass' : Real = 0.28909372274994966;
                                attribute Cx : Real = -82.14233331382275;
                                attribute 'σ_Cx' : Real = 28.721044428837228;
                                attribute Cy : Real = -7.761460728943348;
                                attribute 'σ_Cy' : Real = 28.23690002309109;
                                attribute Cz : Real = -37.70593642257154;
                                attribute 'σ_Cz' : Real = 29.057750463592832;
                                attribute Ixx : Real = 0.14621557235676333;
                                attribute 'σ_Ixx' : Real = 0.37074144170588635;
                                attribute Iyy : Real = 0.15875580355933167;
                                attribute 'σ_Iyy' : Real = 0.3723953238821935;
                                attribute Izz : Real = 0.1598558902233007;
                                attribute 'σ_Izz' : Real = 0.37017423652493897;
                                attribute Ixy : Real = -0.0013767401604286532;
                                attribute 'σ_Ixy' : Real = 0.02351283871158888;
                                attribute Ixz : Real = -0.006732267851022406;
                                attribute 'σ_Ixz' : Real = 0.022566176940390956;
                                attribute Iyz : Real = 0.0042305014789834694;
                                attribute 'σ_Iyz' : Real = 0.02209918015384651;
                            }
                        }
                        part <'C.1.1.4.2.1.2'> 'Subassembly 155' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.2.1.2.1'> 'Part 534' {
                                attribute POIconv : String = "+";
                                attribute Ipoint : Boolean = false;
                                attribute mass : Real = 0.4657461544717662;
                                attribute 'σ_mass' : Real = 0.28909372274994966;
                                attribute Cx : Real = 5.800252268090844;
                                attribute 'σ_Cx' : Real = 28.721044428837228;
                                attribute Cy : Real = -72.93368326500058;
                                attribute 'σ_Cy' : Real = 28.23690002309109;
                                attribute Cz : Real = -25.423532770946622;
                                attribute 'σ_Cz' : Real = 29.057750463592832;
                                attribute Ixx : Real = 0.5480583530158745;
                                attribute 'σ_Ixx' : Real = 0.37074144170588635;
                                attribute Iyy : Real = 0.5033229840496285;
                                attribute 'σ_Iyy' : Real = 0.3723953238821935;
                                attribute Izz : Real = 0.523754412413112;
                                attribute 'σ_Izz' : Real = 0.37017423652493897;
                                attribute Ixy : Real = -0.02342975070662707;
                                attribute 'σ_Ixy' : Real = 0.02351283871158888;
                                attribute Ixz : Real = -0.02320241428108455;
                                attribute 'σ_Ixz' : Real = 0.022566176940390956;
                                attribute Iyz : Real = 0.059725708379910356;
                                attribute 'σ_Iyz' : Real = 0.02209918015384651;
                            }
                            part <'C.1.1.4.2.1.2.2'> 'Part 535' {
                                attribute POIconv : String = "-";
                                attribute Ipoint : Boolean = false;
                                attribute mass : Real = 0.708368724582484;
                                attribute 'σ_mass' : Real = 0.28909372274994966;
                                attribute Cx : Real = -2.962869079783559;
                                attribute 'σ_Cx' : Real = 28.721044428837228;
                                attribute Cy : Real = -18.834841949865222;
                                attribute 'σ_Cy' : Real = 28.23690002309109;
                                attribute Cz : Real = 84.76543403230608;
                                attribute 'σ_Cz' : Real = 29.057750463592832;
                                attribute Ixx : Real = 0.9557488699156569;
                                attribute 'σ_Ixx' : Real = 0.37074144170588635;
                                attribute Iyy : Real = 0.9478724504228753;
                                attribute 'σ_Iyy' : Real = 0.3723953238821935;
                                attribute Izz : Real = 0.8907177825407292;
                                attribute 'σ_Izz' : Real = 0.37017423652493897;
                                attribute Ixy : Real = 0.0715800352531528;
                                attribute 'σ_Ixy' : Real = 0.02351283871158888;
                                attribute Ixz : Real = 0.07652906918950679;
                                attribute 'σ_Ixz' : Real = 0.022566176940390956;
                                attribute Iyz : Real = -0.011895995890804813;
                                attribute 'σ_Iyz' : Real = 0.02209918015384651;
                            }
                            part <'C.1.1.4.2.1.2.3'> 'Part 536' {
                                attribute POIconv : String = "+";
                                attribute Ipoint : Boolean = false;
                                attribute mass : Real = 0.6628257029645611;
                                attribute 'σ_mass' : Real = 0.28909372274994966;
                                attribute Cx : Real = 35.52412101998925;
                                attribute 'σ_Cx' : Real = 28.721044428837228;
                                attribute Cy : Real = -21.8517092987895;
                                attribute 'σ_Cy' : Real = 28.23690002309109;
                                attribute Cz : Real = -98.48964870907366;
                                attribute 'σ_Cz' : Real = 29.057750463592832;
                                attribute Ixx : Real = 0.9830451768702235;
                                attribute 'σ_Ixx' : Real = 0.37074144170588635;
                                attribute Iyy : Real = 0.9849088532831146;
                                attribute 'σ_Iyy' : Real = 0.3723953238821935;
                                attribute Izz : Real = 0.9842174754763611;
                                attribute 'σ_Izz' : Real = 0.37017423652493897;
                                attribute Ixy : Real = 0.003545144513851524;
                                attribute 'σ_Ixy' : Real = 0.02351283871158888;
                                attribute Ixz : Real = -5.210878980795506e-4;
                                attribute 'σ_Ixz' : Real = 0.022566176940390956;
                                attribute Iyz : Real = -0.0015091910428400648;
                                attribute 'σ_Iyz' : Real = 0.02209918015384651;
                            }
                            part <'C.1.1.4.2.1.2.4'> 'Part 537' {
                                attribute POIconv : String = "+";
                                attribute Ipoint : Boolean = false;
                                attribute mass : Real = 0.9399353961327579;
                                attribute 'σ_mass' : Real = 0.28909372274994966;
                                attribute Cx : Real = 25.65035130828619;
                                attribute 'σ_Cx' : Real = 28.721044428837228;
                                attribute Cy : Real = -68.08663532137871;
                                attribute 'σ_Cy' : Real = 28.23690002309109;
                                attribute Cz : Real = -2.2828385699540377;
                                attribute 'σ_Cz' : Real = 29.057750463592832;
                                attribute Ixx : Real = 1.097678129085793;
                                attribute 'σ_Ixx' : Real = 0.37074144170588635;
                                attribute Iyy : Real = 1.1465270037558788;
                                attribute 'σ_Iyy' : Real = 0.3723953238821935;
                                attribute Izz : Real = 0.9542284492203658;
                                attribute 'σ_Izz' : Real = 0.37017423652493897;
                                attribute Ixy : Real = -0.02442688857373019;
                                attribute 'σ_Ixy' : Real = 0.02351283871158888;
                                attribute Ixz : Real = -0.055751840769548214;
                                attribute 'σ_Ixz' : Real = 0.022566176940390956;
                                attribute Iyz : Real = -0.046223090685541104;
                                attribute 'σ_Iyz' : Real = 0.02209918015384651;
                            }
                        }
                        part <'C.1.1.4.2.1.3'> 'Subassembly 156' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.2.1.3.1'> 'Part 538' {
                                attribute POIconv : String = "-";
                                attribute Ipoint : Boolean = false;
                                attribute mass : Real = 0.7383363500193227;
                                attribute 'σ_mass' : Real = 0.28909372274994966;
                                attribute Cx : Real = -69.464538199827075;
                                attribute 'σ_Cx' : Real = 28.721044428837228;
                                attribute Cy : Real = 55.96396620385349;
                                attribute 'σ_Cy' : Real = 28.23690002309109;
                                attribute Cz : Real = -94.76968771778047;
                                attribute 'σ_Cz' : Real = 29.057750463592832;
                                attribute Ixx : Real = 0.7691287407056433;
                                attribute 'σ_Ixx' : Real = 0.37074144170588635;
                                attribute Iyy : Real = 0.7059330592358886;
                                attribute 'σ_Iyy' : Real = 0.3723953238821935;
                                attribute Izz : Real = 0.7518713933723802;
                                attribute 'σ_Izz' : Real = 0.37017423652493897;
                                attribute Ixy : Real = 0.002617184935424134;
                                attribute 'σ_Ixy' : Real = 0.02351283871158888;
                                attribute Ixz : Real = -0.012043657024025588;
                                attribute 'σ_Ixz' : Real = 0.022566176940390956;
                                attribute Iyz : Real = 0.017934178162199856;
                                attribute 'σ_Iyz' : Real = 0.02209918015384651;
                            }
                            part <'C.1.1.4.2.1.3.2'> 'Part 539' {
                                attribute POIconv : String = "-";
                                attribute Ipoint : Boolean = false;
                                attribute mass : Real = 0.3451222735252231;
                                attribute 'σ_mass' : Real = 0.28909372274994966;
                                attribute Cx : Real = 16.026701079681516;
                                attribute 'σ_Cx' : Real = 28.721044428837228;
                                attribute Cy : Real = 20.043739024549723;
                                attribute 'σ_Cy' : Real = 28.23690002309109;
                                attribute Cz : Real = 61.908615566790104;
                                attribute 'σ_Cz' : Real = 29.057750463592832;
                                attribute Ixx : Real = 0.375324994078699;
                                attribute 'σ_Ixx' : Real = 0.37074144170588635;
                                attribute Iyy : Real = 0.368040021751063;
                                attribute 'σ_Iyy' : Real = 0.3723953238821935;
                                attribute Izz : Real = 0.4115690276752031;
                                attribute 'σ_Izz' : Real = 0.37017423652493897;
                                attribute Ixy : Real = -0.0015055319594046539;
                                attribute 'σ_Ixy' : Real = 0.02351283871158888;
                                attribute Ixz : Real = -0.0026964433776489713;
                                attribute 'σ_Ixz' : Real = 0.022566176940390956;
                                attribute Iyz : Real = 0.008751069413777667;
                                attribute 'σ_Iyz' : Real = 0.02209918015384651;
                            }
                            part <'C.1.1.4.2.1.3.3'> 'Part 540' {
                                attribute POIconv : String = "+";
                                attribute Ipoint : Boolean = false;
                                attribute mass : Real = 0.052552033765474335;
                                attribute 'σ_mass' : Real = 0.28909372274994966;
                                attribute Cx : Real = -64.08582553267479;
                                attribute 'σ_Cx' : Real = 28.721044428837228;
                                attribute Cy : Real = 82.70698431879282;
                                attribute 'σ_Cy' : Real = 28.23690002309109;
                                attribute Cz : Real = -15.889395726844668;
                                attribute 'σ_Cz' : Real = 29.057750463592832;
                                attribute Ixx : Real = 0.06360908333705996;
                                attribute 'σ_Ixx' : Real = 0.37074144170588635;
                                attribute Iyy : Real = 0.06285384151786627;
                                attribute 'σ_Iyy' : Real = 0.3723953238821935;
                                attribute Izz : Real = 0.06517171056053056;
                                attribute 'σ_Izz' : Real = 0.37017423652493897;
                                attribute Ixy : Real = -0.0045690687115205455;
                                attribute 'σ_Ixy' : Real = 0.02351283871158888;
                                attribute Ixz : Real = -0.003387823044323876;
                                attribute 'σ_Ixz' : Real = 0.022566176940390956;
                                attribute Iyz : Real = 0.005779686744971064;
                                attribute 'σ_Iyz' : Real = 0.02209918015384651;
                            }
                            part <'C.1.1.4.2.1.3.4'> 'Part 541' {
                                attribute POIconv : String = "+";
                                attribute Ipoint : Boolean = false;
                                attribute mass : Real = 0.7164267662265338;
                                attribute 'σ_mass' : Real = 0.28909372274994966;
                                attribute Cx : Real = 80.08025335147977;
                                attribute 'σ_Cx' : Real = 28.721044428837228;
                                attribute Cy : Real = -3.715879423543811;
                                attribute 'σ_Cy' : Real = 28.23690002309109;
                                attribute Cz : Real = 61.16606825962663;
                                attribute 'σ_Cz' : Real = 29.057750463592832;
                                attribute Ixx : Real = 0.8430160260796978;
                                attribute 'σ_Ixx' : Real = 0.37074144170588635;
                                attribute Iyy : Real = 0.7708042621553833;
                                attribute 'σ_Iyy' : Real = 0.3723953238821935;
                                attribute Izz : Real = 0.7888681653646481;
                                attribute 'σ_Izz' : Real = 0.37017423652493897;
                                attribute Ixy : Real = -0.0748368805427142;
                                attribute 'σ_Ixy' : Real = 0.02351283871158888;
                                attribute Ixz : Real = -0.01976521840754839;
                                attribute 'σ_Ixz' : Real = 0.022566176940390956;
                                attribute Iyz : Real = 0.04886149207397042;
                                attribute 'σ_Iyz' : Real = 0.02209918015384651;
                            }
                            part <'C.1.1.4.2.1.3.5'> 'Part 542' {
                                attribute POIconv : String = "-";
                                attribute Ipoint : Boolean = false;
                                attribute mass : Real = 0.2785438962986227;
                                attribute 'σ_mass' : Real = 0.28909372274994966;
                                attribute Cx : Real = -22.489386424422264;
                                attribute 'σ_Cx' : Real = 28.721044428837228;
                                attribute Cy : Real = -45.85138885304332;
                                attribute 'σ_Cy' : Real = 28.23690002309109;
                                attribute Cz : Real = 5.043858662247658;
                                attribute 'σ_Cz' : Real = 29.057750463592832;
                                attribute Ixx : Real = 0.32740854031804395;
                                attribute 'σ_Ixx' : Real = 0.37074144170588635;
                                attribute Iyy : Real = 0.313891588789434;
                                attribute 'σ_Iyy' : Real = 0.3723953238821935;
                                attribute Izz : Real = 0.3250402143584981;
                                attribute 'σ_Izz' : Real = 0.37017423652493897;
                                attribute Ixy : Real = -0.009300320141077572;
                                attribute 'σ_Ixy' : Real = 0.02351283871158888;
                                attribute Ixz : Real = -0.014073114757763489;
                                attribute 'σ_Ixz' : Real = 0.022566176940390956;
                                attribute Iyz : Real = -0.008192898554829096;
                                attribute 'σ_Iyz' : Real = 0.02209918015384651;
                            }
                        }
                        part <'C.1.1.4.2.1.4'> 'Subassembly 157' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.2.1.4.1'> 'Part 543' {
                                attribute POIconv : String = "+";
                                attribute Ipoint : Boolean = false;
                                attribute mass : Real = 0.6805268835944589;
                                attribute 'σ_mass' : Real = 0.28909372274994966;
                                attribute Cx : Real = -99.55102046951652;
                                attribute 'σ_Cx' : Real = 28.721044428837228;
                                attribute Cy : Real = 88.09943278320134;
                                attribute 'σ_Cy' : Real = 28.23690002309109;
                                attribute Cz : Real = -26.05195203796029;
                                attribute 'σ_Cz' : Real = 29.057750463592832;
                                attribute Ixx : Real = 0.8353861292482151;
                                attribute 'σ_Ixx' : Real = 0.37074144170588635;
                                attribute Iyy : Real = 0.8298846727665306;
                                attribute 'σ_Iyy' : Real = 0.3723953238821935;
                                attribute Izz : Real = 0.87564849004982;
                                attribute 'σ_Izz' : Real = 0.37017423652493897;
                                attribute Ixy : Real = 0.017574295771792432;
                                attribute 'σ_Ixy' : Real = 0.02351283871158888;
                                attribute Ixz : Real = -7.373827787249098e-4;
                                attribute 'σ_Ixz' : Real = 0.022566176940390956;
                                attribute Iyz : Real = -0.0011680976378086743;
                                attribute 'σ_Iyz' : Real = 0.02209918015384651;
                            }
                            part <'C.1.1.4.2.1.4.2'> 'Part 544' {
                                attribute POIconv : String = "-";
                                attribute Ipoint : Boolean = false;
                                attribute mass : Real = 0.2165224535432644;
                                attribute 'σ_mass' : Real = 0.28909372274994966;
                                attribute Cx : Real = -51.99009836651385;
                                attribute 'σ_Cx' : Real = 28.721044428837228;
                                attribute Cy : Real = -57.73820839822292;
                                attribute 'σ_Cy' : Real = 28.23690002309109;
                                attribute Cz : Real = -99.54786384478211;
                                attribute 'σ_Cz' : Real = 29.057750463592832;
                                attribute Ixx : Real = 0.28376107568454423;
                                attribute 'σ_Ixx' : Real = 0.37074144170588635;
                                attribute Iyy : Real = 0.30767209346058827;
                                attribute 'σ_Iyy' : Real = 0.3723953238821935;
                                attribute Izz : Real = 0.2622591836229972;
                                attribute 'σ_Izz' : Real = 0.37017423652493897;
                                attribute Ixy : Real = -0.007219193944532361;
                                attribute 'σ_Ixy' : Real = 0.02351283871158888;
                                attribute Ixz : Real = 0.012428906731383332;
                                attribute 'σ_Ixz' : Real = 0.022566176940390956;
                                attribute Iyz : Real = -0.012101320503557035;
                                attribute 'σ_Iyz' : Real = 0.02209918015384651;
                            }
                            part <'C.1.1.4.2.1.4.3'> 'Part 545' {
                                attribute POIconv : String = "-";
                                attribute Ipoint : Boolean = false;
                                attribute mass : Real = 0.4018748601465486;
                                attribute 'σ_mass' : Real = 0.28909372274994966;
                                attribute Cx : Real = -53.06802932173014;
                                attribute 'σ_Cx' : Real = 28.721044428837228;
                                attribute Cy : Real = 47.127873031422496;
                                attribute 'σ_Cy' : Real = 28.23690002309109;
                                attribute Cz : Real = -36.10486467368901;
                                attribute 'σ_Cz' : Real = 29.057750463592832;
                                attribute Ixx : Real = 0.5553258955821561;
                                attribute 'σ_Ixx' : Real = 0.37074144170588635;
                                attribute Iyy : Real = 0.5007267768773431;
                                attribute 'σ_Iyy' : Real = 0.3723953238821935;
                                attribute Izz : Real = 0.506531662518624;
                                attribute 'σ_Izz' : Real = 0.37017423652493897;
                                attribute Ixy : Real = -0.05634551638548464;
                                attribute 'σ_Ixy' : Real = 0.02351283871158888;
                                attribute Ixz : Real = 0.024153508237850934;
                                attribute 'σ_Ixz' : Real = 0.022566176940390956;
                                attribute Iyz : Real = 0.02393250925198019;
                                attribute 'σ_Iyz' : Real = 0.02209918015384651;
                            }
                        }
                    }
                    part <'C.1.1.4.2.2'> 'Assembly 43' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.2.2.1'> 'Subassembly 158' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.2.2.1.1'> 'Part 546' {
                                attribute POIconv : String = "-";
                                attribute Ipoint : Boolean = false;
                                attribute mass : Real = 0.25636351422360165;
                                attribute 'σ_mass' : Real = 0.28909372274994966;
                                attribute Cx : Real = 16.567286243662238;
                                attribute 'σ_Cx' : Real = 28.721044428837228;
                                attribute Cy : Real = -25.547335715964437;
                                attribute 'σ_Cy' : Real = 28.23690002309109;
                                attribute Cz : Real = 29.57569658756256;
                                attribute 'σ_Cz' : Real = 29.057750463592832;
                                attribute Ixx : Real = 0.304352013479283;
                                attribute 'σ_Ixx' : Real = 0.37074144170588635;
                                attribute Iyy : Real = 0.2688870682151256;
                                attribute 'σ_Iyy' : Real = 0.3723953238821935;
                                attribute Izz : Real = 0.31801408114176444;
                                attribute 'σ_Izz' : Real = 0.37017423652493897;
                                attribute Ixy : Real = 0.04057703859762528;
                                attribute 'σ_Ixy' : Real = 0.02351283871158888;
                                attribute Ixz : Real = 0.004149136417418268;
                                attribute 'σ_Ixz' : Real = 0.022566176940390956;
                                attribute Iyz : Real = -0.010230417881111144;
                                attribute 'σ_Iyz' : Real = 0.02209918015384651;
                            }
                            part <'C.1.1.4.2.2.1.2'> 'Part 547' {
                                attribute POIconv : String = "+";
                                attribute Ipoint : Boolean = false;
                                attribute mass : Real = 0.4265429007196799;
                                attribute 'σ_mass' : Real = 0.28909372274994966;
                                attribute Cx : Real = -94.37498175539076;
                                attribute 'σ_Cx' : Real = 28.721044428837228;
                                attribute Cy : Real = -7.771098846569657;
                                attribute 'σ_Cy' : Real = 28.23690002309109;
                                attribute Cz : Real = -82.91450361721218;
                                attribute 'σ_Cz' : Real = 29.057750463592832;
                                attribute Ixx : Real = 0.5306955308005038;
                                attribute 'σ_Ixx' : Real = 0.37074144170588635;
                                attribute Iyy : Real = 0.5304025783148245;
                                attribute 'σ_Iyy' : Real = 0.3723953238821935;
                                attribute Izz : Real = 0.4667624810250703;
                                attribute 'σ_Izz' : Real = 0.37017423652493897;
                                attribute Ixy : Real = 0.026647985301828984;
                                attribute 'σ_Ixy' : Real = 0.02351283871158888;
                                attribute Ixz : Real = -0.05231512571603075;
                                attribute 'σ_Ixz' : Real = 0.022566176940390956;
                                attribute Iyz : Real = -0.03131181646354376;
                                attribute 'σ_Iyz' : Real = 0.02209918015384651;
                            }
                            part <'C.1.1.4.2.2.1.3'> 'Part 548' {
                                attribute POIconv : String = "-";
                                attribute Ipoint : Boolean = false;
                                attribute mass : Real = 0.07483926034369506;
                                attribute 'σ_mass' : Real = 0.28909372274994966;
                                attribute Cx : Real = -50.029705138877034;
                                attribute 'σ_Cx' : Real = 28.721044428837228;
                                attribute Cy : Real = 18.062815396115184;
                                attribute 'σ_Cy' : Real = 28.23690002309109;
                                attribute Cz : Real = -41.40526936389506;
                                attribute 'σ_Cz' : Real = 29.057750463592832;
                                attribute Ixx : Real = 0.09031389749193572;
                                attribute 'σ_Ixx' : Real = 0.37074144170588635;
                                attribute Iyy : Real = 0.10456432226114966;
                                attribute 'σ_Iyy' : Real = 0.3723953238821935;
                                attribute Izz : Real = 0.09110165943614627;
                                attribute 'σ_Izz' : Real = 0.37017423652493897;
                                attribute Ixy : Real = -0.010910682490777191;
                                attribute 'σ_Ixy' : Real = 0.02351283871158888;
                                attribute Ixz : Real = -0.006770658948247846;
                                attribute 'σ_Ixz' : Real = 0.022566176940390956;
                                attribute Iyz : Real = -3.697602270605658e-7;
                                attribute 'σ_Iyz' : Real = 0.02209918015384651;
                            }
                            part <'C.1.1.4.2.2.1.4'> 'Part 549' {
                                attribute POIconv : String = "+";
                                attribute Ipoint : Boolean = false;
                                attribute mass : Real = 0.7654017967197578;
                                attribute 'σ_mass' : Real = 0.28909372274994966;
                                attribute Cx : Real = -37.4867572914809;
                                attribute 'σ_Cx' : Real = 28.721044428837228;
                                attribute Cy : Real = -46.64961490780115;
                                attribute 'σ_Cy' : Real = 28.23690002309109;
                                attribute Cz : Real = 86.91031346097589;
                                attribute 'σ_Cz' : Real = 29.057750463592832;
                                attribute Ixx : Real = 1.025983105500719;
                                attribute 'σ_Ixx' : Real = 0.37074144170588635;
                                attribute Iyy : Real = 0.9522094112097353;
                                attribute 'σ_Iyy' : Real = 0.3723953238821935;
                                attribute Izz : Real = 1.1253164273782172;
                                attribute 'σ_Izz' : Real = 0.37017423652493897;
                                attribute Ixy : Real = -0.02816918943121456;
                                attribute 'σ_Ixy' : Real = 0.02351283871158888;
                                attribute Ixz : Real = -0.022442803188690328;
                                attribute 'σ_Ixz' : Real = 0.022566176940390956;
                                attribute Iyz : Real = 0.04084812667436109;
                                attribute 'σ_Iyz' : Real = 0.02209918015384651;
                            }
                        }
                        part <'C.1.1.4.2.2.2'> 'Subassembly 159' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.2.2.2.1'> 'Part 550' {
                                attribute POIconv : String = "+";
                                attribute Ipoint : Boolean = false;
                                attribute mass : Real = 0.5870577115502674;
                                attribute 'σ_mass' : Real = 0.28909372274994966;
                                attribute Cx : Real = -67.26254322566092;
                                attribute 'σ_Cx' : Real = 28.721044428837228;
                                attribute Cy : Real = -38.265931187197566;
                                attribute 'σ_Cy' : Real = 28.23690002309109;
                                attribute Cz : Real = -50.29050302691758;
                                attribute 'σ_Cz' : Real = 29.057750463592832;
                                attribute Ixx : Real = 0.9474624115586364;
                                attribute 'σ_Ixx' : Real = 0.37074144170588635;
                                attribute Iyy : Real = 0.9292519126193977;
                                attribute 'σ_Iyy' : Real = 0.3723953238821935;
                                attribute Izz : Real = 0.9060865628793592;
                                attribute 'σ_Izz' : Real = 0.37017423652493897;
                                attribute Ixy : Real = 0.03298156795088358;
                                attribute 'σ_Ixy' : Real = 0.02351283871158888;
                                attribute Ixz : Real = 0.004370402340443938;
                                attribute 'σ_Ixz' : Real = 0.022566176940390956;
                                attribute Iyz : Real = -0.005939288031687957;
                                attribute 'σ_Iyz' : Real = 0.02209918015384651;
                            }
                            part <'C.1.1.4.2.2.2.2'> 'Part 551' {
                                attribute POIconv : String = "-";
                                attribute Ipoint : Boolean = false;
                                attribute mass : Real = 0.8029823325271718;
                                attribute 'σ_mass' : Real = 0.28909372274994966;
                                attribute Cx : Real = -62.90370328351855;
                                attribute 'σ_Cx' : Real = 28.721044428837228;
                                attribute Cy : Real = -28.55105842463672;
                                attribute 'σ_Cy' : Real = 28.23690002309109;
                                attribute Cz : Real = 96.41939611174166;
                                attribute 'σ_Cz' : Real = 29.057750463592832;
                                attribute Ixx : Real = 0.9374900921613957;
                                attribute 'σ_Ixx' : Real = 0.37074144170588635;
                                attribute Iyy : Real = 0.9804289116120805;
                                attribute 'σ_Iyy' : Real = 0.3723953238821935;
                                attribute Izz : Real = 0.9499191182170574;
                                attribute 'σ_Izz' : Real = 0.37017423652493897;
                                attribute Ixy : Real = -0.06876600890451912;
                                attribute 'σ_Ixy' : Real = 0.02351283871158888;
                                attribute Ixz : Real = 0.05487835049668996;
                                attribute 'σ_Ixz' : Real = 0.022566176940390956;
                                attribute Iyz : Real = -0.07923946599343144;
                                attribute 'σ_Iyz' : Real = 0.02209918015384651;
                            }
                            part <'C.1.1.4.2.2.2.3'> 'Part 552' {
                                attribute POIconv : String = "-";
                                attribute Ipoint : Boolean = false;
                                attribute mass : Real = 0.552696571841836;
                                attribute 'σ_mass' : Real = 0.28909372274994966;
                                attribute Cx : Real = -61.351537657901645;
                                attribute 'σ_Cx' : Real = 28.721044428837228;
                                attribute Cy : Real = 60.49366411752999;
                                attribute 'σ_Cy' : Real = 28.23690002309109;
                                attribute Cz : Real = 31.701836129650474;
                                attribute 'σ_Cz' : Real = 29.057750463592832;
                                attribute Ixx : Real = 0.68733282373598;
                                attribute 'σ_Ixx' : Real = 0.37074144170588635;
                                attribute Iyy : Real = 0.6772730218494515;
                                attribute 'σ_Iyy' : Real = 0.3723953238821935;
                                attribute Izz : Real = 0.6441308233078188;
                                attribute 'σ_Izz' : Real = 0.37017423652493897;
                                attribute Ixy : Real = -0.02291490719414696;
                                attribute 'σ_Ixy' : Real = 0.02351283871158888;
                                attribute Ixz : Real = -0.00406134666606856;
                                attribute 'σ_Ixz' : Real = 0.022566176940390956;
                                attribute Iyz : Real = 0.013507009809684462;
                                attribute 'σ_Iyz' : Real = 0.02209918015384651;
                            }
                            part <'C.1.1.4.2.2.2.4'> 'Part 553' {
                                attribute POIconv : String = "-";
                                attribute Ipoint : Boolean = false;
                                attribute mass : Real = 0.22820158980274574;
                                attribute 'σ_mass' : Real = 0.28909372274994966;
                                attribute Cx : Real = -98.28789196908474;
                                attribute 'σ_Cx' : Real = 28.721044428837228;
                                attribute Cy : Real = -57.99896940588951;
                                attribute 'σ_Cy' : Real = 28.23690002309109;
                                attribute Cz : Real = 3.299996303394437;
                                attribute 'σ_Cz' : Real = 29.057750463592832;
                                attribute Ixx : Real = 0.27265577626979587;
                                attribute 'σ_Ixx' : Real = 0.37074144170588635;
                                attribute Iyy : Real = 0.2583815740212346;
                                attribute 'σ_Iyy' : Real = 0.3723953238821935;
                                attribute Izz : Real = 0.2448786297821035;
                                attribute 'σ_Izz' : Real = 0.37017423652493897;
                                attribute Ixy : Real = 0.020159222194703827;
                                attribute 'σ_Ixy' : Real = 0.02351283871158888;
                                attribute Ixz : Real = -0.02437106528308207;
                                attribute 'σ_Ixz' : Real = 0.022566176940390956;
                                attribute Iyz : Real = 0.037826121537472016;
                                attribute 'σ_Iyz' : Real = 0.02209918015384651;
                            }
                        }
                    }
                    part <'C.1.1.4.2.3'> 'Assembly 44' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.2.3.1'> 'Subassembly 160' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.2.3.1.1'> 'Part 554' {
                                attribute POIconv : String = "+";
                                attribute Ipoint : Boolean = false;
                                attribute mass : Real = 0.6390874491217546;
                                attribute 'σ_mass' : Real = 0.28909372274994966;
                                attribute Cx : Real = 44.47537660598755;
                                attribute 'σ_Cx' : Real = 28.721044428837228;
                                attribute Cy : Real = 77.97959730960429;
                                attribute 'σ_Cy' : Real = 28.23690002309109;
                                attribute Cz : Real = -36.490082601085305;
                                attribute 'σ_Cz' : Real = 29.057750463592832;
                                attribute Ixx : Real = 0.5718513319100267;
                                attribute 'σ_Ixx' : Real = 0.37074144170588635;
                                attribute Iyy : Real = 0.593640463540544;
                                attribute 'σ_Iyy' : Real = 0.3723953238821935;
                                attribute Izz : Real = 0.595917365410761;
                                attribute 'σ_Izz' : Real = 0.37017423652493897;
                                attribute Ixy : Real = -0.024137199261449593;
                                attribute 'σ_Ixy' : Real = 0.02351283871158888;
                                attribute Ixz : Real = 0.01996523645553008;
                                attribute 'σ_Ixz' : Real = 0.022566176940390956;
                                attribute Iyz : Real = -0.011746420250287628;
                                attribute 'σ_Iyz' : Real = 0.02209918015384651;
                            }
                            part <'C.1.1.4.2.3.1.2'> 'Part 555' {
                                attribute POIconv : String = "+";
                                attribute Ipoint : Boolean = false;
                                attribute mass : Real = 0.6867221168074756;
                                attribute 'σ_mass' : Real = 0.28909372274994966;
                                attribute Cx : Real = -10.688582994043827;
                                attribute 'σ_Cx' : Real = 28.721044428837228;
                                attribute Cy : Real = 23.70650079101324;
                                attribute 'σ_Cy' : Real = 28.23690002309109;
                                attribute Cz : Real = -79.03767903335392;
                                attribute 'σ_Cz' : Real = 29.057750463592832;
                                attribute Ixx : Real = 0.9231429596934091;
                                attribute 'σ_Ixx' : Real = 0.37074144170588635;
                                attribute Iyy : Real = 0.9236895947026476;
                                attribute 'σ_Iyy' : Real = 0.3723953238821935;
                                attribute Izz : Real = 0.9285492114978481;
                                attribute 'σ_Izz' : Real = 0.37017423652493897;
                                attribute Ixy : Real = 0.005315808831326371;
                                attribute 'σ_Ixy' : Real = 0.02351283871158888;
                                attribute Ixz : Real = -0.021973862324148163;
                                attribute 'σ_Ixz' : Real = 0.022566176940390956;
                                attribute Iyz : Real = 0.013402329831122786;
                                attribute 'σ_Iyz' : Real = 0.02209918015384651;
                            }
                            part <'C.1.1.4.2.3.1.3'> 'Part 556' {
                                attribute POIconv : String = "+";
                                attribute Ipoint : Boolean = false;
                                attribute mass : Real = 0.7489517897311598;
                                attribute 'σ_mass' : Real = 0.28909372274994966;
                                attribute Cx : Real = -1.8283696379512548;
                                attribute 'σ_Cx' : Real = 28.721044428837228;
                                attribute Cy : Real = 28.59921739436686;
                                attribute 'σ_Cy' : Real = 28.23690002309109;
                                attribute Cz : Real = -5.588723905384541;
                                attribute 'σ_Cz' : Real = 29.057750463592832;
                                attribute Ixx : Real = 0.751780520643569;
                                attribute 'σ_Ixx' : Real = 0.37074144170588635;
                                attribute Iyy : Real = 0.7858954161948697;
                                attribute 'σ_Iyy' : Real = 0.3723953238821935;
                                attribute Izz : Real = 0.7520851906183658;
                                attribute 'σ_Izz' : Real = 0.37017423652493897;
                                attribute Ixy : Real = 0.013360890583591106;
                                attribute 'σ_Ixy' : Real = 0.02351283871158888;
                                attribute Ixz : Real = 0.03372653169667156;
                                attribute 'σ_Ixz' : Real = 0.022566176940390956;
                                attribute Iyz : Real = -0.026624408490709968;
                                attribute 'σ_Iyz' : Real = 0.02209918015384651;
                            }
                            part <'C.1.1.4.2.3.1.4'> 'Part 557' {
                                attribute POIconv : String = "-";
                                attribute Ipoint : Boolean = false;
                                attribute mass : Real = 0.6538818781422451;
                                attribute 'σ_mass' : Real = 0.28909372274994966;
                                attribute Cx : Real = 27.86654271185398;
                                attribute 'σ_Cx' : Real = 28.721044428837228;
                                attribute Cy : Real = -30.13402889482677;
                                attribute 'σ_Cy' : Real = 28.23690002309109;
                                attribute Cz : Real = -31.85533881187439;
                                attribute 'σ_Cz' : Real = 29.057750463592832;
                                attribute Ixx : Real = 0.7845183122916826;
                                attribute 'σ_Ixx' : Real = 0.37074144170588635;
                                attribute Iyy : Real = 0.8793151402722938;
                                attribute 'σ_Iyy' : Real = 0.3723953238821935;
                                attribute Izz : Real = 0.8231047052948112;
                                attribute 'σ_Izz' : Real = 0.37017423652493897;
                                attribute Ixy : Real = -0.05421460090447962;
                                attribute 'σ_Ixy' : Real = 0.02351283871158888;
                                attribute Ixz : Real = 0.03553407384820725;
                                attribute 'σ_Ixz' : Real = 0.022566176940390956;
                                attribute Iyz : Real = 0.03931396092729838;
                                attribute 'σ_Iyz' : Real = 0.02209918015384651;
                            }
                            part <'C.1.1.4.2.3.1.5'> 'Part 558' {
                                attribute POIconv : String = "-";
                                attribute Ipoint : Boolean = false;
                                attribute mass : Real = 0.07703952400782145;
                                attribute 'σ_mass' : Real = 0.28909372274994966;
                                attribute Cx : Real = 91.12650458700955;
                                attribute 'σ_Cx' : Real = 28.721044428837228;
                                attribute Cy : Real = 52.75932983495295;
                                attribute 'σ_Cy' : Real = 28.23690002309109;
                                attribute Cz : Real = 98.83786719292402;
                                attribute 'σ_Cz' : Real = 29.057750463592832;
                                attribute Ixx : Real = 0.09003545196587522;
                                attribute 'σ_Ixx' : Real = 0.37074144170588635;
                                attribute Iyy : Real = 0.09319265062849776;
                                attribute 'σ_Iyy' : Real = 0.3723953238821935;
                                attribute Izz : Real = 0.10503822958214182;
                                attribute 'σ_Izz' : Real = 0.37017423652493897;
                                attribute Ixy : Real = -0.002071234390311979;
                                attribute 'σ_Ixy' : Real = 0.02351283871158888;
                                attribute Ixz : Real = 0.005433185009588266;
                                attribute 'σ_Ixz' : Real = 0.022566176940390956;
                                attribute Iyz : Real = -0.005962003645871171;
                                attribute 'σ_Iyz' : Real = 0.02209918015384651;
                            }
                        }
                        part <'C.1.1.4.2.3.2'> 'Subassembly 161' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.2.3.2.1'> 'Part 559' {
                                attribute POIconv : String = "+";
                                attribute Ipoint : Boolean = false;
                                attribute mass : Real = 0.8591342536716257;
                                attribute 'σ_mass' : Real = 0.28909372274994966;
                                attribute Cx : Real = 41.44640960730612;
                                attribute 'σ_Cx' : Real = 28.721044428837228;
                                attribute Cy : Real = -63.33728148601949;
                                attribute 'σ_Cy' : Real = 28.23690002309109;
                                attribute Cz : Real = 52.37458241172135;
                                attribute 'σ_Cz' : Real = 29.057750463592832;
                                attribute Ixx : Real = 1.0965468854936127;
                                attribute 'σ_Ixx' : Real = 0.37074144170588635;
                                attribute Iyy : Real = 1.0847419509756013;
                                attribute 'σ_Iyy' : Real = 0.3723953238821935;
                                attribute Izz : Real = 1.066529365277042;
                                attribute 'σ_Izz' : Real = 0.37017423652493897;
                                attribute Ixy : Real = -0.01188852046246876;
                                attribute 'σ_Ixy' : Real = 0.02351283871158888;
                                attribute Ixz : Real = 0.005844404768099375;
                                attribute 'σ_Ixz' : Real = 0.022566176940390956;
                                attribute Iyz : Real = 0.028539371019446154;
                                attribute 'σ_Iyz' : Real = 0.02209918015384651;
                            }
                            part <'C.1.1.4.2.3.2.2'> 'Part 560' {
                                attribute POIconv : String = "-";
                                attribute Ipoint : Boolean = false;
                                attribute mass : Real = 0.0049375325427390634;
                                attribute 'σ_mass' : Real = 0.28909372274994966;
                                attribute Cx : Real = 95.65344690345228;
                                attribute 'σ_Cx' : Real = 28.721044428837228;
                                attribute Cy : Real = 83.07131957262754;
                                attribute 'σ_Cy' : Real = 28.23690002309109;
                                attribute Cz : Real = 77.80659068375826;
                                attribute 'σ_Cz' : Real = 29.057750463592832;
                                attribute Ixx : Real = 0.00610876098741308;
                                attribute 'σ_Ixx' : Real = 0.37074144170588635;
                                attribute Iyy : Real = 0.005442463683858844;
                                attribute 'σ_Iyy' : Real = 0.3723953238821935;
                                attribute Izz : Real = 0.006308753217115438;
                                attribute 'σ_Izz' : Real = 0.37017423652493897;
                                attribute Ixy : Real = 1.403527327509397e-4;
                                attribute 'σ_Ixy' : Real = 0.02351283871158888;
                                attribute Ixz : Real = 1.3260319660579889e-5;
                                attribute 'σ_Ixz' : Real = 0.022566176940390956;
                                attribute Iyz : Real = 8.883368461058734e-5;
                                attribute 'σ_Iyz' : Real = 0.02209918015384651;
                            }
                            part <'C.1.1.4.2.3.2.3'> 'Part 561' {
                                attribute POIconv : String = "-";
                                attribute Ipoint : Boolean = false;
                                attribute mass : Real = 0.009036969212582336;
                                attribute 'σ_mass' : Real = 0.28909372274994966;
                                attribute Cx : Real = 40.00760447233915;
                                attribute 'σ_Cx' : Real = 28.721044428837228;
                                attribute Cy : Real = 72.95060381293297;
                                attribute 'σ_Cy' : Real = 28.23690002309109;
                                attribute Cz : Real = 75.86175962351263;
                                attribute 'σ_Cz' : Real = 29.057750463592832;
                                attribute Ixx : Real = 0.01090247294954537;
                                attribute 'σ_Ixx' : Real = 0.37074144170588635;
                                attribute Iyy : Real = 0.012545484649135883;
                                attribute 'σ_Iyy' : Real = 0.3723953238821935;
                                attribute Izz : Real = 0.012485647303607668;
                                attribute 'σ_Izz' : Real = 0.37017423652493897;
                                attribute Ixy : Real = 8.836987982284184e-5;
                                attribute 'σ_Ixy' : Real = 0.02351283871158888;
                                attribute Ixz : Real = 7.419283863169482e-5;
                                attribute 'σ_Ixz' : Real = 0.022566176940390956;
                                attribute Iyz : Real = -1.7849561648082135e-6;
                                attribute 'σ_Iyz' : Real = 0.02209918015384651;
                            }
                            part <'C.1.1.4.2.3.2.4'> 'Part 562' {
                                attribute POIconv : String = "+";
                                attribute Ipoint : Boolean = false;
                                attribute mass : Real = 0.6596703603491187;
                                attribute 'σ_mass' : Real = 0.28909372274994966;
                                attribute Cx : Real = -79.13040807470679;
                                attribute 'σ_Cx' : Real = 28.721044428837228;
                                attribute Cy : Real = -50.16894810833037;
                                attribute 'σ_Cy' : Real = 28.23690002309109;
                                attribute Cz : Real = 52.39933622069657;
                                attribute 'σ_Cz' : Real = 29.057750463592832;
                                attribute Ixx : Real = 0.8684199615390704;
                                attribute 'σ_Ixx' : Real = 0.37074144170588635;
                                attribute Iyy : Real = 0.9679389923495302;
                                attribute 'σ_Iyy' : Real = 0.3723953238821935;
                                attribute Izz : Real = 0.8710903445486811;
                                attribute 'σ_Izz' : Real = 0.37017423652493897;
                                attribute Ixy : Real = 0.04275996013393244;
                                attribute 'σ_Ixy' : Real = 0.02351283871158888;
                                attribute Ixz : Real = 0.038811496128369524;
                                attribute 'σ_Ixz' : Real = 0.022566176940390956;
                                attribute Iyz : Real = 0.022350567648236255;
                                attribute 'σ_Iyz' : Real = 0.02209918015384651;
                            }
                        }
                        part <'C.1.1.4.2.3.3'> 'Subassembly 162' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.2.3.3.1'> 'Part 563' {
                                attribute POIconv : String = "-";
                                attribute Ipoint : Boolean = false;
                                attribute mass : Real = 0.6277585705115926;
                                attribute 'σ_mass' : Real = 0.28909372274994966;
                                attribute Cx : Real = 35.83303205668926;
                                attribute 'σ_Cx' : Real = 28.721044428837228;
                                attribute Cy : Real = -24.605528684332967;
                                attribute 'σ_Cy' : Real = 28.23690002309109;
                                attribute Cz : Real = 13.133471505716443;
                                attribute 'σ_Cz' : Real = 29.057750463592832;
                                attribute Ixx : Real = 0.6588166881277798;
                                attribute 'σ_Ixx' : Real = 0.37074144170588635;
                                attribute Iyy : Real = 0.68855310931017;
                                attribute 'σ_Iyy' : Real = 0.3723953238821935;
                                attribute Izz : Real = 0.747473104081539;
                                attribute 'σ_Izz' : Real = 0.37017423652493897;
                                attribute Ixy : Real = 0.005145008010603911;
                                attribute 'σ_Ixy' : Real = 0.02351283871158888;
                                attribute Ixz : Real = 0.009485129676954314;
                                attribute 'σ_Ixz' : Real = 0.022566176940390956;
                                attribute Iyz : Real = -0.05088716452832105;
                                attribute 'σ_Iyz' : Real = 0.02209918015384651;
                            }
                            part <'C.1.1.4.2.3.3.2'> 'Part 564' {
                                attribute POIconv : String = "+";
                                attribute Ipoint : Boolean = false;
                                attribute mass : Real = 0.6717972078570165;
                                attribute 'σ_mass' : Real = 0.28909372274994966;
                                attribute Cx : Real = -3.6818392109125853;
                                attribute 'σ_Cx' : Real = 28.721044428837228;
                                attribute Cy : Real = -66.98945756070316;
                                attribute 'σ_Cy' : Real = 28.23690002309109;
                                attribute Cz : Real = -63.15990178845823;
                                attribute 'σ_Cz' : Real = 29.057750463592832;
                                attribute Ixx : Real = 0.6848663668307794;
                                attribute 'σ_Ixx' : Real = 0.37074144170588635;
                                attribute Iyy : Real = 0.6865844209665427;
                                attribute 'σ_Iyy' : Real = 0.3723953238821935;
                                attribute Izz : Real = 0.615360991149833;
                                attribute 'σ_Izz' : Real = 0.37017423652493897;
                                attribute Ixy : Real = -0.005363122223356696;
                                attribute 'σ_Ixy' : Real = 0.02351283871158888;
                                attribute Ixz : Real = 0.007347015021025872;
                                attribute 'σ_Ixz' : Real = 0.022566176940390956;
                                attribute Iyz : Real = -0.03821034159040357;
                                attribute 'σ_Iyz' : Real = 0.02209918015384651;
                            }
                            part <'C.1.1.4.2.3.3.3'> 'Part 565' {
                                attribute POIconv : String = "-";
                                attribute Ipoint : Boolean = false;
                                attribute mass : Real = 0.2436396779124625;
                                attribute 'σ_mass' : Real = 0.28909372274994966;
                                attribute Cx : Real = 75.95817060209811;
                                attribute 'σ_Cx' : Real = 28.721044428837228;
                                attribute Cy : Real = 26.662041386589408;
                                attribute 'σ_Cy' : Real = 28.23690002309109;
                                attribute Cz : Real = -42.508628219366074;
                                attribute 'σ_Cz' : Real = 29.057750463592832;
                                attribute Ixx : Real = 0.3299325861738954;
                                attribute 'σ_Ixx' : Real = 0.37074144170588635;
                                attribute Iyy : Real = 0.3223920137726299;
                                attribute 'σ_Iyy' : Real = 0.3723953238821935;
                                attribute Izz : Real = 0.30894218608930507;
                                attribute 'σ_Izz' : Real = 0.37017423652493897;
                                attribute Ixy : Real = 6.379470038580912e-4;
                                attribute 'σ_Ixy' : Real = 0.02351283871158888;
                                attribute Ixz : Real = -0.0010388216119853457;
                                attribute 'σ_Ixz' : Real = 0.022566176940390956;
                                attribute Iyz : Real = 0.001437451576463343;
                                attribute 'σ_Iyz' : Real = 0.02209918015384651;
                            }
                            part <'C.1.1.4.2.3.3.4'> 'Part 566' {
                                attribute POIconv : String = "-";
                                attribute Ipoint : Boolean = false;
                                attribute mass : Real = 0.19961190195451492;
                                attribute 'σ_mass' : Real = 0.28909372274994966;
                                attribute Cx : Real = 23.01814374513924;
                                attribute 'σ_Cx' : Real = 28.721044428837228;
                                attribute Cy : Real = -83.50895131006837;
                                attribute 'σ_Cy' : Real = 28.23690002309109;
                                attribute Cz : Real = 97.36863914877176;
                                attribute 'σ_Cz' : Real = 29.057750463592832;
                                attribute Ixx : Real = 0.2654232912503311;
                                attribute 'σ_Ixx' : Real = 0.37074144170588635;
                                attribute Iyy : Real = 0.27809692576339706;
                                attribute 'σ_Iyy' : Real = 0.3723953238821935;
                                attribute Izz : Real = 0.26425225296215754;
                                attribute 'σ_Izz' : Real = 0.37017423652493897;
                                attribute Ixy : Real = -0.00157327623618214;
                                attribute 'σ_Ixy' : Real = 0.02351283871158888;
                                attribute Ixz : Real = -0.013981965897234766;
                                attribute 'σ_Ixz' : Real = 0.022566176940390956;
                                attribute Iyz : Real = -0.010154826337579002;
                                attribute 'σ_Iyz' : Real = 0.02209918015384651;
                            }
                            part <'C.1.1.4.2.3.3.5'> 'Part 567' {
                                attribute POIconv : String = "-";
                                attribute Ipoint : Boolean = false;
                                attribute mass : Real = 0.16161723364936187;
                                attribute 'σ_mass' : Real = 0.28909372274994966;
                                attribute Cx : Real = -7.608089875429869;
                                attribute 'σ_Cx' : Real = 28.721044428837228;
                                attribute Cy : Real = 79.23393836244941;
                                attribute 'σ_Cy' : Real = 28.23690002309109;
                                attribute Cz : Real = -95.04326554015279;
                                attribute 'σ_Cz' : Real = 29.057750463592832;
                                attribute Ixx : Real = 0.18490934789817873;
                                attribute 'σ_Ixx' : Real = 0.37074144170588635;
                                attribute Iyy : Real = 0.17710767664219454;
                                attribute 'σ_Iyy' : Real = 0.3723953238821935;
                                attribute Izz : Real = 0.17571955929648203;
                                attribute 'σ_Izz' : Real = 0.37017423652493897;
                                attribute Ixy : Real = 0.004375307414183448;
                                attribute 'σ_Ixy' : Real = 0.02351283871158888;
                                attribute Ixz : Real = -0.0020381048765742565;
                                attribute 'σ_Ixz' : Real = 0.022566176940390956;
                                attribute Iyz : Real = 0.014013253837733686;
                                attribute 'σ_Iyz' : Real = 0.02209918015384651;
                            }
                        }
                    }
                }
                part <'C.1.1.4.3'> 'Subsystem 13' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.4.3.1'> 'Assembly 45' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.3.1.1'> 'Subassembly 163' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.1.1.1'> 'Part 568' {
                                attribute POIconv : String = "+";
                                attribute Ipoint : Boolean = false;
                                attribute mass : Real = 0.8065986763322726;
                                attribute 'σ_mass' : Real = 0.28909372274994966;
                                attribute Cx : Real = -10.833349404856563;
                                attribute 'σ_Cx' : Real = 28.721044428837228;
                                attribute Cy : Real = -72.0840894151479;
                                attribute 'σ_Cy' : Real = 28.23690002309109;
                                attribute Cz : Real = -35.41034609079361;
                                attribute 'σ_Cz' : Real = 29.057750463592832;
                                attribute Ixx : Real = 0.8727911528726691;
                                attribute 'σ_Ixx' : Real = 0.37074144170588635;
                                attribute Iyy : Real = 0.8798708728587485;
                                attribute 'σ_Iyy' : Real = 0.3723953238821935;
                                attribute Izz : Real = 0.7773476110004565;
                                attribute 'σ_Izz' : Real = 0.37017423652493897;
                                attribute Ixy : Real = -0.035036843269332915;
                                attribute 'σ_Ixy' : Real = 0.02351283871158888;
                                attribute Ixz : Real = -0.07660405653541293;
                                attribute 'σ_Ixz' : Real = 0.022566176940390956;
                                attribute Iyz : Real = 0.07264522211248191;
                                attribute 'σ_Iyz' : Real = 0.02209918015384651;
                            }
                            part <'C.1.1.4.3.1.1.2'> 'Part 569' {
                                attribute POIconv : String = "-";
                                attribute Ipoint : Boolean = false;
                                attribute mass : Real = 0.6751535173088777;
                                attribute 'σ_mass' : Real = 0.28909372274994966;
                                attribute Cx : Real = -28.28746736049652;
                                attribute 'σ_Cx' : Real = 28.721044428837228;
                                attribute Cy : Real = 53.00339697860181;
                                attribute 'σ_Cy' : Real = 28.23690002309109;
                                attribute Cz : Real = -3.930800361558795;
                                attribute 'σ_Cz' : Real = 29.057750463592832;
                                attribute Ixx : Real = 1.000326475243058;
                                attribute 'σ_Ixx' : Real = 0.37074144170588635;
                                attribute Iyy : Real = 0.826854712009798;
                                attribute 'σ_Iyy' : Real = 0.3723953238821935;
                                attribute Izz : Real = 0.9027142988374947;
                                attribute 'σ_Izz' : Real = 0.37017423652493897;
                                attribute Ixy : Real = 0.03131651596773279;
                                attribute 'σ_Ixy' : Real = 0.02351283871158888;
                                attribute Ixz : Real = 0.07934209751355806;
                                attribute 'σ_Ixz' : Real = 0.022566176940390956;
                                attribute Iyz : Real = 0.016300339201205466;
                                attribute 'σ_Iyz' : Real = 0.02209918015384651;
                            }
                            part <'C.1.1.4.3.1.1.3'> 'Part 570' {
                                attribute POIconv : String = "-";
                                attribute Ipoint : Boolean = false;
                                attribute mass : Real = 0.539346057710005;
                                attribute 'σ_mass' : Real = 0.28909372274994966;
                                attribute Cx : Real = -46.31761037744582;
                                attribute 'σ_Cx' : Real = 28.721044428837228;
                                attribute Cy : Real = 63.228671392425895;
                                attribute 'σ_Cy' : Real = 28.23690002309109;
                                attribute Cz : Real = 66.34975168853998;
                                attribute 'σ_Cz' : Real = 29.057750463592832;
                                attribute Ixx : Real = 0.6057957122756009;
                                attribute 'σ_Ixx' : Real = 0.37074144170588635;
                                attribute Iyy : Real = 0.6535129085354897;
                                attribute 'σ_Iyy' : Real = 0.3723953238821935;
                                attribute Izz : Real = 0.6079532882499885;
                                attribute 'σ_Izz' : Real = 0.37017423652493897;
                                attribute Ixy : Real = -0.023781006496004502;
                                attribute 'σ_Ixy' : Real = 0.02351283871158888;
                                attribute Ixz : Real = 0.011299809443557782;
                                attribute 'σ_Ixz' : Real = 0.022566176940390956;
                                attribute Iyz : Real = 0.00980316885851607;
                                attribute 'σ_Iyz' : Real = 0.02209918015384651;
                            }
                        }
                        part <'C.1.1.4.3.1.2'> 'Subassembly 164' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.1.2.1'> 'Part 571' {
                                attribute POIconv : String = "+";
                                attribute Ipoint : Boolean = false;
                                attribute mass : Real = 0.8712604045490734;
                                attribute 'σ_mass' : Real = 0.28909372274994966;
                                attribute Cx : Real = -62.147762067615986;
                                attribute 'σ_Cx' : Real = 28.721044428837228;
                                attribute Cy : Real = 97.22028323449194;
                                attribute 'σ_Cy' : Real = 28.23690002309109;
                                attribute Cz : Real = -80.98488850519061;
                                attribute 'σ_Cz' : Real = 29.057750463592832;
                                attribute Ixx : Real = 1.2674694936894066;
                                attribute 'σ_Ixx' : Real = 0.37074144170588635;
                                attribute Iyy : Real = 1.3650474460137054;
                                attribute 'σ_Iyy' : Real = 0.3723953238821935;
                                attribute Izz : Real = 1.2578833584376354;
                                attribute 'σ_Izz' : Real = 0.37017423652493897;
                                attribute Ixy : Real = 0.03160772878268484;
                                attribute 'σ_Ixy' : Real = 0.02351283871158888;
                                attribute Ixz : Real = 0.00939403217593755;
                                attribute 'σ_Ixz' : Real = 0.022566176940390956;
                                attribute Iyz : Real = -0.041928482569012854;
                                attribute 'σ_Iyz' : Real = 0.02209918015384651;
                            }
                            part <'C.1.1.4.3.1.2.2'> 'Part 572' {
                                attribute POIconv : String = "-";
                                attribute Ipoint : Boolean = false;
                                attribute mass : Real = 0.16523359280591832;
                                attribute 'σ_mass' : Real = 0.28909372274994966;
                                attribute Cx : Real = 9.646197501569986;
                                attribute 'σ_Cx' : Real = 28.721044428837228;
                                attribute Cy : Real = -10.468652565032244;
                                attribute 'σ_Cy' : Real = 28.23690002309109;
                                attribute Cz : Real = 15.642839716747403;
                                attribute 'σ_Cz' : Real = 29.057750463592832;
                                attribute Ixx : Real = 0.18605388394751585;
                                attribute 'σ_Ixx' : Real = 0.37074144170588635;
                                attribute Iyy : Real = 0.2221832698722716;
                                attribute 'σ_Iyy' : Real = 0.3723953238821935;
                                attribute Izz : Real = 0.21734918475683057;
                                attribute 'σ_Izz' : Real = 0.37017423652493897;
                                attribute Ixy : Real = 0.004220553160068899;
                                attribute 'σ_Ixy' : Real = 0.02351283871158888;
                                attribute Ixz : Real = -0.006009814813861999;
                                attribute 'σ_Ixz' : Real = 0.022566176940390956;
                                attribute Iyz : Real = 0.013788005873994294;
                                attribute 'σ_Iyz' : Real = 0.02209918015384651;
                            }
                        }
                        part <'C.1.1.4.3.1.3'> 'Subassembly 165' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.1.3.1'> 'Part 573' {
                                attribute POIconv : String = "-";
                                attribute Ipoint : Boolean = false;
                                attribute mass : Real = 0.9844077281497885;
                                attribute 'σ_mass' : Real = 0.28909372274994966;
                                attribute Cx : Real = -6.16714246571064;
                                attribute 'σ_Cx' : Real = 28.721044428837228;
                                attribute Cy : Real = -12.968294229358435;
                                attribute 'σ_Cy' : Real = 28.23690002309109;
                                attribute Cz : Real = -6.8360373843461275;
                                attribute 'σ_Cz' : Real = 29.057750463592832;
                                attribute Ixx : Real = 1.097402270270673;
                                attribute 'σ_Ixx' : Real = 0.37074144170588635;
                                attribute Iyy : Real = 1.0169660815939237;
                                attribute 'σ_Iyy' : Real = 0.3723953238821935;
                                attribute Izz : Real = 1.1060157730603195;
                                attribute 'σ_Izz' : Real = 0.37017423652493897;
                                attribute Ixy : Real = 0.05025355058673975;
                                attribute 'σ_Ixy' : Real = 0.02351283871158888;
                                attribute Ixz : Real = -0.010566011771067281;
                                attribute 'σ_Ixz' : Real = 0.022566176940390956;
                                attribute Iyz : Real = 0.11968075547228059;
                                attribute 'σ_Iyz' : Real = 0.02209918015384651;
                            }
                            part <'C.1.1.4.3.1.3.2'> 'Part 574' {
                                attribute POIconv : String = "-";
                                attribute Ipoint : Boolean = false;
                                attribute mass : Real = 0.983066041162936;
                                attribute 'σ_mass' : Real = 0.28909372274994966;
                                attribute Cx : Real = -92.69731459207833;
                                attribute 'σ_Cx' : Real = 28.721044428837228;
                                attribute Cy : Real = -22.00828343629837;
                                attribute 'σ_Cy' : Real = 28.23690002309109;
                                attribute Cz : Real = -83.30649198032916;
                                attribute 'σ_Cz' : Real = 29.057750463592832;
                                attribute Ixx : Real = 1.3075234008202243;
                                attribute 'σ_Ixx' : Real = 0.37074144170588635;
                                attribute Iyy : Real = 1.3908132550135497;
                                attribute 'σ_Iyy' : Real = 0.3723953238821935;
                                attribute Izz : Real = 1.1410880881993417;
                                attribute 'σ_Izz' : Real = 0.37017423652493897;
                                attribute Ixy : Real = -0.01382025968840965;
                                attribute 'σ_Ixy' : Real = 0.02351283871158888;
                                attribute Ixz : Real = 1.4040649634041584e-7;
                                attribute 'σ_Ixz' : Real = 0.022566176940390956;
                                attribute Iyz : Real = 0.0023475482338300895;
                                attribute 'σ_Iyz' : Real = 0.02209918015384651;
                            }
                            part <'C.1.1.4.3.1.3.3'> 'Part 575' {
                                attribute POIconv : String = "+";
                                attribute Ipoint : Boolean = false;
                                attribute mass : Real = 0.26354837158252487;
                                attribute 'σ_mass' : Real = 0.28909372274994966;
                                attribute Cx : Real = -68.0096261203289;
                                attribute 'σ_Cx' : Real = 28.721044428837228;
                                attribute Cy : Real = 19.001063471660018;
                                attribute 'σ_Cy' : Real = 28.23690002309109;
                                attribute Cz : Real = -37.3550059273839;
                                attribute 'σ_Cz' : Real = 29.057750463592832;
                                attribute Ixx : Real = 0.4203564976739275;
                                attribute 'σ_Ixx' : Real = 0.37074144170588635;
                                attribute Iyy : Real = 0.4265443008644212;
                                attribute 'σ_Iyy' : Real = 0.3723953238821935;
                                attribute Izz : Real = 0.41808562670064187;
                                attribute 'σ_Izz' : Real = 0.37017423652493897;
                                attribute Ixy : Real = -0.002530499115762736;
                                attribute 'σ_Ixy' : Real = 0.02351283871158888;
                                attribute Ixz : Real = -0.003561421436528379;
                                attribute 'σ_Ixz' : Real = 0.022566176940390956;
                                attribute Iyz : Real = -0.002622962972975264;
                                attribute 'σ_Iyz' : Real = 0.02209918015384651;
                            }
                        }
                        part <'C.1.1.4.3.1.4'> 'Subassembly 166' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.1.4.1'> 'Part 576' {
                                attribute POIconv : String = "+";
                                attribute Ipoint : Boolean = false;
                                attribute mass : Real = 0.4552455420200713;
                                attribute 'σ_mass' : Real = 0.28909372274994966;
                                attribute Cx : Real = 47.41039630025625;
                                attribute 'σ_Cx' : Real = 28.721044428837228;
                                attribute Cy : Real = 77.8739676810801;
                                attribute 'σ_Cy' : Real = 28.23690002309109;
                                attribute Cz : Real = 94.13015800528228;
                                attribute 'σ_Cz' : Real = 29.057750463592832;
                                attribute Ixx : Real = 0.5744331515348395;
                                attribute 'σ_Ixx' : Real = 0.37074144170588635;
                                attribute Iyy : Real = 0.5559206481007796;
                                attribute 'σ_Iyy' : Real = 0.3723953238821935;
                                attribute Izz : Real = 0.5726534718639972;
                                attribute 'σ_Izz' : Real = 0.37017423652493897;
                                attribute Ixy : Real = -0.0018468662969857925;
                                attribute 'σ_Ixy' : Real = 0.02351283871158888;
                                attribute Ixz : Real = -0.013806764760521648;
                                attribute 'σ_Ixz' : Real = 0.022566176940390956;
                                attribute Iyz : Real = 0.008184652031829212;
                                attribute 'σ_Iyz' : Real = 0.02209918015384651;
                            }
                            part <'C.1.1.4.3.1.4.2'> 'Part 577' {
                                attribute POIconv : String = "+";
                                attribute Ipoint : Boolean = false;
                                attribute mass : Real = 0.993118840953568;
                                attribute 'σ_mass' : Real = 0.28909372274994966;
                                attribute Cx : Real = 81.43258169293404;
                                attribute 'σ_Cx' : Real = 28.721044428837228;
                                attribute Cy : Real = 67.84097463823855;
                                attribute 'σ_Cy' : Real = 28.23690002309109;
                                attribute Cz : Real = 71.9372860621661;
                                attribute 'σ_Cz' : Real = 29.057750463592832;
                                attribute Ixx : Real = 1.0854334812130173;
                                attribute 'σ_Ixx' : Real = 0.37074144170588635;
                                attribute Iyy : Real = 1.1455400213171718;
                                attribute 'σ_Iyy' : Real = 0.3723953238821935;
                                attribute Izz : Real = 1.2353600302111918;
                                attribute 'σ_Izz' : Real = 0.37017423652493897;
                                attribute Ixy : Real = -0.11076367568579323;
                                attribute 'σ_Ixy' : Real = 0.02351283871158888;
                                attribute Ixz : Real = -0.02604495772071208;
                                attribute 'σ_Ixz' : Real = 0.022566176940390956;
                                attribute Iyz : Real = 0.011428361884830074;
                                attribute 'σ_Iyz' : Real = 0.02209918015384651;
                            }
                        }
                        part <'C.1.1.4.3.1.5'> 'Subassembly 167' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.1.5.1'> 'Part 578' {
                                attribute POIconv : String = "+";
                                attribute Ipoint : Boolean = false;
                                attribute mass : Real = 0.6317836605468765;
                                attribute 'σ_mass' : Real = 0.28909372274994966;
                                attribute Cx : Real = 64.71298728138208;
                                attribute 'σ_Cx' : Real = 28.721044428837228;
                                attribute Cy : Real = 57.985171442851424;
                                attribute 'σ_Cy' : Real = 28.23690002309109;
                                attribute Cz : Real = -74.4332299567759;
                                attribute 'σ_Cz' : Real = 29.057750463592832;
                                attribute Ixx : Real = 0.8302302590252909;
                                attribute 'σ_Ixx' : Real = 0.37074144170588635;
                                attribute Iyy : Real = 0.7929546916747786;
                                attribute 'σ_Iyy' : Real = 0.3723953238821935;
                                attribute Izz : Real = 0.7824910653845862;
                                attribute 'σ_Izz' : Real = 0.37017423652493897;
                                attribute Ixy : Real = -0.0262613785025231;
                                attribute 'σ_Ixy' : Real = 0.02351283871158888;
                                attribute Ixz : Real = 0.007174324060803509;
                                attribute 'σ_Ixz' : Real = 0.022566176940390956;
                                attribute Iyz : Real = 0.003659208346762329;
                                attribute 'σ_Iyz' : Real = 0.02209918015384651;
                            }
                            part <'C.1.1.4.3.1.5.2'> 'Part 579' {
                                attribute POIconv : String = "-";
                                attribute Ipoint : Boolean = false;
                                attribute mass : Real = 0.9080223237508908;
                                attribute 'σ_mass' : Real = 0.28909372274994966;
                                attribute Cx : Real = 99.20267998240888;
                                attribute 'σ_Cx' : Real = 28.721044428837228;
                                attribute Cy : Real = -56.72974172048271;
                                attribute 'σ_Cy' : Real = 28.23690002309109;
                                attribute Cz : Real = 54.70510870218277;
                                attribute 'σ_Cz' : Real = 29.057750463592832;
                                attribute Ixx : Real = 1.3429724114963764;
                                attribute 'σ_Ixx' : Real = 0.37074144170588635;
                                attribute Iyy : Real = 1.2701845229348838;
                                attribute 'σ_Iyy' : Real = 0.3723953238821935;
                                attribute Izz : Real = 1.2709593863106332;
                                attribute 'σ_Izz' : Real = 0.37017423652493897;
                                attribute Ixy : Real = 0.03478001377515316;
                                attribute 'σ_Ixy' : Real = 0.02351283871158888;
                                attribute Ixz : Real = 0.004313622161004088;
                                attribute 'σ_Ixz' : Real = 0.022566176940390956;
                                attribute Iyz : Real = -0.027748598271113045;
                                attribute 'σ_Iyz' : Real = 0.02209918015384651;
                            }
                        }
                    }
                    part <'C.1.1.4.3.2'> 'Assembly 46' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.3.2.1'> 'Subassembly 168' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.2.1.1'> 'Part 580' {
                                attribute POIconv : String = "-";
                                attribute Ipoint : Boolean = false;
                                attribute mass : Real = 0.7358381890321616;
                                attribute 'σ_mass' : Real = 0.28909372274994966;
                                attribute Cx : Real = 85.55333097465336;
                                attribute 'σ_Cx' : Real = 28.721044428837228;
                                attribute Cy : Real = 99.2712639272213;
                                attribute 'σ_Cy' : Real = 28.23690002309109;
                                attribute Cz : Real = 93.73734663240612;
                                attribute 'σ_Cz' : Real = 29.057750463592832;
                                attribute Ixx : Real = 0.9293189078969663;
                                attribute 'σ_Ixx' : Real = 0.37074144170588635;
                                attribute Iyy : Real = 0.8943825958847074;
                                attribute 'σ_Iyy' : Real = 0.3723953238821935;
                                attribute Izz : Real = 0.863344267161111;
                                attribute 'σ_Izz' : Real = 0.37017423652493897;
                                attribute Ixy : Real = 0.025021063246738313;
                                attribute 'σ_Ixy' : Real = 0.02351283871158888;
                                attribute Ixz : Real = -0.04068541962047893;
                                attribute 'σ_Ixz' : Real = 0.022566176940390956;
                                attribute Iyz : Real = 0.06691461668440601;
                                attribute 'σ_Iyz' : Real = 0.02209918015384651;
                            }
                            part <'C.1.1.4.3.2.1.2'> 'Part 581' {
                                attribute POIconv : String = "+";
                                attribute Ipoint : Boolean = false;
                                attribute mass : Real = 0.18177427060878837;
                                attribute 'σ_mass' : Real = 0.28909372274994966;
                                attribute Cx : Real = 88.75071117654443;
                                attribute 'σ_Cx' : Real = 28.721044428837228;
                                attribute Cy : Real = -75.4959904588759;
                                attribute 'σ_Cy' : Real = 28.23690002309109;
                                attribute Cz : Real = 45.786814112216234;
                                attribute 'σ_Cz' : Real = 29.057750463592832;
                                attribute Ixx : Real = 0.2159100735788343;
                                attribute 'σ_Ixx' : Real = 0.37074144170588635;
                                attribute Iyy : Real = 0.24185380993458014;
                                attribute 'σ_Iyy' : Real = 0.3723953238821935;
                                attribute Izz : Real = 0.18853456525796025;
                                attribute 'σ_Izz' : Real = 0.37017423652493897;
                                attribute Ixy : Real = -1.1197166823510621e-4;
                                attribute 'σ_Ixy' : Real = 0.02351283871158888;
                                attribute Ixz : Real = 0.0035915518035626428;
                                attribute 'σ_Ixz' : Real = 0.022566176940390956;
                                attribute Iyz : Real = -0.009848288424389305;
                                attribute 'σ_Iyz' : Real = 0.02209918015384651;
                            }
                        }
                        part <'C.1.1.4.3.2.2'> 'Subassembly 169' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.2.2.1'> 'Part 582' {
                                attribute POIconv : String = "+";
                                attribute Ipoint : Boolean = false;
                                attribute mass : Real = 0.8669420333269517;
                                attribute 'σ_mass' : Real = 0.28909372274994966;
                                attribute Cx : Real = -72.9844493791461;
                                attribute 'σ_Cx' : Real = 28.721044428837228;
                                attribute Cy : Real = -54.542559292167425;
                                attribute 'σ_Cy' : Real = 28.23690002309109;
                                attribute Cz : Real = -37.68028072081506;
                                attribute 'σ_Cz' : Real = 29.057750463592832;
                                attribute Ixx : Real = 1.0705245710311226;
                                attribute 'σ_Ixx' : Real = 0.37074144170588635;
                                attribute Iyy : Real = 1.07576171874703;
                                attribute 'σ_Iyy' : Real = 0.3723953238821935;
                                attribute Izz : Real = 1.3660182309242799;
                                attribute 'σ_Izz' : Real = 0.37017423652493897;
                                attribute Ixy : Real = 0.0053437163424603085;
                                attribute 'σ_Ixy' : Real = 0.02351283871158888;
                                attribute Ixz : Real = -0.023459772690525932;
                                attribute 'σ_Ixz' : Real = 0.022566176940390956;
                                attribute Iyz : Real = 0.043790615525153134;
                                attribute 'σ_Iyz' : Real = 0.02209918015384651;
                            }
                            part <'C.1.1.4.3.2.2.2'> 'Part 583' {
                                attribute POIconv : String = "+";
                                attribute Ipoint : Boolean = false;
                                attribute mass : Real = 0.3446949692459311;
                                attribute 'σ_mass' : Real = 0.28909372274994966;
                                attribute Cx : Real = 62.88189422339201;
                                attribute 'σ_Cx' : Real = 28.721044428837228;
                                attribute Cy : Real = 56.431751465424895;
                                attribute 'σ_Cy' : Real = 28.23690002309109;
                                attribute Cz : Real = 25.264057470485568;
                                attribute 'σ_Cz' : Real = 29.057750463592832;
                                attribute Ixx : Real = 0.502299963161536;
                                attribute 'σ_Ixx' : Real = 0.37074144170588635;
                                attribute Iyy : Real = 0.5115285741510668;
                                attribute 'σ_Iyy' : Real = 0.3723953238821935;
                                attribute Izz : Real = 0.5015946308286685;
                                attribute 'σ_Izz' : Real = 0.37017423652493897;
                                attribute Ixy : Real = 0.002704509236806771;
                                attribute 'σ_Ixy' : Real = 0.02351283871158888;
                                attribute Ixz : Real = 0.0027625676506873014;
                                attribute 'σ_Ixz' : Real = 0.022566176940390956;
                                attribute Iyz : Real = -0.010183550308785271;
                                attribute 'σ_Iyz' : Real = 0.02209918015384651;
                            }
                            part <'C.1.1.4.3.2.2.3'> 'Part 584' {
                                attribute POIconv : String = "+";
                                attribute Ipoint : Boolean = false;
                                attribute mass : Real = 0.9991648010311183;
                                attribute 'σ_mass' : Real = 0.28909372274994966;
                                attribute Cx : Real = -36.093724658712745;
                                attribute 'σ_Cx' : Real = 28.721044428837228;
                                attribute Cy : Real = -42.64837778173387;
                                attribute 'σ_Cy' : Real = 28.23690002309109;
                                attribute Cz : Real = 6.684871204197407;
                                attribute 'σ_Cz' : Real = 29.057750463592832;
                                attribute Ixx : Real = 0.9764572606991789;
                                attribute 'σ_Ixx' : Real = 0.37074144170588635;
                                attribute Iyy : Real = 0.9168374543124701;
                                attribute 'σ_Iyy' : Real = 0.3723953238821935;
                                attribute Izz : Real = 0.9441844556800005;
                                attribute 'σ_Izz' : Real = 0.37017423652493897;
                                attribute Ixy : Real = -0.022605669214486538;
                                attribute 'σ_Ixy' : Real = 0.02351283871158888;
                                attribute Ixz : Real = -0.0014970573623820506;
                                attribute 'σ_Ixz' : Real = 0.022566176940390956;
                                attribute Iyz : Real = 3.67879143992848e-4;
                                attribute 'σ_Iyz' : Real = 0.02209918015384651;
                            }
                            part <'C.1.1.4.3.2.2.4'> 'Part 585' {
                                attribute POIconv : String = "-";
                                attribute Ipoint : Boolean = false;
                                attribute mass : Real = 0.22930727002304047;
                                attribute 'σ_mass' : Real = 0.28909372274994966;
                                attribute Cx : Real = 10.920222429558635;
                                attribute 'σ_Cx' : Real = 28.721044428837228;
                                attribute Cy : Real = 9.986065980046988;
                                attribute 'σ_Cy' : Real = 28.23690002309109;
                                attribute Cz : Real = 35.70701773278415;
                                attribute 'σ_Cz' : Real = 29.057750463592832;
                                attribute Ixx : Real = 0.35489902247098315;
                                attribute 'σ_Ixx' : Real = 0.37074144170588635;
                                attribute Iyy : Real = 0.3703487215093558;
                                attribute 'σ_Iyy' : Real = 0.3723953238821935;
                                attribute Izz : Real = 0.35977977300296343;
                                attribute 'σ_Izz' : Real = 0.37017423652493897;
                                attribute Ixy : Real = -0.0021077304500223383;
                                attribute 'σ_Ixy' : Real = 0.02351283871158888;
                                attribute Ixz : Real = -4.4862380427924946e-5;
                                attribute 'σ_Ixz' : Real = 0.022566176940390956;
                                attribute Iyz : Real = 7.855969687733738e-5;
                                attribute 'σ_Iyz' : Real = 0.02209918015384651;
                            }
                            part <'C.1.1.4.3.2.2.5'> 'Part 586' {
                                attribute POIconv : String = "-";
                                attribute Ipoint : Boolean = false;
                                attribute mass : Real = 0.9041953575089574;
                                attribute 'σ_mass' : Real = 0.28909372274994966;
                                attribute Cx : Real = 15.210539009422064;
                                attribute 'σ_Cx' : Real = 28.721044428837228;
                                attribute Cy : Real = -33.36887317709625;
                                attribute 'σ_Cy' : Real = 28.23690002309109;
                                attribute Cz : Real = 25.635775830596685;
                                attribute 'σ_Cz' : Real = 29.057750463592832;
                                attribute Ixx : Real = 0.9809673462533376;
                                attribute 'σ_Ixx' : Real = 0.37074144170588635;
                                attribute Iyy : Real = 1.0259054973620636;
                                attribute 'σ_Iyy' : Real = 0.3723953238821935;
                                attribute Izz : Real = 0.847084015046195;
                                attribute 'σ_Izz' : Real = 0.37017423652493897;
                                attribute Ixy : Real = -0.01267750919999319;
                                attribute 'σ_Ixy' : Real = 0.02351283871158888;
                                attribute Ixz : Real = 0.01695835079185267;
                                attribute 'σ_Ixz' : Real = 0.022566176940390956;
                                attribute Iyz : Real = 0.01902947869014241;
                                attribute 'σ_Iyz' : Real = 0.02209918015384651;
                            }
                        }
                        part <'C.1.1.4.3.2.3'> 'Subassembly 170' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.2.3.1'> 'Part 587' {
                                attribute POIconv : String = "+";
                                attribute Ipoint : Boolean = false;
                                attribute mass : Real = 0.10974312634416857;
                                attribute 'σ_mass' : Real = 0.28909372274994966;
                                attribute Cx : Real = 37.778127985075116;
                                attribute 'σ_Cx' : Real = 28.721044428837228;
                                attribute Cy : Real = 52.712550619617105;
                                attribute 'σ_Cy' : Real = 28.23690002309109;
                                attribute Cz : Real = 76.85025939717889;
                                attribute 'σ_Cz' : Real = 29.057750463592832;
                                attribute Ixx : Real = 0.14545869476211204;
                                attribute 'σ_Ixx' : Real = 0.37074144170588635;
                                attribute Iyy : Real = 0.14430438866334505;
                                attribute 'σ_Iyy' : Real = 0.3723953238821935;
                                attribute Izz : Real = 0.12410002010498686;
                                attribute 'σ_Izz' : Real = 0.37017423652493897;
                                attribute Ixy : Real = 0.005910819981491447;
                                attribute 'σ_Ixy' : Real = 0.02351283871158888;
                                attribute Ixz : Real = -0.003263841324965932;
                                attribute 'σ_Ixz' : Real = 0.022566176940390956;
                                attribute Iyz : Real = 0.014093329485940678;
                                attribute 'σ_Iyz' : Real = 0.02209918015384651;
                            }
                            part <'C.1.1.4.3.2.3.2'> 'Part 588' {
                                attribute POIconv : String = "-";
                                attribute Ipoint : Boolean = false;
                                attribute mass : Real = 0.45529639883409256;
                                attribute 'σ_mass' : Real = 0.28909372274994966;
                                attribute Cx : Real = -8.79065990447998;
                                attribute 'σ_Cx' : Real = 28.721044428837228;
                                attribute Cy : Real = -0.7168313954025507;
                                attribute 'σ_Cy' : Real = 28.23690002309109;
                                attribute Cz : Real = 49.17320990934968;
                                attribute 'σ_Cz' : Real = 29.057750463592832;
                                attribute Ixx : Real = 0.634628509404182;
                                attribute 'σ_Ixx' : Real = 0.37074144170588635;
                                attribute Iyy : Real = 0.6096522944332439;
                                attribute 'σ_Iyy' : Real = 0.3723953238821935;
                                attribute Izz : Real = 0.6198715692581757;
                                attribute 'σ_Izz' : Real = 0.37017423652493897;
                                attribute Ixy : Real = -0.015789449918281604;
                                attribute 'σ_Ixy' : Real = 0.02351283871158888;
                                attribute Ixz : Real = -0.01928378526527994;
                                attribute 'σ_Ixz' : Real = 0.022566176940390956;
                                attribute Iyz : Real = -0.004918880867733209;
                                attribute 'σ_Iyz' : Real = 0.02209918015384651;
                            }
                            part <'C.1.1.4.3.2.3.3'> 'Part 589' {
                                attribute POIconv : String = "+";
                                attribute Ipoint : Boolean = false;
                                attribute mass : Real = 0.28313015251536855;
                                attribute 'σ_mass' : Real = 0.28909372274994966;
                                attribute Cx : Real = 34.413322200998664;
                                attribute 'σ_Cx' : Real = 28.721044428837228;
                                attribute Cy : Real = 57.712893979623914;
                                attribute 'σ_Cy' : Real = 28.23690002309109;
                                attribute Cz : Real = -30.869585927575827;
                                attribute 'σ_Cz' : Real = 29.057750463592832;
                                attribute Ixx : Real = 0.3952854533412433;
                                attribute 'σ_Ixx' : Real = 0.37074144170588635;
                                attribute Iyy : Real = 0.36342049563386675;
                                attribute 'σ_Iyy' : Real = 0.3723953238821935;
                                attribute Izz : Real = 0.3540532777624591;
                                attribute 'σ_Izz' : Real = 0.37017423652493897;
                                attribute Ixy : Real = -0.0118354610617851;
                                attribute 'σ_Ixy' : Real = 0.02351283871158888;
                                attribute Ixz : Real = 0.03769667273417954;
                                attribute 'σ_Ixz' : Real = 0.022566176940390956;
                                attribute Iyz : Real = -0.010576398360564832;
                                attribute 'σ_Iyz' : Real = 0.02209918015384651;
                            }
                            part <'C.1.1.4.3.2.3.4'> 'Part 590' {
                                attribute POIconv : String = "-";
                                attribute Ipoint : Boolean = false;
                                attribute mass : Real = 0.641334931537509;
                                attribute 'σ_mass' : Real = 0.28909372274994966;
                                attribute Cx : Real = 79.2581157758832;
                                attribute 'σ_Cx' : Real = 28.721044428837228;
                                attribute Cy : Real = -33.784930128604174;
                                attribute 'σ_Cy' : Real = 28.23690002309109;
                                attribute Cz : Real = -47.89508325047791;
                                attribute 'σ_Cz' : Real = 29.057750463592832;
                                attribute Ixx : Real = 0.6793592097573864;
                                attribute 'σ_Ixx' : Real = 0.37074144170588635;
                                attribute Iyy : Real = 0.607680210556734;
                                attribute 'σ_Iyy' : Real = 0.3723953238821935;
                                attribute Izz : Real = 0.6978975407343123;
                                attribute 'σ_Izz' : Real = 0.37017423652493897;
                                attribute Ixy : Real = -0.0050337870014808325;
                                attribute 'σ_Ixy' : Real = 0.02351283871158888;
                                attribute Ixz : Real = 0.009546757024649747;
                                attribute 'σ_Ixz' : Real = 0.022566176940390956;
                                attribute Iyz : Real = 0.007302995440491721;
                                attribute 'σ_Iyz' : Real = 0.02209918015384651;
                            }
                            part <'C.1.1.4.3.2.3.5'> 'Part 591' {
                                attribute POIconv : String = "+";
                                attribute Ipoint : Boolean = false;
                                attribute mass : Real = 0.5268292204269673;
                                attribute 'σ_mass' : Real = 0.28909372274994966;
                                attribute Cx : Real = -36.02099670097232;
                                attribute 'σ_Cx' : Real = 28.721044428837228;
                                attribute Cy : Real = -3.2584079541265965;
                                attribute 'σ_Cy' : Real = 28.23690002309109;
                                attribute Cz : Real = -57.79769471846521;
                                attribute 'σ_Cz' : Real = 29.057750463592832;
                                attribute Ixx : Real = 0.5152005969782072;
                                attribute 'σ_Ixx' : Real = 0.37074144170588635;
                                attribute Iyy : Real = 0.5003554709795122;
                                attribute 'σ_Iyy' : Real = 0.3723953238821935;
                                attribute Izz : Real = 0.4651185688899954;
                                attribute 'σ_Izz' : Real = 0.37017423652493897;
                                attribute Ixy : Real = -0.00515238008314637;
                                attribute 'σ_Ixy' : Real = 0.02351283871158888;
                                attribute Ixz : Real = 0.011558711851901134;
                                attribute 'σ_Ixz' : Real = 0.022566176940390956;
                                attribute Iyz : Real = -0.014553249124662052;
                                attribute 'σ_Iyz' : Real = 0.02209918015384651;
                            }
                        }
                        part <'C.1.1.4.3.2.4'> 'Subassembly 171' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.2.4.1'> 'Part 592' {
                                attribute POIconv : String = "-";
                                attribute Ipoint : Boolean = false;
                                attribute mass : Real = 0.6222756587970071;
                                attribute 'σ_mass' : Real = 0.28909372274994966;
                                attribute Cx : Real = -41.583311930298805;
                                attribute 'σ_Cx' : Real = 28.721044428837228;
                                attribute Cy : Real = 15.35527459345758;
                                attribute 'σ_Cy' : Real = 28.23690002309109;
                                attribute Cz : Real = -97.60544435121119;
                                attribute 'σ_Cz' : Real = 29.057750463592832;
                                attribute Ixx : Real = 0.7633877135686887;
                                attribute 'σ_Ixx' : Real = 0.37074144170588635;
                                attribute Iyy : Real = 0.7326336942129332;
                                attribute 'σ_Iyy' : Real = 0.3723953238821935;
                                attribute Izz : Real = 0.6974698235665074;
                                attribute 'σ_Izz' : Real = 0.37017423652493897;
                                attribute Ixy : Real = 0.020541241309192344;
                                attribute 'σ_Ixy' : Real = 0.02351283871158888;
                                attribute Ixz : Real = 0.02252378312326079;
                                attribute 'σ_Ixz' : Real = 0.022566176940390956;
                                attribute Iyz : Real = 0.06140045773560951;
                                attribute 'σ_Iyz' : Real = 0.02209918015384651;
                            }
                            part <'C.1.1.4.3.2.4.2'> 'Part 593' {
                                attribute POIconv : String = "+";
                                attribute Ipoint : Boolean = false;
                                attribute mass : Real = 0.6343683958356269;
                                attribute 'σ_mass' : Real = 0.28909372274994966;
                                attribute Cx : Real = -20.117552764713764;
                                attribute 'σ_Cx' : Real = 28.721044428837228;
                                attribute Cy : Real = 17.424153303727508;
                                attribute 'σ_Cy' : Real = 28.23690002309109;
                                attribute Cz : Real = -3.173608426004648;
                                attribute 'σ_Cz' : Real = 29.057750463592832;
                                attribute Ixx : Real = 0.7160316039069908;
                                attribute 'σ_Ixx' : Real = 0.37074144170588635;
                                attribute Iyy : Real = 0.8192711213122226;
                                attribute 'σ_Iyy' : Real = 0.3723953238821935;
                                attribute Izz : Real = 0.7582056512860335;
                                attribute 'σ_Izz' : Real = 0.37017423652493897;
                                attribute Ixy : Real = -0.09059207532236102;
                                attribute 'σ_Ixy' : Real = 0.02351283871158888;
                                attribute Ixz : Real = -0.006717858152166623;
                                attribute 'σ_Ixz' : Real = 0.022566176940390956;
                                attribute Iyz : Real = -0.022894753323617713;
                                attribute 'σ_Iyz' : Real = 0.02209918015384651;
                            }
                            part <'C.1.1.4.3.2.4.3'> 'Part 594' {
                                attribute POIconv : String = "+";
                                attribute Ipoint : Boolean = false;
                                attribute mass : Real = 0.44397627799678596;
                                attribute 'σ_mass' : Real = 0.28909372274994966;
                                attribute Cx : Real = 75.66130026243627;
                                attribute 'σ_Cx' : Real = 28.721044428837228;
                                attribute Cy : Real = 24.1464264690876;
                                attribute 'σ_Cy' : Real = 28.23690002309109;
                                attribute Cz : Real = -37.03067544847727;
                                attribute 'σ_Cz' : Real = 29.057750463592832;
                                attribute Ixx : Real = 0.6070584513632067;
                                attribute 'σ_Ixx' : Real = 0.37074144170588635;
                                attribute Iyy : Real = 0.5748620740549539;
                                attribute 'σ_Iyy' : Real = 0.3723953238821935;
                                attribute Izz : Real = 0.47742288035191494;
                                attribute 'σ_Izz' : Real = 0.37017423652493897;
                                attribute Ixy : Real = 0.026180467016522532;
                                attribute 'σ_Ixy' : Real = 0.02351283871158888;
                                attribute Ixz : Real = 0.008559906189002825;
                                attribute 'σ_Ixz' : Real = 0.022566176940390956;
                                attribute Iyz : Real = 0.04092632033875103;
                                attribute 'σ_Iyz' : Real = 0.02209918015384651;
                            }
                        }
                        part <'C.1.1.4.3.2.5'> 'Subassembly 172' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.2.5.1'> 'Part 595' {
                                attribute POIconv : String = "-";
                                attribute Ipoint : Boolean = false;
                                attribute mass : Real = 0.21141506774141453;
                                attribute 'σ_mass' : Real = 0.28909372274994966;
                                attribute Cx : Real = -61.93469692952931;
                                attribute 'σ_Cx' : Real = 28.721044428837228;
                                attribute Cy : Real = 34.88537222146988;
                                attribute 'σ_Cy' : Real = 28.23690002309109;
                                attribute Cz : Real = -62.02297578565776;
                                attribute 'σ_Cz' : Real = 29.057750463592832;
                                attribute Ixx : Real = 0.21155481802466644;
                                attribute 'σ_Ixx' : Real = 0.37074144170588635;
                                attribute Iyy : Real = 0.19162972423682545;
                                attribute 'σ_Iyy' : Real = 0.3723953238821935;
                                attribute Izz : Real = 0.20454667459509468;
                                attribute 'σ_Izz' : Real = 0.37017423652493897;
                                attribute Ixy : Real = -0.0045764944922120215;
                                attribute 'σ_Ixy' : Real = 0.02351283871158888;
                                attribute Ixz : Real = -0.0028316954538534387;
                                attribute 'σ_Ixz' : Real = 0.022566176940390956;
                                attribute Iyz : Real = -0.00448013427923099;
                                attribute 'σ_Iyz' : Real = 0.02209918015384651;
                            }
                            part <'C.1.1.4.3.2.5.2'> 'Part 596' {
                                attribute POIconv : String = "+";
                                attribute Ipoint : Boolean = false;
                                attribute mass : Real = 0.42681109623238445;
                                attribute 'σ_mass' : Real = 0.28909372274994966;
                                attribute Cx : Real = -76.16292117163539;
                                attribute 'σ_Cx' : Real = 28.721044428837228;
                                attribute Cy : Real = -57.035246631130576;
                                attribute 'σ_Cy' : Real = 28.23690002309109;
                                attribute Cz : Real = 42.93741104193032;
                                attribute 'σ_Cz' : Real = 29.057750463592832;
                                attribute Ixx : Real = 0.40125260414341757;
                                attribute 'σ_Ixx' : Real = 0.37074144170588635;
                                attribute Iyy : Real = 0.39643732441148505;
                                attribute 'σ_Iyy' : Real = 0.3723953238821935;
                                attribute Izz : Real = 0.41806574057907264;
                                attribute 'σ_Izz' : Real = 0.37017423652493897;
                                attribute Ixy : Real = 0.0032411073175351583;
                                attribute 'σ_Ixy' : Real = 0.02351283871158888;
                                attribute Ixz : Real = 1.1461311960420589e-4;
                                attribute 'σ_Ixz' : Real = 0.022566176940390956;
                                attribute Iyz : Real = 0.010257559606107608;
                                attribute 'σ_Iyz' : Real = 0.02209918015384651;
                            }
                            part <'C.1.1.4.3.2.5.3'> 'Part 597' {
                                attribute POIconv : String = "+";
                                attribute Ipoint : Boolean = false;
                                attribute mass : Real = 0.14810859161592088;
                                attribute 'σ_mass' : Real = 0.28909372274994966;
                                attribute Cx : Real = -93.7698619440198;
                                attribute 'σ_Cx' : Real = 28.721044428837228;
                                attribute Cy : Real = 87.73533538915217;
                                attribute 'σ_Cy' : Real = 28.23690002309109;
                                attribute Cz : Real = -39.31658072397113;
                                attribute 'σ_Cz' : Real = 29.057750463592832;
                                attribute Ixx : Real = 0.19107249053578962;
                                attribute 'σ_Ixx' : Real = 0.37074144170588635;
                                attribute Iyy : Real = 0.17954552893449496;
                                attribute 'σ_Iyy' : Real = 0.3723953238821935;
                                attribute Izz : Real = 0.19238040576723525;
                                attribute 'σ_Izz' : Real = 0.37017423652493897;
                                attribute Ixy : Real = 0.006368426861721866;
                                attribute 'σ_Ixy' : Real = 0.02351283871158888;
                                attribute Ixz : Real = -0.004160709909507991;
                                attribute 'σ_Ixz' : Real = 0.022566176940390956;
                                attribute Iyz : Real = -0.0016844437592338237;
                                attribute 'σ_Iyz' : Real = 0.02209918015384651;
                            }
                        }
                    }
                    part <'C.1.1.4.3.3'> 'Assembly 47' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.3.3.1'> 'Subassembly 173' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.3.1.1'> 'Part 598' {
                                attribute POIconv : String = "+";
                                attribute Ipoint : Boolean = false;
                                attribute mass : Real = 0.9364393398214598;
                                attribute 'σ_mass' : Real = 0.28909372274994966;
                                attribute Cx : Real = 18.053495464846492;
                                attribute 'σ_Cx' : Real = 28.721044428837228;
                                attribute Cy : Real = 60.10230388492346;
                                attribute 'σ_Cy' : Real = 28.23690002309109;
                                attribute Cz : Real = -36.785451881587505;
                                attribute 'σ_Cz' : Real = 29.057750463592832;
                                attribute Ixx : Real = 1.481118330393314;
                                attribute 'σ_Ixx' : Real = 0.37074144170588635;
                                attribute Iyy : Real = 1.4671997173191935;
                                attribute 'σ_Iyy' : Real = 0.3723953238821935;
                                attribute Izz : Real = 1.4529240368855632;
                                attribute 'σ_Izz' : Real = 0.37017423652493897;
                                attribute Ixy : Real = -0.0034257630175328103;
                                attribute 'σ_Ixy' : Real = 0.02351283871158888;
                                attribute Ixz : Real = -0.008811573143954504;
                                attribute 'σ_Ixz' : Real = 0.022566176940390956;
                                attribute Iyz : Real = 0.03667034175302378;
                                attribute 'σ_Iyz' : Real = 0.02209918015384651;
                            }
                            part <'C.1.1.4.3.3.1.2'> 'Part 599' {
                                attribute POIconv : String = "-";
                                attribute Ipoint : Boolean = false;
                                attribute mass : Real = 0.3504300986316521;
                                attribute 'σ_mass' : Real = 0.28909372274994966;
                                attribute Cx : Real = -95.96335315145552;
                                attribute 'σ_Cx' : Real = 28.721044428837228;
                                attribute Cy : Real = 4.882714664563537;
                                attribute 'σ_Cy' : Real = 28.23690002309109;
                                attribute Cz : Real = 24.19962123967707;
                                attribute 'σ_Cz' : Real = 29.057750463592832;
                                attribute Ixx : Real = 0.44827762874589333;
                                attribute 'σ_Ixx' : Real = 0.37074144170588635;
                                attribute Iyy : Real = 0.4459444848445588;
                                attribute 'σ_Iyy' : Real = 0.3723953238821935;
                                attribute Izz : Real = 0.4109705619947464;
                                attribute 'σ_Izz' : Real = 0.37017423652493897;
                                attribute Ixy : Real = -0.006202891125401592;
                                attribute 'σ_Ixy' : Real = 0.02351283871158888;
                                attribute Ixz : Real = 0.015748807480085586;
                                attribute 'σ_Ixz' : Real = 0.022566176940390956;
                                attribute Iyz : Real = 0.018059685242964262;
                                attribute 'σ_Iyz' : Real = 0.02209918015384651;
                            }
                            part <'C.1.1.4.3.3.1.3'> 'Part 600' {
                                attribute POIconv : String = "-";
                                attribute Ipoint : Boolean = false;
                                attribute mass : Real = 0.16554944202816113;
                                attribute 'σ_mass' : Real = 0.28909372274994966;
                                attribute Cx : Real = 7.517693750560284;
                                attribute 'σ_Cx' : Real = 28.721044428837228;
                                attribute Cy : Real = -48.106974409893155;
                                attribute 'σ_Cy' : Real = 28.23690002309109;
                                attribute Cz : Real = 3.316257568076253;
                                attribute 'σ_Cz' : Real = 29.057750463592832;
                                attribute Ixx : Real = 0.23140397240232954;
                                attribute 'σ_Ixx' : Real = 0.37074144170588635;
                                attribute Iyy : Real = 0.22305672091389891;
                                attribute 'σ_Iyy' : Real = 0.3723953238821935;
                                attribute Izz : Real = 0.21675261238427423;
                                attribute 'σ_Izz' : Real = 0.37017423652493897;
                                attribute Ixy : Real = 2.860452119445841e-4;
                                attribute 'σ_Ixy' : Real = 0.02351283871158888;
                                attribute Ixz : Real = 0.015978375674585703;
                                attribute 'σ_Ixz' : Real = 0.022566176940390956;
                                attribute Iyz : Real = -8.768428067218783e-5;
                                attribute 'σ_Iyz' : Real = 0.02209918015384651;
                            }
                            part <'C.1.1.4.3.3.1.4'> 'Part 601' {
                                attribute POIconv : String = "+";
                                attribute Ipoint : Boolean = false;
                                attribute mass : Real = 0.10452514446899296;
                                attribute 'σ_mass' : Real = 0.28909372274994966;
                                attribute Cx : Real = -74.16816940531135;
                                attribute 'σ_Cx' : Real = 28.721044428837228;
                                attribute Cy : Real = -42.442279448732734;
                                attribute 'σ_Cy' : Real = 28.23690002309109;
                                attribute Cz : Real = 8.191929431632161;
                                attribute 'σ_Cz' : Real = 29.057750463592832;
                                attribute Ixx : Real = 0.11225229261476123;
                                attribute 'σ_Ixx' : Real = 0.37074144170588635;
                                attribute Iyy : Real = 0.11816795145459982;
                                attribute 'σ_Iyy' : Real = 0.3723953238821935;
                                attribute Izz : Real = 0.1288751704164729;
                                attribute 'σ_Izz' : Real = 0.37017423652493897;
                                attribute Ixy : Real = 0.010037411725029779;
                                attribute 'σ_Ixy' : Real = 0.02351283871158888;
                                attribute Ixz : Real = 0.0013012015741664033;
                                attribute 'σ_Ixz' : Real = 0.022566176940390956;
                                attribute Iyz : Real = 7.657993104434903e-4;
                                attribute 'σ_Iyz' : Real = 0.02209918015384651;
                            }
                            part <'C.1.1.4.3.3.1.5'> 'Part 602' {
                                attribute POIconv : String = "+";
                                attribute Ipoint : Boolean = false;
                                attribute mass : Real = 0.4204389826168772;
                                attribute 'σ_mass' : Real = 0.28909372274994966;
                                attribute Cx : Real = 41.86448487453163;
                                attribute 'σ_Cx' : Real = 28.721044428837228;
                                attribute Cy : Real = -90.55250431410968;
                                attribute 'σ_Cy' : Real = 28.23690002309109;
                                attribute Cz : Real = -82.45935449376702;
                                attribute 'σ_Cz' : Real = 29.057750463592832;
                                attribute Ixx : Real = 0.6034603438235938;
                                attribute 'σ_Ixx' : Real = 0.37074144170588635;
                                attribute Iyy : Real = 0.6316481335124572;
                                attribute 'σ_Iyy' : Real = 0.3723953238821935;
                                attribute Izz : Real = 0.5895291890872871;
                                attribute 'σ_Izz' : Real = 0.37017423652493897;
                                attribute Ixy : Real = 0.034116664588859494;
                                attribute 'σ_Ixy' : Real = 0.02351283871158888;
                                attribute Ixz : Real = 0.00896616449497183;
                                attribute 'σ_Ixz' : Real = 0.022566176940390956;
                                attribute Iyz : Real = -0.006897048633327298;
                                attribute 'σ_Iyz' : Real = 0.02209918015384651;
                            }
                        }
                        part <'C.1.1.4.3.3.2'> 'Subassembly 174' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.3.2.1'> 'Part 603' {
                                attribute POIconv : String = "-";
                                attribute Ipoint : Boolean = false;
                                attribute mass : Real = 0.4595927965408191;
                                attribute 'σ_mass' : Real = 0.28909372274994966;
                                attribute Cx : Real = -72.91880464181304;
                                attribute 'σ_Cx' : Real = 28.721044428837228;
                                attribute Cy : Real = -75.09202337823808;
                                attribute 'σ_Cy' : Real = 28.23690002309109;
                                attribute Cz : Real = 99.56393404863775;
                                attribute 'σ_Cz' : Real = 29.057750463592832;
                                attribute Ixx : Real = 0.40720172849512176;
                                attribute 'σ_Ixx' : Real = 0.37074144170588635;
                                attribute Iyy : Real = 0.4332272757671695;
                                attribute 'σ_Iyy' : Real = 0.3723953238821935;
                                attribute Izz : Real = 0.42965699625104203;
                                attribute 'σ_Izz' : Real = 0.37017423652493897;
                                attribute Ixy : Real = 0.0011794358640240476;
                                attribute 'σ_Ixy' : Real = 0.02351283871158888;
                                attribute Ixz : Real = 0.0028523070260651597;
                                attribute 'σ_Ixz' : Real = 0.022566176940390956;
                                attribute Iyz : Real = 0.005890855245595964;
                                attribute 'σ_Iyz' : Real = 0.02209918015384651;
                            }
                            part <'C.1.1.4.3.3.2.2'> 'Part 604' {
                                attribute POIconv : String = "+";
                                attribute Ipoint : Boolean = false;
                                attribute mass : Real = 0.014043472690973433;
                                attribute 'σ_mass' : Real = 0.28909372274994966;
                                attribute Cx : Real = 11.09547521919012;
                                attribute 'σ_Cx' : Real = 28.721044428837228;
                                attribute Cy : Real = 16.28094487823546;
                                attribute 'σ_Cy' : Real = 28.23690002309109;
                                attribute Cz : Real = 44.031385984271765;
                                attribute 'σ_Cz' : Real = 29.057750463592832;
                                attribute Ixx : Real = 0.019047714683683412;
                                attribute 'σ_Ixx' : Real = 0.37074144170588635;
                                attribute Iyy : Real = 0.015894725091493134;
                                attribute 'σ_Iyy' : Real = 0.3723953238821935;
                                attribute Izz : Real = 0.017437816721696097;
                                attribute 'σ_Izz' : Real = 0.37017423652493897;
                                attribute Ixy : Real = 2.28975362489425e-4;
                                attribute 'σ_Ixy' : Real = 0.02351283871158888;
                                attribute Ixz : Real = 7.297890490088315e-4;
                                attribute 'σ_Ixz' : Real = 0.022566176940390956;
                                attribute Iyz : Real = -0.0011976925159597565;
                                attribute 'σ_Iyz' : Real = 0.02209918015384651;
                            }
                            part <'C.1.1.4.3.3.2.3'> 'Part 605' {
                                attribute POIconv : String = "-";
                                attribute Ipoint : Boolean = false;
                                attribute mass : Real = 0.11925877195596694;
                                attribute 'σ_mass' : Real = 0.28909372274994966;
                                attribute Cx : Real = 62.93086241930723;
                                attribute 'σ_Cx' : Real = 28.721044428837228;
                                attribute Cy : Real = 5.970837594941258;
                                attribute 'σ_Cy' : Real = 28.23690002309109;
                                attribute Cz : Real = -73.37302137166262;
                                attribute 'σ_Cz' : Real = 29.057750463592832;
                                attribute Ixx : Real = 0.13997082890234597;
                                attribute 'σ_Ixx' : Real = 0.37074144170588635;
                                attribute Iyy : Real = 0.1386223523515246;
                                attribute 'σ_Iyy' : Real = 0.3723953238821935;
                                attribute Izz : Real = 0.15082960895798023;
                                attribute 'σ_Izz' : Real = 0.37017423652493897;
                                attribute Ixy : Real = -8.83477722562124e-4;
                                attribute 'σ_Ixy' : Real = 0.02351283871158888;
                                attribute Ixz : Real = 0.0015367364212254399;
                                attribute 'σ_Ixz' : Real = 0.022566176940390956;
                                attribute Iyz : Real = 0.0023001925390887783;
                                attribute 'σ_Iyz' : Real = 0.02209918015384651;
                            }
                            part <'C.1.1.4.3.3.2.4'> 'Part 606' {
                                attribute POIconv : String = "-";
                                attribute Ipoint : Boolean = false;
                                attribute mass : Real = 0.8371082595579792;
                                attribute 'σ_mass' : Real = 0.28909372274994966;
                                attribute Cx : Real = 44.634277233853936;
                                attribute 'σ_Cx' : Real = 28.721044428837228;
                                attribute Cy : Real = -90.89736305177212;
                                attribute 'σ_Cy' : Real = 28.23690002309109;
                                attribute Cz : Real = -9.007533174008131;
                                attribute 'σ_Cz' : Real = 29.057750463592832;
                                attribute Ixx : Real = 0.9139273821368273;
                                attribute 'σ_Ixx' : Real = 0.37074144170588635;
                                attribute Iyy : Real = 0.8979005741579907;
                                attribute 'σ_Iyy' : Real = 0.3723953238821935;
                                attribute Izz : Real = 1.0832077165705272;
                                attribute 'σ_Izz' : Real = 0.37017423652493897;
                                attribute Ixy : Real = 1.9820324130290134e-4;
                                attribute 'σ_Ixy' : Real = 0.02351283871158888;
                                attribute Ixz : Real = -0.05103977255612301;
                                attribute 'σ_Ixz' : Real = 0.022566176940390956;
                                attribute Iyz : Real = -0.016637835465993567;
                                attribute 'σ_Iyz' : Real = 0.02209918015384651;
                            }
                        }
                        part <'C.1.1.4.3.3.3'> 'Subassembly 175' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.3.3.1'> 'Part 607' {
                                attribute POIconv : String = "+";
                                attribute Ipoint : Boolean = false;
                                attribute mass : Real = 0.33409749166760594;
                                attribute 'σ_mass' : Real = 0.28909372274994966;
                                attribute Cx : Real = 30.620905896648765;
                                attribute 'σ_Cx' : Real = 28.721044428837228;
                                attribute Cy : Real = -35.56217709556222;
                                attribute 'σ_Cy' : Real = 28.23690002309109;
                                attribute Cz : Real = -93.64090203307569;
                                attribute 'σ_Cz' : Real = 29.057750463592832;
                                attribute Ixx : Real = 0.4521524801301306;
                                attribute 'σ_Ixx' : Real = 0.37074144170588635;
                                attribute Iyy : Real = 0.4018983274983767;
                                attribute 'σ_Iyy' : Real = 0.3723953238821935;
                                attribute Izz : Real = 0.38307454046030576;
                                attribute 'σ_Izz' : Real = 0.37017423652493897;
                                attribute Ixy : Real = 0.03010189475768419;
                                attribute 'σ_Ixy' : Real = 0.02351283871158888;
                                attribute Ixz : Real = 0.01041018927097695;
                                attribute 'σ_Ixz' : Real = 0.022566176940390956;
                                attribute Iyz : Real = -0.0016853135406593922;
                                attribute 'σ_Iyz' : Real = 0.02209918015384651;
                            }
                            part <'C.1.1.4.3.3.3.2'> 'Part 608' {
                                attribute POIconv : String = "+";
                                attribute Ipoint : Boolean = false;
                                attribute mass : Real = 0.31380860361410307;
                                attribute 'σ_mass' : Real = 0.28909372274994966;
                                attribute Cx : Real = 40.80463903956115;
                                attribute 'σ_Cx' : Real = 28.721044428837228;
                                attribute Cy : Real = 68.83005886338651;
                                attribute 'σ_Cy' : Real = 28.23690002309109;
                                attribute Cz : Real = 58.59446604736149;
                                attribute 'σ_Cz' : Real = 29.057750463592832;
                                attribute Ixx : Real = 0.5048631354760448;
                                attribute 'σ_Ixx' : Real = 0.37074144170588635;
                                attribute Iyy : Real = 0.46284647589605754;
                                attribute 'σ_Iyy' : Real = 0.3723953238821935;
                                attribute Izz : Real = 0.4600216874064529;
                                attribute 'σ_Izz' : Real = 0.37017423652493897;
                                attribute Ixy : Real = 0.012849075120804406;
                                attribute 'σ_Ixy' : Real = 0.02351283871158888;
                                attribute Ixz : Real = -0.016918620194096044;
                                attribute 'σ_Ixz' : Real = 0.022566176940390956;
                                attribute Iyz : Real = 0.0026309038496957473;
                                attribute 'σ_Iyz' : Real = 0.02209918015384651;
                            }
                            part <'C.1.1.4.3.3.3.3'> 'Part 609' {
                                attribute POIconv : String = "+";
                                attribute Ipoint : Boolean = false;
                                attribute mass : Real = 0.2103283561053686;
                                attribute 'σ_mass' : Real = 0.28909372274994966;
                                attribute Cx : Real = -28.502837987616658;
                                attribute 'σ_Cx' : Real = 28.721044428837228;
                                attribute Cy : Real = 44.96724219061434;
                                attribute 'σ_Cy' : Real = 28.23690002309109;
                                attribute Cz : Real = 90.25048143230379;
                                attribute 'σ_Cz' : Real = 29.057750463592832;
                                attribute Ixx : Real = 0.2481775524098801;
                                attribute 'σ_Ixx' : Real = 0.37074144170588635;
                                attribute Iyy : Real = 0.28662023955904664;
                                attribute 'σ_Iyy' : Real = 0.3723953238821935;
                                attribute Izz : Real = 0.25178410703081316;
                                attribute 'σ_Izz' : Real = 0.37017423652493897;
                                attribute Ixy : Real = 0.028321664779133962;
                                attribute 'σ_Ixy' : Real = 0.02351283871158888;
                                attribute Ixz : Real = 0.012647883362059291;
                                attribute 'σ_Ixz' : Real = 0.022566176940390956;
                                attribute Iyz : Real = 0.006076796732560149;
                                attribute 'σ_Iyz' : Real = 0.02209918015384651;
                            }
                        }
                    }
                    part <'C.1.1.4.3.4'> 'Assembly 48' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.3.4.1'> 'Subassembly 176' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.4.1.1'> 'Part 610' {
                                attribute POIconv : String = "+";
                                attribute Ipoint : Boolean = false;
                                attribute mass : Real = 0.2656773105228785;
                                attribute 'σ_mass' : Real = 0.28909372274994966;
                                attribute Cx : Real = -80.33401514403522;
                                attribute 'σ_Cx' : Real = 28.721044428837228;
                                attribute Cy : Real = 94.28526987321675;
                                attribute 'σ_Cy' : Real = 28.23690002309109;
                                attribute Cz : Real = -21.640755468979478;
                                attribute 'σ_Cz' : Real = 29.057750463592832;
                                attribute Ixx : Real = 0.3267084257802191;
                                attribute 'σ_Ixx' : Real = 0.37074144170588635;
                                attribute Iyy : Real = 0.33815512254078517;
                                attribute 'σ_Iyy' : Real = 0.3723953238821935;
                                attribute Izz : Real = 0.3326086121627109;
                                attribute 'σ_Izz' : Real = 0.37017423652493897;
                                attribute Ixy : Real = 0.003268070653877986;
                                attribute 'σ_Ixy' : Real = 0.02351283871158888;
                                attribute Ixz : Real = -1.62476016236583e-5;
                                attribute 'σ_Ixz' : Real = 0.022566176940390956;
                                attribute Iyz : Real = 2.142950688256802e-4;
                                attribute 'σ_Iyz' : Real = 0.02209918015384651;
                            }
                            part <'C.1.1.4.3.4.1.2'> 'Part 611' {
                                attribute POIconv : String = "+";
                                attribute Ipoint : Boolean = false;
                                attribute mass : Real = 0.6373585346913897;
                                attribute 'σ_mass' : Real = 0.28909372274994966;
                                attribute Cx : Real = 60.95930193550885;
                                attribute 'σ_Cx' : Real = 28.721044428837228;
                                attribute Cy : Real = 86.72547196038067;
                                attribute 'σ_Cy' : Real = 28.23690002309109;
                                attribute Cz : Real = 70.9997967351228;
                                attribute 'σ_Cz' : Real = 29.057750463592832;
                                attribute Ixx : Real = 0.601692236666902;
                                attribute 'σ_Ixx' : Real = 0.37074144170588635;
                                attribute Iyy : Real = 0.8008996587609389;
                                attribute 'σ_Iyy' : Real = 0.3723953238821935;
                                attribute Izz : Real = 0.7537394135934217;
                                attribute 'σ_Izz' : Real = 0.37017423652493897;
                                attribute Ixy : Real = 0.027813013919976932;
                                attribute 'σ_Ixy' : Real = 0.02351283871158888;
                                attribute Ixz : Real = 0.02472736154060891;
                                attribute 'σ_Ixz' : Real = 0.022566176940390956;
                                attribute Iyz : Real = 0.007003289602096967;
                                attribute 'σ_Iyz' : Real = 0.02209918015384651;
                            }
                            part <'C.1.1.4.3.4.1.3'> 'Part 612' {
                                attribute POIconv : String = "-";
                                attribute Ipoint : Boolean = false;
                                attribute mass : Real = 0.26737424880149774;
                                attribute 'σ_mass' : Real = 0.28909372274994966;
                                attribute Cx : Real = -88.10887238942087;
                                attribute 'σ_Cx' : Real = 28.721044428837228;
                                attribute Cy : Real = -57.8130520414561;
                                attribute 'σ_Cy' : Real = 28.23690002309109;
                                attribute Cz : Real = 59.29036121815443;
                                attribute 'σ_Cz' : Real = 29.057750463592832;
                                attribute Ixx : Real = 0.35475491658125613;
                                attribute 'σ_Ixx' : Real = 0.37074144170588635;
                                attribute Iyy : Real = 0.35650217239533155;
                                attribute 'σ_Iyy' : Real = 0.3723953238821935;
                                attribute Izz : Real = 0.34663442210444284;
                                attribute 'σ_Izz' : Real = 0.37017423652493897;
                                attribute Ixy : Real = -0.0028252134728761437;
                                attribute 'σ_Ixy' : Real = 0.02351283871158888;
                                attribute Ixz : Real = -0.006881694618507912;
                                attribute 'σ_Ixz' : Real = 0.022566176940390956;
                                attribute Iyz : Real = -0.004427563417236822;
                                attribute 'σ_Iyz' : Real = 0.02209918015384651;
                            }
                            part <'C.1.1.4.3.4.1.4'> 'Part 613' {
                                attribute POIconv : String = "-";
                                attribute Ipoint : Boolean = false;
                                attribute mass : Real = 0.9810857957242988;
                                attribute 'σ_mass' : Real = 0.28909372274994966;
                                attribute Cx : Real = -72.85161898471415;
                                attribute 'σ_Cx' : Real = 28.721044428837228;
                                attribute Cy : Real = -62.826147908344865;
                                attribute 'σ_Cy' : Real = 28.23690002309109;
                                attribute Cz : Real = 13.354952866211534;
                                attribute 'σ_Cz' : Real = 29.057750463592832;
                                attribute Ixx : Real = 1.2735345142686227;
                                attribute 'σ_Ixx' : Real = 0.37074144170588635;
                                attribute Iyy : Real = 1.0575627610220366;
                                attribute 'σ_Iyy' : Real = 0.3723953238821935;
                                attribute Izz : Real = 1.2096568508134407;
                                attribute 'σ_Izz' : Real = 0.37017423652493897;
                                attribute Ixy : Real = -0.04264771343180812;
                                attribute 'σ_Ixy' : Real = 0.02351283871158888;
                                attribute Ixz : Real = 0.05629149624704567;
                                attribute 'σ_Ixz' : Real = 0.022566176940390956;
                                attribute Iyz : Real = 0.009299563351676617;
                                attribute 'σ_Iyz' : Real = 0.02209918015384651;
                            }
                            part <'C.1.1.4.3.4.1.5'> 'Part 614' {
                                attribute POIconv : String = "+";
                                attribute Ipoint : Boolean = false;
                                attribute mass : Real = 0.6888172699850984;
                                attribute 'σ_mass' : Real = 0.28909372274994966;
                                attribute Cx : Real = 67.01885610818863;
                                attribute 'σ_Cx' : Real = 28.721044428837228;
                                attribute Cy : Real = 24.642146890982985;
                                attribute 'σ_Cy' : Real = 28.23690002309109;
                                attribute Cz : Real = -55.19423000514507;
                                attribute 'σ_Cz' : Real = 29.057750463592832;
                                attribute Ixx : Real = 0.8489431213330922;
                                attribute 'σ_Ixx' : Real = 0.37074144170588635;
                                attribute Iyy : Real = 0.8873412652922231;
                                attribute 'σ_Iyy' : Real = 0.3723953238821935;
                                attribute Izz : Real = 0.7792877189646696;
                                attribute 'σ_Izz' : Real = 0.37017423652493897;
                                attribute Ixy : Real = -0.044500647369686175;
                                attribute 'σ_Ixy' : Real = 0.02351283871158888;
                                attribute Ixz : Real = -0.024339757222151124;
                                attribute 'σ_Ixz' : Real = 0.022566176940390956;
                                attribute Iyz : Real = 1.828165040163568e-4;
                                attribute 'σ_Iyz' : Real = 0.02209918015384651;
                            }
                        }
                        part <'C.1.1.4.3.4.2'> 'Subassembly 177' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.4.2.1'> 'Part 615' {
                                attribute POIconv : String = "-";
                                attribute Ipoint : Boolean = false;
                                attribute mass : Real = 0.30510484090121465;
                                attribute 'σ_mass' : Real = 0.28909372274994966;
                                attribute Cx : Real = 24.81723129749298;
                                attribute 'σ_Cx' : Real = 28.721044428837228;
                                attribute Cy : Real = -10.214749770238996;
                                attribute 'σ_Cy' : Real = 28.23690002309109;
                                attribute Cz : Real = -99.26368980668485;
                                attribute 'σ_Cz' : Real = 29.057750463592832;
                                attribute Ixx : Real = 0.36726805956294817;
                                attribute 'σ_Ixx' : Real = 0.37074144170588635;
                                attribute Iyy : Real = 0.36027594004515484;
                                attribute 'σ_Iyy' : Real = 0.3723953238821935;
                                attribute Izz : Real = 0.44165506129856763;
                                attribute 'σ_Izz' : Real = 0.37017423652493897;
                                attribute Ixy : Real = -0.007869226533338576;
                                attribute 'σ_Ixy' : Real = 0.02351283871158888;
                                attribute Ixz : Real = 0.00750034548684524;
                                attribute 'σ_Ixz' : Real = 0.022566176940390956;
                                attribute Iyz : Real = 0.01439152655906041;
                                attribute 'σ_Iyz' : Real = 0.02209918015384651;
                            }
                            part <'C.1.1.4.3.4.2.2'> 'Part 616' {
                                attribute POIconv : String = "-";
                                attribute Ipoint : Boolean = false;
                                attribute mass : Real = 0.23407681215344928;
                                attribute 'σ_mass' : Real = 0.28909372274994966;
                                attribute Cx : Real = -64.75849249400198;
                                attribute 'σ_Cx' : Real = 28.721044428837228;
                                attribute Cy : Real = -70.23985991254449;
                                attribute 'σ_Cy' : Real = 28.23690002309109;
                                attribute Cz : Real = -70.36133245564997;
                                attribute 'σ_Cz' : Real = 29.057750463592832;
                                attribute Ixx : Real = 0.2283135519671674;
                                attribute 'σ_Ixx' : Real = 0.37074144170588635;
                                attribute Iyy : Real = 0.2561044301878222;
                                attribute 'σ_Iyy' : Real = 0.3723953238821935;
                                attribute Izz : Real = 0.26985652001674604;
                                attribute 'σ_Izz' : Real = 0.37017423652493897;
                                attribute Ixy : Real = -0.008857264258454465;
                                attribute 'σ_Ixy' : Real = 0.02351283871158888;
                                attribute Ixz : Real = 1.0401126086884647e-4;
                                attribute 'σ_Ixz' : Real = 0.022566176940390956;
                                attribute Iyz : Real = 0.006339513881813936;
                                attribute 'σ_Iyz' : Real = 0.02209918015384651;
                            }
                            part <'C.1.1.4.3.4.2.3'> 'Part 617' {
                                attribute POIconv : String = "-";
                                attribute Ipoint : Boolean = false;
                                attribute mass : Real = 0.907384101170348;
                                attribute 'σ_mass' : Real = 0.28909372274994966;
                                attribute Cx : Real = -63.547415006905794;
                                attribute 'σ_Cx' : Real = 28.721044428837228;
                                attribute Cy : Real = -9.002038324251771;
                                attribute 'σ_Cy' : Real = 28.23690002309109;
                                attribute Cz : Real = 20.371656212955713;
                                attribute 'σ_Cz' : Real = 29.057750463592832;
                                attribute Ixx : Real = 1.0789642397667212;
                                attribute 'σ_Ixx' : Real = 0.37074144170588635;
                                attribute Iyy : Real = 1.2456587244945194;
                                attribute 'σ_Iyy' : Real = 0.3723953238821935;
                                attribute Izz : Real = 1.2938684443306618;
                                attribute 'σ_Izz' : Real = 0.37017423652493897;
                                attribute Ixy : Real = -0.032861802898589615;
                                attribute 'σ_Ixy' : Real = 0.02351283871158888;
                                attribute Ixz : Real = -0.02159219808528338;
                                attribute 'σ_Ixz' : Real = 0.022566176940390956;
                                attribute Iyz : Real = -0.013593625129310123;
                                attribute 'σ_Iyz' : Real = 0.02209918015384651;
                            }
                            part <'C.1.1.4.3.4.2.4'> 'Part 618' {
                                attribute POIconv : String = "-";
                                attribute Ipoint : Boolean = false;
                                attribute mass : Real = 0.21186608048318886;
                                attribute 'σ_mass' : Real = 0.28909372274994966;
                                attribute Cx : Real = -9.593516122549772;
                                attribute 'σ_Cx' : Real = 28.721044428837228;
                                attribute Cy : Real = 33.33836211822927;
                                attribute 'σ_Cy' : Real = 28.23690002309109;
                                attribute Cz : Real = 91.75040274858475;
                                attribute 'σ_Cz' : Real = 29.057750463592832;
                                attribute Ixx : Real = 0.24113315541219454;
                                attribute 'σ_Ixx' : Real = 0.37074144170588635;
                                attribute Iyy : Real = 0.2542320275473199;
                                attribute 'σ_Iyy' : Real = 0.3723953238821935;
                                attribute Izz : Real = 0.2384186919880083;
                                attribute 'σ_Izz' : Real = 0.37017423652493897;
                                attribute Ixy : Real = 0.008502206007822647;
                                attribute 'σ_Ixy' : Real = 0.02351283871158888;
                                attribute Ixz : Real = 3.6909246326706144e-4;
                                attribute 'σ_Ixz' : Real = 0.022566176940390956;
                                attribute Iyz : Real = -0.0021335869360487275;
                                attribute 'σ_Iyz' : Real = 0.02209918015384651;
                            }
                        }
                    }
                    part <'C.1.1.4.3.5'> 'Assembly 49' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.3.5.1'> 'Subassembly 178' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.5.1.1'> 'Part 619' {
                                attribute POIconv : String = "-";
                                attribute Ipoint : Boolean = false;
                                attribute mass : Real = 0.36018784902687184;
                                attribute 'σ_mass' : Real = 0.28909372274994966;
                                attribute Cx : Real = -54.99962489120662;
                                attribute 'σ_Cx' : Real = 28.721044428837228;
                                attribute Cy : Real = 14.565082965418696;
                                attribute 'σ_Cy' : Real = 28.23690002309109;
                                attribute Cz : Real = 26.739184837788343;
                                attribute 'σ_Cz' : Real = 29.057750463592832;
                                attribute Ixx : Real = 0.46593398089072524;
                                attribute 'σ_Ixx' : Real = 0.37074144170588635;
                                attribute Iyy : Real = 0.4154572955856419;
                                attribute 'σ_Iyy' : Real = 0.3723953238821935;
                                attribute Izz : Real = 0.44596979356504857;
                                attribute 'σ_Izz' : Real = 0.37017423652493897;
                                attribute Ixy : Real = 0.03018700574865391;
                                attribute 'σ_Ixy' : Real = 0.02351283871158888;
                                attribute Ixz : Real = 0.012002372931002866;
                                attribute 'σ_Ixz' : Real = 0.022566176940390956;
                                attribute Iyz : Real = 0.005172284348578503;
                                attribute 'σ_Iyz' : Real = 0.02209918015384651;
                            }
                            part <'C.1.1.4.3.5.1.2'> 'Part 620' {
                                attribute POIconv : String = "-";
                                attribute Ipoint : Boolean = false;
                                attribute mass : Real = 0.42649520421214404;
                                attribute 'σ_mass' : Real = 0.28909372274994966;
                                attribute Cx : Real = 84.20097441412508;
                                attribute 'σ_Cx' : Real = 28.721044428837228;
                                attribute Cy : Real = 99.38832256011665;
                                attribute 'σ_Cy' : Real = 28.23690002309109;
                                attribute Cz : Real = 72.96246164478362;
                                attribute 'σ_Cz' : Real = 29.057750463592832;
                                attribute Ixx : Real = 0.648733878506769;
                                attribute 'σ_Ixx' : Real = 0.37074144170588635;
                                attribute Iyy : Real = 0.64468474392724;
                                attribute 'σ_Iyy' : Real = 0.3723953238821935;
                                attribute Izz : Real = 0.617968950476794;
                                attribute 'σ_Izz' : Real = 0.37017423652493897;
                                attribute Ixy : Real = 0.022996312027488773;
                                attribute 'σ_Ixy' : Real = 0.02351283871158888;
                                attribute Ixz : Real = 0.019348612174992758;
                                attribute 'σ_Ixz' : Real = 0.022566176940390956;
                                attribute Iyz : Real = 0.01929193355889416;
                                attribute 'σ_Iyz' : Real = 0.02209918015384651;
                            }
                            part <'C.1.1.4.3.5.1.3'> 'Part 621' {
                                attribute POIconv : String = "+";
                                attribute Ipoint : Boolean = false;
                                attribute mass : Real = 0.8611739555306267;
                                attribute 'σ_mass' : Real = 0.28909372274994966;
                                attribute Cx : Real = -2.658510860055685;
                                attribute 'σ_Cx' : Real = 28.721044428837228;
                                attribute Cy : Real = 84.4280946534127;
                                attribute 'σ_Cy' : Real = 28.23690002309109;
                                attribute Cz : Real = -36.79147348739207;
                                attribute 'σ_Cz' : Real = 29.057750463592832;
                                attribute Ixx : Real = 0.9745464104751347;
                                attribute 'σ_Ixx' : Real = 0.37074144170588635;
                                attribute Iyy : Real = 1.0348666460656122;
                                attribute 'σ_Iyy' : Real = 0.3723953238821935;
                                attribute Izz : Real = 0.9936865779140995;
                                attribute 'σ_Izz' : Real = 0.37017423652493897;
                                attribute Ixy : Real = -0.01074890360035264;
                                attribute 'σ_Ixy' : Real = 0.02351283871158888;
                                attribute Ixz : Real = 0.0589430824941516;
                                attribute 'σ_Ixz' : Real = 0.022566176940390956;
                                attribute Iyz : Real = 0.03205383412988933;
                                attribute 'σ_Iyz' : Real = 0.02209918015384651;
                            }
                        }
                        part <'C.1.1.4.3.5.2'> 'Subassembly 179' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.3.5.2.1'> 'Part 622' {
                                attribute POIconv : String = "+";
                                attribute Ipoint : Boolean = false;
                                attribute mass : Real = 0.3421195869478397;
                                attribute 'σ_mass' : Real = 0.28909372274994966;
                                attribute Cx : Real = 29.029591754078865;
                                attribute 'σ_Cx' : Real = 28.721044428837228;
                                attribute Cy : Real = 28.445147769525647;
                                attribute 'σ_Cy' : Real = 28.23690002309109;
                                attribute Cz : Real = 20.892047323286533;
                                attribute 'σ_Cz' : Real = 29.057750463592832;
                                attribute Ixx : Real = 0.35100196471735606;
                                attribute 'σ_Ixx' : Real = 0.37074144170588635;
                                attribute Iyy : Real = 0.36166656520119794;
                                attribute 'σ_Iyy' : Real = 0.3723953238821935;
                                attribute Izz : Real = 0.35903603307787907;
                                attribute 'σ_Izz' : Real = 0.37017423652493897;
                                attribute Ixy : Real = -0.010653515180882141;
                                attribute 'σ_Ixy' : Real = 0.02351283871158888;
                                attribute Ixz : Real = -0.012655681288910342;
                                attribute 'σ_Ixz' : Real = 0.022566176940390956;
                                attribute Iyz : Real = 0.0038556263087321874;
                                attribute 'σ_Iyz' : Real = 0.02209918015384651;
                            }
                            part <'C.1.1.4.3.5.2.2'> 'Part 623' {
                                attribute POIconv : String = "-";
                                attribute Ipoint : Boolean = false;
                                attribute mass : Real = 0.8102129244310782;
                                attribute 'σ_mass' : Real = 0.28909372274994966;
                                attribute Cx : Real = -40.272019570693374;
                                attribute 'σ_Cx' : Real = 28.721044428837228;
                                attribute Cy : Real = -10.40549916215241;
                                attribute 'σ_Cy' : Real = 28.23690002309109;
                                attribute Cz : Real = 74.13752945140004;
                                attribute 'σ_Cz' : Real = 29.057750463592832;
                                attribute Ixx : Real = 1.1239316887072173;
                                attribute 'σ_Ixx' : Real = 0.37074144170588635;
                                attribute Iyy : Real = 1.062737904100701;
                                attribute 'σ_Iyy' : Real = 0.3723953238821935;
                                attribute Izz : Real = 0.916419075046008;
                                attribute 'σ_Izz' : Real = 0.37017423652493897;
                                attribute Ixy : Real = -0.08185847323484557;
                                attribute 'σ_Ixy' : Real = 0.02351283871158888;
                                attribute Ixz : Real = 0.009321796889378741;
                                attribute 'σ_Ixz' : Real = 0.022566176940390956;
                                attribute Iyz : Real = -0.028886946978181692;
                                attribute 'σ_Iyz' : Real = 0.02209918015384651;
                            }
                            part <'C.1.1.4.3.5.2.3'> 'Part 624' {
                                attribute POIconv : String = "+";
                                attribute Ipoint : Boolean = false;
                                attribute mass : Real = 0.05466605667327531;
                                attribute 'σ_mass' : Real = 0.28909372274994966;
                                attribute Cx : Real = 73.01968978717923;
                                attribute 'σ_Cx' : Real = 28.721044428837228;
                                attribute Cy : Real = 91.64281198754907;
                                attribute 'σ_Cy' : Real = 28.23690002309109;
                                attribute Cz : Real = -39.88271108828485;
                                attribute 'σ_Cz' : Real = 29.057750463592832;
                                attribute Ixx : Real = 0.07400038338779258;
                                attribute 'σ_Ixx' : Real = 0.37074144170588635;
                                attribute Iyy : Real = 0.07007849895235144;
                                attribute 'σ_Iyy' : Real = 0.3723953238821935;
                                attribute Izz : Real = 0.06647157977087918;
                                attribute 'σ_Izz' : Real = 0.37017423652493897;
                                attribute Ixy : Real = -0.0024084044725299486;
                                attribute 'σ_Ixy' : Real = 0.02351283871158888;
                                attribute Ixz : Real = -6.24158241917667e-4;
                                attribute 'σ_Ixz' : Real = 0.022566176940390956;
                                attribute Iyz : Real = 0.002195849483704372;
                                attribute 'σ_Iyz' : Real = 0.02209918015384651;
                            }
                        }
                    }
                }
                part <'C.1.1.4.4'> 'Subsystem 14' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.4.4.1'> 'Assembly 50' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.4.1.1'> 'Subassembly 180' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.1.1.1'> 'Part 625' {
                                attribute POIconv : String = "+";
                                attribute Ipoint : Boolean = false;
                                attribute mass : Real = 0.7876343644401058;
                                attribute 'σ_mass' : Real = 0.28909372274994966;
                                attribute Cx : Real = -73.83402697741985;
                                attribute 'σ_Cx' : Real = 28.721044428837228;
                                attribute Cy : Real = 13.13617629930377;
                                attribute 'σ_Cy' : Real = 28.23690002309109;
                                attribute Cz : Real = 73.16198796033859;
                                attribute 'σ_Cz' : Real = 29.057750463592832;
                                attribute Ixx : Real = 1.139252763741179;
                                attribute 'σ_Ixx' : Real = 0.37074144170588635;
                                attribute Iyy : Real = 0.9711585230914291;
                                attribute 'σ_Iyy' : Real = 0.3723953238821935;
                                attribute Izz : Real = 0.9862007547185113;
                                attribute 'σ_Izz' : Real = 0.37017423652493897;
                                attribute Ixy : Real = 0.015287389186507846;
                                attribute 'σ_Ixy' : Real = 0.02351283871158888;
                                attribute Ixz : Real = 0.008703336641789189;
                                attribute 'σ_Ixz' : Real = 0.022566176940390956;
                                attribute Iyz : Real = -0.005018832835694189;
                                attribute 'σ_Iyz' : Real = 0.02209918015384651;
                            }
                            part <'C.1.1.4.4.1.1.2'> 'Part 626' {
                                attribute POIconv : String = "-";
                                attribute Ipoint : Boolean = false;
                                attribute mass : Real = 0.578128091476392;
                                attribute 'σ_mass' : Real = 0.28909372274994966;
                                attribute Cx : Real = 55.574284167960286;
                                attribute 'σ_Cx' : Real = 28.721044428837228;
                                attribute Cy : Real = 19.393894588574767;
                                attribute 'σ_Cy' : Real = 28.23690002309109;
                                attribute Cz : Real = -26.010617520660162;
                                attribute 'σ_Cz' : Real = 29.057750463592832;
                                attribute Ixx : Real = 0.5831513984532389;
                                attribute 'σ_Ixx' : Real = 0.37074144170588635;
                                attribute Iyy : Real = 0.5607295373395104;
                                attribute 'σ_Iyy' : Real = 0.3723953238821935;
                                attribute Izz : Real = 0.6249180587770601;
                                attribute 'σ_Izz' : Real = 0.37017423652493897;
                                attribute Ixy : Real = 0.0259678977135785;
                                attribute 'σ_Ixy' : Real = 0.02351283871158888;
                                attribute Ixz : Real = 0.0024976451974963983;
                                attribute 'σ_Ixz' : Real = 0.022566176940390956;
                                attribute Iyz : Real = 0.010692804773251394;
                                attribute 'σ_Iyz' : Real = 0.02209918015384651;
                            }
                            part <'C.1.1.4.4.1.1.3'> 'Part 627' {
                                attribute POIconv : String = "-";
                                attribute Ipoint : Boolean = false;
                                attribute mass : Real = 0.134961188639747;
                                attribute 'σ_mass' : Real = 0.28909372274994966;
                                attribute Cx : Real = 28.62754762172699;
                                attribute 'σ_Cx' : Real = 28.721044428837228;
                                attribute Cy : Real = 24.620764516294003;
                                attribute 'σ_Cy' : Real = 28.23690002309109;
                                attribute Cz : Real = 66.66370336897671;
                                attribute 'σ_Cz' : Real = 29.057750463592832;
                                attribute Ixx : Real = 0.16727766255622784;
                                attribute 'σ_Ixx' : Real = 0.37074144170588635;
                                attribute Iyy : Real = 0.16610874643914114;
                                attribute 'σ_Iyy' : Real = 0.3723953238821935;
                                attribute Izz : Real = 0.16012159839722556;
                                attribute 'σ_Izz' : Real = 0.37017423652493897;
                                attribute Ixy : Real = -0.0020515438828217396;
                                attribute 'σ_Ixy' : Real = 0.02351283871158888;
                                attribute Ixz : Real = -0.0035147450648254585;
                                attribute 'σ_Ixz' : Real = 0.022566176940390956;
                                attribute Iyz : Real = -0.002231452592443744;
                                attribute 'σ_Iyz' : Real = 0.02209918015384651;
                            }
                            part <'C.1.1.4.4.1.1.4'> 'Part 628' {
                                attribute POIconv : String = "+";
                                attribute Ipoint : Boolean = false;
                                attribute mass : Real = 0.9090832123777364;
                                attribute 'σ_mass' : Real = 0.28909372274994966;
                                attribute Cx : Real = 83.87243486940861;
                                attribute 'σ_Cx' : Real = 28.721044428837228;
                                attribute Cy : Real = 10.607843147590756;
                                attribute 'σ_Cy' : Real = 28.23690002309109;
                                attribute Cz : Real = -5.592089518904686;
                                attribute 'σ_Cz' : Real = 29.057750463592832;
                                attribute Ixx : Real = 1.1806435467087562;
                                attribute 'σ_Ixx' : Real = 0.37074144170588635;
                                attribute Iyy : Real = 1.1912181174350485;
                                attribute 'σ_Iyy' : Real = 0.3723953238821935;
                                attribute Izz : Real = 1.1621758224177816;
                                attribute 'σ_Izz' : Real = 0.37017423652493897;
                                attribute Ixy : Real = 0.0428009847603786;
                                attribute 'σ_Ixy' : Real = 0.02351283871158888;
                                attribute Ixz : Real = 0.001608703548696245;
                                attribute 'σ_Ixz' : Real = 0.022566176940390956;
                                attribute Iyz : Real = -0.0199117417816868;
                                attribute 'σ_Iyz' : Real = 0.02209918015384651;
                            }
                        }
                        part <'C.1.1.4.4.1.2'> 'Subassembly 181' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.1.2.1'> 'Part 629' {
                                attribute POIconv : String = "-";
                                attribute Ipoint : Boolean = false;
                                attribute mass : Real = 0.2530637267380953;
                                attribute 'σ_mass' : Real = 0.28909372274994966;
                                attribute Cx : Real = 36.555469408631325;
                                attribute 'σ_Cx' : Real = 28.721044428837228;
                                attribute Cy : Real = 95.08864753879607;
                                attribute 'σ_Cy' : Real = 28.23690002309109;
                                attribute Cz : Real = 88.61079043708742;
                                attribute 'σ_Cz' : Real = 29.057750463592832;
                                attribute Ixx : Real = 0.2751498190880859;
                                attribute 'σ_Ixx' : Real = 0.37074144170588635;
                                attribute Iyy : Real = 0.2884679399052517;
                                attribute 'σ_Iyy' : Real = 0.3723953238821935;
                                attribute Izz : Real = 0.27654683093940435;
                                attribute 'σ_Izz' : Real = 0.37017423652493897;
                                attribute Ixy : Real = 0.008134720288820205;
                                attribute 'σ_Ixy' : Real = 0.02351283871158888;
                                attribute Ixz : Real = -0.0037418441572790503;
                                attribute 'σ_Ixz' : Real = 0.022566176940390956;
                                attribute Iyz : Real = -0.007731692357026624;
                                attribute 'σ_Iyz' : Real = 0.02209918015384651;
                            }
                            part <'C.1.1.4.4.1.2.2'> 'Part 630' {
                                attribute POIconv : String = "+";
                                attribute Ipoint : Boolean = false;
                                attribute mass : Real = 0.5131104602287524;
                                attribute 'σ_mass' : Real = 0.28909372274994966;
                                attribute Cx : Real = 33.715164894238114;
                                attribute 'σ_Cx' : Real = 28.721044428837228;
                                attribute Cy : Real = -2.213059226050973;
                                attribute 'σ_Cy' : Real = 28.23690002309109;
                                attribute Cz : Real = 22.465278627350926;
                                attribute 'σ_Cz' : Real = 29.057750463592832;
                                attribute Ixx : Real = 0.5908585732543389;
                                attribute 'σ_Ixx' : Real = 0.37074144170588635;
                                attribute Iyy : Real = 0.6727778525177867;
                                attribute 'σ_Iyy' : Real = 0.3723953238821935;
                                attribute Izz : Real = 0.632929651044438;
                                attribute 'σ_Izz' : Real = 0.37017423652493897;
                                attribute Ixy : Real = 5.841571015980603e-5;
                                attribute 'σ_Ixy' : Real = 0.02351283871158888;
                                attribute Ixz : Real = 0.008695652902468383;
                                attribute 'σ_Ixz' : Real = 0.022566176940390956;
                                attribute Iyz : Real = -0.048628502840556684;
                                attribute 'σ_Iyz' : Real = 0.02209918015384651;
                            }
                            part <'C.1.1.4.4.1.2.3'> 'Part 631' {
                                attribute POIconv : String = "+";
                                attribute Ipoint : Boolean = false;
                                attribute mass : Real = 0.09627683711610735;
                                attribute 'σ_mass' : Real = 0.28909372274994966;
                                attribute Cx : Real = 44.73222210071981;
                                attribute 'σ_Cx' : Real = 28.721044428837228;
                                attribute Cy : Real = -76.81080126203597;
                                attribute 'σ_Cy' : Real = 28.23690002309109;
                                attribute Cz : Real = 6.381321884691715;
                                attribute 'σ_Cz' : Real = 29.057750463592832;
                                attribute Ixx : Real = 0.10038840498046217;
                                attribute 'σ_Ixx' : Real = 0.37074144170588635;
                                attribute Iyy : Real = 0.10288062559698441;
                                attribute 'σ_Iyy' : Real = 0.3723953238821935;
                                attribute Izz : Real = 0.10105545383956836;
                                attribute 'σ_Izz' : Real = 0.37017423652493897;
                                attribute Ixy : Real = -5.2345651808272e-4;
                                attribute 'σ_Ixy' : Real = 0.02351283871158888;
                                attribute Ixz : Real = 0.001621883754674607;
                                attribute 'σ_Ixz' : Real = 0.022566176940390956;
                                attribute Iyz : Real = -0.002887650154809425;
                                attribute 'σ_Iyz' : Real = 0.02209918015384651;
                            }
                            part <'C.1.1.4.4.1.2.4'> 'Part 632' {
                                attribute POIconv : String = "+";
                                attribute Ipoint : Boolean = false;
                                attribute mass : Real = 0.7189656034540385;
                                attribute 'σ_mass' : Real = 0.28909372274994966;
                                attribute Cx : Real = -77.27161380462348;
                                attribute 'σ_Cx' : Real = 28.721044428837228;
                                attribute Cy : Real = -21.555351465940475;
                                attribute 'σ_Cy' : Real = 28.23690002309109;
                                attribute Cz : Real = 83.10190890915692;
                                attribute 'σ_Cz' : Real = 29.057750463592832;
                                attribute Ixx : Real = 0.8998275937366682;
                                attribute 'σ_Ixx' : Real = 0.37074144170588635;
                                attribute Iyy : Real = 0.8781170989823803;
                                attribute 'σ_Iyy' : Real = 0.3723953238821935;
                                attribute Izz : Real = 0.8928099108972033;
                                attribute 'σ_Izz' : Real = 0.37017423652493897;
                                attribute Ixy : Real = -0.1133287122914308;
                                attribute 'σ_Ixy' : Real = 0.02351283871158888;
                                attribute Ixz : Real = 0.019949234854670192;
                                attribute 'σ_Ixz' : Real = 0.022566176940390956;
                                attribute Iyz : Real = 0.002908574202194272;
                                attribute 'σ_Iyz' : Real = 0.02209918015384651;
                            }
                            part <'C.1.1.4.4.1.2.5'> 'Part 633' {
                                attribute POIconv : String = "-";
                                attribute Ipoint : Boolean = false;
                                attribute mass : Real = 0.45745119171915577;
                                attribute 'σ_mass' : Real = 0.28909372274994966;
                                attribute Cx : Real = 61.73730925656855;
                                attribute 'σ_Cx' : Real = 28.721044428837228;
                                attribute Cy : Real = -13.850621040910482;
                                attribute 'σ_Cy' : Real = 28.23690002309109;
                                attribute Cz : Real = -58.137682639062405;
                                attribute 'σ_Cz' : Real = 29.057750463592832;
                                attribute Ixx : Real = 0.5902970737033577;
                                attribute 'σ_Ixx' : Real = 0.37074144170588635;
                                attribute Iyy : Real = 0.6866288310140553;
                                attribute 'σ_Iyy' : Real = 0.3723953238821935;
                                attribute Izz : Real = 0.65671479826207;
                                attribute 'σ_Izz' : Real = 0.37017423652493897;
                                attribute Ixy : Real = -0.008924095188379094;
                                attribute 'σ_Ixy' : Real = 0.02351283871158888;
                                attribute Ixz : Real = -0.011028995694243936;
                                attribute 'σ_Ixz' : Real = 0.022566176940390956;
                                attribute Iyz : Real = 0.022484405377679366;
                                attribute 'σ_Iyz' : Real = 0.02209918015384651;
                            }
                        }
                        part <'C.1.1.4.4.1.3'> 'Subassembly 182' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.1.3.1'> 'Part 634' {
                                attribute POIconv : String = "-";
                                attribute Ipoint : Boolean = false;
                                attribute mass : Real = 0.7445031916454901;
                                attribute 'σ_mass' : Real = 0.28909372274994966;
                                attribute Cx : Real = -77.09335209801793;
                                attribute 'σ_Cx' : Real = 28.721044428837228;
                                attribute Cy : Real = 56.73170727677643;
                                attribute 'σ_Cy' : Real = 28.23690002309109;
                                attribute Cz : Real = -62.00810060836375;
                                attribute 'σ_Cz' : Real = 29.057750463592832;
                                attribute Ixx : Real = 1.0505947686101482;
                                attribute 'σ_Ixx' : Real = 0.37074144170588635;
                                attribute Iyy : Real = 1.0911259668615945;
                                attribute 'σ_Iyy' : Real = 0.3723953238821935;
                                attribute Izz : Real = 1.0419452762255526;
                                attribute 'σ_Izz' : Real = 0.37017423652493897;
                                attribute Ixy : Real = 0.002777205497951083;
                                attribute 'σ_Ixy' : Real = 0.02351283871158888;
                                attribute Ixz : Real = 0.04384984317939566;
                                attribute 'σ_Ixz' : Real = 0.022566176940390956;
                                attribute Iyz : Real = 0.005179359757764826;
                                attribute 'σ_Iyz' : Real = 0.02209918015384651;
                            }
                            part <'C.1.1.4.4.1.3.2'> 'Part 635' {
                                attribute POIconv : String = "+";
                                attribute Ipoint : Boolean = false;
                                attribute mass : Real = 0.7894681825775187;
                                attribute 'σ_mass' : Real = 0.28909372274994966;
                                attribute Cx : Real = 43.335770489647985;
                                attribute 'σ_Cx' : Real = 28.721044428837228;
                                attribute Cy : Real = 38.13791209831834;
                                attribute 'σ_Cy' : Real = 28.23690002309109;
                                attribute Cz : Real = -91.25747540965676;
                                attribute 'σ_Cz' : Real = 29.057750463592832;
                                attribute Ixx : Real = 1.0521098089407661;
                                attribute 'σ_Ixx' : Real = 0.37074144170588635;
                                attribute Iyy : Real = 0.9764479277985872;
                                attribute 'σ_Iyy' : Real = 0.3723953238821935;
                                attribute Izz : Real = 0.98443750283496545;
                                attribute 'σ_Izz' : Real = 0.37017423652493897;
                                attribute Ixy : Real = -0.002212063508913096;
                                attribute 'σ_Ixy' : Real = 0.02351283871158888;
                                attribute Ixz : Real = 0.13761180567479708;
                                attribute 'σ_Ixz' : Real = 0.022566176940390956;
                                attribute Iyz : Real = -0.06166974936489115;
                                attribute 'σ_Iyz' : Real = 0.02209918015384651;
                            }
                            part <'C.1.1.4.4.1.3.3'> 'Part 636' {
                                attribute POIconv : String = "+";
                                attribute Ipoint : Boolean = false;
                                attribute mass : Real = 0.600022737139836;
                                attribute 'σ_mass' : Real = 0.28909372274994966;
                                attribute Cx : Real = -39.65528765693307;
                                attribute 'σ_Cx' : Real = 28.721044428837228;
                                attribute Cy : Real = -69.50015788897872;
                                attribute 'σ_Cy' : Real = 28.23690002309109;
                                attribute Cz : Real = -82.10981488227844;
                                attribute 'σ_Cz' : Real = 29.057750463592832;
                                attribute Ixx : Real = 0.7467293868149234;
                                attribute 'σ_Ixx' : Real = 0.37074144170588635;
                                attribute Iyy : Real = 0.7132531140447513;
                                attribute 'σ_Iyy' : Real = 0.3723953238821935;
                                attribute Izz : Real = 0.6617734497211627;
                                attribute 'σ_Izz' : Real = 0.37017423652493897;
                                attribute Ixy : Real = 0.030410120387099393;
                                attribute 'σ_Ixy' : Real = 0.02351283871158888;
                                attribute Ixz : Real = -0.0035022425268600196;
                                attribute 'σ_Ixz' : Real = 0.022566176940390956;
                                attribute Iyz : Real = 0.024813186905203406;
                                attribute 'σ_Iyz' : Real = 0.02209918015384651;
                            }
                        }
                    }
                    part <'C.1.1.4.4.2'> 'Assembly 51' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.4.2.1'> 'Subassembly 183' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.2.1.1'> 'Part 637' {
                                attribute POIconv : String = "+";
                                attribute Ipoint : Boolean = false;
                                attribute mass : Real = 0.5850285754469223;
                                attribute 'σ_mass' : Real = 0.28909372274994966;
                                attribute Cx : Real = 92.03333049081266;
                                attribute 'σ_Cx' : Real = 28.721044428837228;
                                attribute Cy : Real = -95.03411869518459;
                                attribute 'σ_Cy' : Real = 28.23690002309109;
                                attribute Cz : Real = -94.54090013168752;
                                attribute 'σ_Cz' : Real = 29.057750463592832;
                                attribute Ixx : Real = 0.7385547623937166;
                                attribute 'σ_Ixx' : Real = 0.37074144170588635;
                                attribute Iyy : Real = 0.7691384008707457;
                                attribute 'σ_Iyy' : Real = 0.3723953238821935;
                                attribute Izz : Real = 0.7587495995937851;
                                attribute 'σ_Izz' : Real = 0.37017423652493897;
                                attribute Ixy : Real = -0.0568511866849163;
                                attribute 'σ_Ixy' : Real = 0.02351283871158888;
                                attribute Ixz : Real = 0.03762691444175087;
                                attribute 'σ_Ixz' : Real = 0.022566176940390956;
                                attribute Iyz : Real = 0.06051961046485135;
                                attribute 'σ_Iyz' : Real = 0.02209918015384651;
                            }
                            part <'C.1.1.4.4.2.1.2'> 'Part 638' {
                                attribute POIconv : String = "-";
                                attribute Ipoint : Boolean = false;
                                attribute mass : Real = 0.7281634239251725;
                                attribute 'σ_mass' : Real = 0.28909372274994966;
                                attribute Cx : Real = -99.07150059007108;
                                attribute 'σ_Cx' : Real = 28.721044428837228;
                                attribute Cy : Real = -20.29116591438651;
                                attribute 'σ_Cy' : Real = 28.23690002309109;
                                attribute Cz : Real = 81.64410474710166;
                                attribute 'σ_Cz' : Real = 29.057750463592832;
                                attribute Ixx : Real = 0.7946678896161208;
                                attribute 'σ_Ixx' : Real = 0.37074144170588635;
                                attribute Iyy : Real = 0.8027839388925051;
                                attribute 'σ_Iyy' : Real = 0.3723953238821935;
                                attribute Izz : Real = 0.6680983673206855;
                                attribute 'σ_Izz' : Real = 0.37017423652493897;
                                attribute Ixy : Real = 0.0015691527312515765;
                                attribute 'σ_Ixy' : Real = 0.02351283871158888;
                                attribute Ixz : Real = 0.01387978728029793;
                                attribute 'σ_Ixz' : Real = 0.022566176940390956;
                                attribute Iyz : Real = 0.005223915830027655;
                                attribute 'σ_Iyz' : Real = 0.02209918015384651;
                            }
                            part <'C.1.1.4.4.2.1.3'> 'Part 639' {
                                attribute POIconv : String = "-";
                                attribute Ipoint : Boolean = false;
                                attribute mass : Real = 0.34984703476168216;
                                attribute 'σ_mass' : Real = 0.28909372274994966;
                                attribute Cx : Real = 11.26664848998189;
                                attribute 'σ_Cx' : Real = 28.721044428837228;
                                attribute Cy : Real = 36.090205470100045;
                                attribute 'σ_Cy' : Real = 28.23690002309109;
                                attribute Cz : Real = -79.79898378252983;
                                attribute 'σ_Cz' : Real = 29.057750463592832;
                                attribute Ixx : Real = 0.34705694331724224;
                                attribute 'σ_Ixx' : Real = 0.37074144170588635;
                                attribute Iyy : Real = 0.34520902025967787;
                                attribute 'σ_Iyy' : Real = 0.3723953238821935;
                                attribute Izz : Real = 0.29848930728677286;
                                attribute 'σ_Izz' : Real = 0.37017423652493897;
                                attribute Ixy : Real = 0.001732562027179664;
                                attribute 'σ_Ixy' : Real = 0.02351283871158888;
                                attribute Ixz : Real = 0.004111237649007722;
                                attribute 'σ_Ixz' : Real = 0.022566176940390956;
                                attribute Iyz : Real = -0.003352189099066421;
                                attribute 'σ_Iyz' : Real = 0.02209918015384651;
                            }
                            part <'C.1.1.4.4.2.1.4'> 'Part 640' {
                                attribute POIconv : String = "+";
                                attribute Ipoint : Boolean = false;
                                attribute mass : Real = 0.5000466931459959;
                                attribute 'σ_mass' : Real = 0.28909372274994966;
                                attribute Cx : Real = -42.53464583307505;
                                attribute 'σ_Cx' : Real = 28.721044428837228;
                                attribute Cy : Real = -19.910336611792445;
                                attribute 'σ_Cy' : Real = 28.23690002309109;
                                attribute Cz : Real = -67.27843726985157;
                                attribute 'σ_Cz' : Real = 29.057750463592832;
                                attribute Ixx : Real = 0.675107583124659;
                                attribute 'σ_Ixx' : Real = 0.37074144170588635;
                                attribute Iyy : Real = 0.7330380267268488;
                                attribute 'σ_Iyy' : Real = 0.3723953238821935;
                                attribute Izz : Real = 0.6225290764573047;
                                attribute 'σ_Izz' : Real = 0.37017423652493897;
                                attribute Ixy : Real = 0.00821429025942937;
                                attribute 'σ_Ixy' : Real = 0.02351283871158888;
                                attribute Ixz : Real = 0.003499141306068416;
                                attribute 'σ_Ixz' : Real = 0.022566176940390956;
                                attribute Iyz : Real = -0.046860042677496855;
                                attribute 'σ_Iyz' : Real = 0.02209918015384651;
                            }
                        }
                        part <'C.1.1.4.4.2.2'> 'Subassembly 184' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.2.2.1'> 'Part 641' {
                                attribute POIconv : String = "+";
                                attribute Ipoint : Boolean = false;
                                attribute mass : Real = 0.8178395064359065;
                                attribute 'σ_mass' : Real = 0.28909372274994966;
                                attribute Cx : Real = -99.41334365867078;
                                attribute 'σ_Cx' : Real = 28.721044428837228;
                                attribute Cy : Real = 66.0095114260912;
                                attribute 'σ_Cy' : Real = 28.23690002309109;
                                attribute Cz : Real = -86.4141988568008;
                                attribute 'σ_Cz' : Real = 29.057750463592832;
                                attribute Ixx : Real = 1.1799980484867147;
                                attribute 'σ_Ixx' : Real = 0.37074144170588635;
                                attribute Iyy : Real = 1.2723315048634494;
                                attribute 'σ_Iyy' : Real = 0.3723953238821935;
                                attribute Izz : Real = 1.2490540993734833;
                                attribute 'σ_Izz' : Real = 0.37017423652493897;
                                attribute Ixy : Real = -0.007872232966019563;
                                attribute 'σ_Ixy' : Real = 0.02351283871158888;
                                attribute Ixz : Real = -0.0038526707459050394;
                                attribute 'σ_Ixz' : Real = 0.022566176940390956;
                                attribute Iyz : Real = -0.018515835467333753;
                                attribute 'σ_Iyz' : Real = 0.02209918015384651;
                            }
                            part <'C.1.1.4.4.2.2.2'> 'Part 642' {
                                attribute POIconv : String = "+";
                                attribute Ipoint : Boolean = false;
                                attribute mass : Real = 0.7008634718770627;
                                attribute 'σ_mass' : Real = 0.28909372274994966;
                                attribute Cx : Real = -26.6862197779119;
                                attribute 'σ_Cx' : Real = 28.721044428837228;
                                attribute Cy : Real = -35.09652717038989;
                                attribute 'σ_Cy' : Real = 28.23690002309109;
                                attribute Cz : Real = 27.19354876317084;
                                attribute 'σ_Cz' : Real = 29.057750463592832;
                                attribute Ixx : Real = 0.8581735090661876;
                                attribute 'σ_Ixx' : Real = 0.37074144170588635;
                                attribute Iyy : Real = 0.7990625431995491;
                                attribute 'σ_Iyy' : Real = 0.3723953238821935;
                                attribute Izz : Real = 0.8340933780478439;
                                attribute 'σ_Izz' : Real = 0.37017423652493897;
                                attribute Ixy : Real = -0.053903288222560616;
                                attribute 'σ_Ixy' : Real = 0.02351283871158888;
                                attribute Ixz : Real = 0.026856863933016447;
                                attribute 'σ_Ixz' : Real = 0.022566176940390956;
                                attribute Iyz : Real = 0.014718945302150503;
                                attribute 'σ_Iyz' : Real = 0.02209918015384651;
                            }
                            part <'C.1.1.4.4.2.2.3'> 'Part 643' {
                                attribute POIconv : String = "-";
                                attribute Ipoint : Boolean = false;
                                attribute mass : Real = 0.11524255599244498;
                                attribute 'σ_mass' : Real = 0.28909372274994966;
                                attribute Cx : Real = 79.45131273008883;
                                attribute 'σ_Cx' : Real = 28.721044428837228;
                                attribute Cy : Real = -33.110162895172834;
                                attribute 'σ_Cy' : Real = 28.23690002309109;
                                attribute Cz : Real = -89.52125748619437;
                                attribute 'σ_Cz' : Real = 29.057750463592832;
                                attribute Ixx : Real = 0.13369376134203798;
                                attribute 'σ_Ixx' : Real = 0.37074144170588635;
                                attribute Iyy : Real = 0.1109909330288093;
                                attribute 'σ_Iyy' : Real = 0.3723953238821935;
                                attribute Izz : Real = 0.13577337908492074;
                                attribute 'σ_Izz' : Real = 0.37017423652493897;
                                attribute Ixy : Real = -0.016250548696400337;
                                attribute 'σ_Ixy' : Real = 0.02351283871158888;
                                attribute Ixz : Real = 0.0018443793115279277;
                                attribute 'σ_Ixz' : Real = 0.022566176940390956;
                                attribute Iyz : Real = 0.004216570133306237;
                                attribute 'σ_Iyz' : Real = 0.02209918015384651;
                            }
                            part <'C.1.1.4.4.2.2.4'> 'Part 644' {
                                attribute POIconv : String = "+";
                                attribute Ipoint : Boolean = false;
                                attribute mass : Real = 0.7713214161780197;
                                attribute 'σ_mass' : Real = 0.28909372274994966;
                                attribute Cx : Real = 34.15020760148764;
                                attribute 'σ_Cx' : Real = 28.721044428837228;
                                attribute Cy : Real = 58.92902300693095;
                                attribute 'σ_Cy' : Real = 28.23690002309109;
                                attribute Cz : Real = -17.255045985803008;
                                attribute 'σ_Cz' : Real = 29.057750463592832;
                                attribute Ixx : Real = 0.9416641897622688;
                                attribute 'σ_Ixx' : Real = 0.37074144170588635;
                                attribute Iyy : Real = 0.8602111167660398;
                                attribute 'σ_Iyy' : Real = 0.3723953238821935;
                                attribute Izz : Real = 0.9335252373162685;
                                attribute 'σ_Izz' : Real = 0.37017423652493897;
                                attribute Ixy : Real = 0.03224752135352436;
                                attribute 'σ_Ixy' : Real = 0.02351283871158888;
                                attribute Ixz : Real = -0.00867700382084487;
                                attribute 'σ_Ixz' : Real = 0.022566176940390956;
                                attribute Iyz : Real = -0.032925345619652005;
                                attribute 'σ_Iyz' : Real = 0.02209918015384651;
                            }
                        }
                    }
                    part <'C.1.1.4.4.3'> 'Assembly 52' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.4.3.1'> 'Subassembly 185' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.3.1.1'> 'Part 645' {
                                attribute POIconv : String = "-";
                                attribute Ipoint : Boolean = false;
                                attribute mass : Real = 0.3708922187909484;
                                attribute 'σ_mass' : Real = 0.28909372274994966;
                                attribute Cx : Real = 95.16847915947437;
                                attribute 'σ_Cx' : Real = 28.721044428837228;
                                attribute Cy : Real = 62.7530378755182;
                                attribute 'σ_Cy' : Real = 28.23690002309109;
                                attribute Cz : Real = 7.694865297526121;
                                attribute 'σ_Cz' : Real = 29.057750463592832;
                                attribute Ixx : Real = 0.48991264372612714;
                                attribute 'σ_Ixx' : Real = 0.37074144170588635;
                                attribute Iyy : Real = 0.4995432845810946;
                                attribute 'σ_Iyy' : Real = 0.3723953238821935;
                                attribute Izz : Real = 0.4629455816568369;
                                attribute 'σ_Izz' : Real = 0.37017423652493897;
                                attribute Ixy : Real = 0.034515841272272085;
                                attribute 'σ_Ixy' : Real = 0.02351283871158888;
                                attribute Ixz : Real = -0.0019665326911897036;
                                attribute 'σ_Ixz' : Real = 0.022566176940390956;
                                attribute Iyz : Real = -0.002147191810277855;
                                attribute 'σ_Iyz' : Real = 0.02209918015384651;
                            }
                            part <'C.1.1.4.4.3.1.2'> 'Part 646' {
                                attribute POIconv : String = "-";
                                attribute Ipoint : Boolean = false;
                                attribute mass : Real = 0.5559666744966526;
                                attribute 'σ_mass' : Real = 0.28909372274994966;
                                attribute Cx : Real = -28.1262690667063;
                                attribute 'σ_Cx' : Real = 28.721044428837228;
                                attribute Cy : Real = -72.25096658803523;
                                attribute 'σ_Cy' : Real = 28.23690002309109;
                                attribute Cz : Real = 54.88128364086151;
                                attribute 'σ_Cz' : Real = 29.057750463592832;
                                attribute Ixx : Real = 0.7292300228806227;
                                attribute 'σ_Ixx' : Real = 0.37074144170588635;
                                attribute Iyy : Real = 0.841315023274269;
                                attribute 'σ_Iyy' : Real = 0.3723953238821935;
                                attribute Izz : Real = 0.7291900871263225;
                                attribute 'σ_Izz' : Real = 0.37017423652493897;
                                attribute Ixy : Real = 0.047261992220689095;
                                attribute 'σ_Ixy' : Real = 0.02351283871158888;
                                attribute Ixz : Real = 0.0040078407510839254;
                                attribute 'σ_Ixz' : Real = 0.022566176940390956;
                                attribute Iyz : Real = -0.05196345428313482;
                                attribute 'σ_Iyz' : Real = 0.02209918015384651;
                            }
                        }
                        part <'C.1.1.4.4.3.2'> 'Subassembly 186' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.3.2.1'> 'Part 647' {
                                attribute POIconv : String = "-";
                                attribute Ipoint : Boolean = false;
                                attribute mass : Real = 0.5929015871589072;
                                attribute 'σ_mass' : Real = 0.28909372274994966;
                                attribute Cx : Real = 90.22030089981854;
                                attribute 'σ_Cx' : Real = 28.721044428837228;
                                attribute Cy : Real = 43.91450327821076;
                                attribute 'σ_Cy' : Real = 28.23690002309109;
                                attribute Cz : Real = 93.74375697225332;
                                attribute 'σ_Cz' : Real = 29.057750463592832;
                                attribute Ixx : Real = 0.7132659420359875;
                                attribute 'σ_Ixx' : Real = 0.37074144170588635;
                                attribute Iyy : Real = 0.8145055400847724;
                                attribute 'σ_Iyy' : Real = 0.3723953238821935;
                                attribute Izz : Real = 0.798426913221992;
                                attribute 'σ_Izz' : Real = 0.37017423652493897;
                                attribute Ixy : Real = -0.028204504287408484;
                                attribute 'σ_Ixy' : Real = 0.02351283871158888;
                                attribute Ixz : Real = -0.01351279316801711;
                                attribute 'σ_Ixz' : Real = 0.022566176940390956;
                                attribute Iyz : Real = 0.0895824291515327;
                                attribute 'σ_Iyz' : Real = 0.02209918015384651;
                            }
                            part <'C.1.1.4.4.3.2.2'> 'Part 648' {
                                attribute POIconv : String = "-";
                                attribute Ipoint : Boolean = false;
                                attribute mass : Real = 0.11944463109923527;
                                attribute 'σ_mass' : Real = 0.28909372274994966;
                                attribute Cx : Real = -70.27734313160181;
                                attribute 'σ_Cx' : Real = 28.721044428837228;
                                attribute Cy : Real = -54.88735265098512;
                                attribute 'σ_Cy' : Real = 28.23690002309109;
                                attribute Cz : Real = -85.39182115346193;
                                attribute 'σ_Cz' : Real = 29.057750463592832;
                                attribute Ixx : Real = 0.15561112986551978;
                                attribute 'σ_Ixx' : Real = 0.37074144170588635;
                                attribute Iyy : Real = 0.13392965961057846;
                                attribute 'σ_Iyy' : Real = 0.3723953238821935;
                                attribute Izz : Real = 0.14201765980254955;
                                attribute 'σ_Izz' : Real = 0.37017423652493897;
                                attribute Ixy : Real = -0.006894970837519226;
                                attribute 'σ_Ixy' : Real = 0.02351283871158888;
                                attribute Ixz : Real = -0.010849575401658864;
                                attribute 'σ_Ixz' : Real = 0.022566176940390956;
                                attribute Iyz : Real = -0.002121634058788813;
                                attribute 'σ_Iyz' : Real = 0.02209918015384651;
                            }
                            part <'C.1.1.4.4.3.2.3'> 'Part 649' {
                                attribute POIconv : String = "+";
                                attribute Ipoint : Boolean = false;
                                attribute mass : Real = 0.7270542142656632;
                                attribute 'σ_mass' : Real = 0.28909372274994966;
                                attribute Cx : Real = 27.828036528080702;
                                attribute 'σ_Cx' : Real = 28.721044428837228;
                                attribute Cy : Real = -91.04517088271677;
                                attribute 'σ_Cy' : Real = 28.23690002309109;
                                attribute Cz : Real = 75.82955206744373;
                                attribute 'σ_Cz' : Real = 29.057750463592832;
                                attribute Ixx : Real = 1.0071645506733111;
                                attribute 'σ_Ixx' : Real = 0.37074144170588635;
                                attribute Iyy : Real = 0.89517000135824;
                                attribute 'σ_Iyy' : Real = 0.3723953238821935;
                                attribute Izz : Real = 0.837896063840597;
                                attribute 'σ_Izz' : Real = 0.37017423652493897;
                                attribute Ixy : Real = -0.004771443169109581;
                                attribute 'σ_Ixy' : Real = 0.02351283871158888;
                                attribute Ixz : Real = -0.07115226375479916;
                                attribute 'σ_Ixz' : Real = 0.022566176940390956;
                                attribute Iyz : Real = 0.06062610864754969;
                                attribute 'σ_Iyz' : Real = 0.02209918015384651;
                            }
                            part <'C.1.1.4.4.3.2.4'> 'Part 650' {
                                attribute POIconv : String = "-";
                                attribute Ipoint : Boolean = false;
                                attribute mass : Real = 0.39043298179726116;
                                attribute 'σ_mass' : Real = 0.28909372274994966;
                                attribute Cx : Real = -34.16824992746115;
                                attribute 'σ_Cx' : Real = 28.721044428837228;
                                attribute Cy : Real = -77.69201076589525;
                                attribute 'σ_Cy' : Real = 28.23690002309109;
                                attribute Cz : Real = -27.146129868924618;
                                attribute 'σ_Cz' : Real = 29.057750463592832;
                                attribute Ixx : Real = 0.4736410963161003;
                                attribute 'σ_Ixx' : Real = 0.37074144170588635;
                                attribute Iyy : Real = 0.5272370345692045;
                                attribute 'σ_Iyy' : Real = 0.3723953238821935;
                                attribute Izz : Real = 0.5095622791079157;
                                attribute 'σ_Izz' : Real = 0.37017423652493897;
                                attribute Ixy : Real = 0.005098307148937808;
                                attribute 'σ_Ixy' : Real = 0.02351283871158888;
                                attribute Ixz : Real = 0.010748909107348673;
                                attribute 'σ_Ixz' : Real = 0.022566176940390956;
                                attribute Iyz : Real = 0.020505577586772107;
                                attribute 'σ_Iyz' : Real = 0.02209918015384651;
                            }
                            part <'C.1.1.4.4.3.2.5'> 'Part 651' {
                                attribute POIconv : String = "-";
                                attribute Ipoint : Boolean = false;
                                attribute mass : Real = 0.057172867042711004;
                                attribute 'σ_mass' : Real = 0.28909372274994966;
                                attribute Cx : Real = 32.895800145342946;
                                attribute 'σ_Cx' : Real = 28.721044428837228;
                                attribute Cy : Real = -23.44853999093175;
                                attribute 'σ_Cy' : Real = 28.23690002309109;
                                attribute Cz : Real = 53.1336369458586;
                                attribute 'σ_Cz' : Real = 29.057750463592832;
                                attribute Ixx : Real = 0.08190849231471198;
                                attribute 'σ_Ixx' : Real = 0.37074144170588635;
                                attribute Iyy : Real = 0.07678246082938343;
                                attribute 'σ_Iyy' : Real = 0.3723953238821935;
                                attribute Izz : Real = 0.07321211261888941;
                                attribute 'σ_Izz' : Real = 0.37017423652493897;
                                attribute Ixy : Real = 0.0032909567413494647;
                                attribute 'σ_Ixy' : Real = 0.02351283871158888;
                                attribute Ixz : Real = -2.642453420887582e-4;
                                attribute 'σ_Ixz' : Real = 0.022566176940390956;
                                attribute Iyz : Real = 1.6256916490882265e-4;
                                attribute 'σ_Iyz' : Real = 0.02209918015384651;
                            }
                        }
                        part <'C.1.1.4.4.3.3'> 'Subassembly 187' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.3.3.1'> 'Part 652' {
                                attribute POIconv : String = "+";
                                attribute Ipoint : Boolean = false;
                                attribute mass : Real = 0.5834298036796972;
                                attribute 'σ_mass' : Real = 0.28909372274994966;
                                attribute Cx : Real = 72.66629724763334;
                                attribute 'σ_Cx' : Real = 28.721044428837228;
                                attribute Cy : Real = -12.304610526189208;
                                attribute 'σ_Cy' : Real = 28.23690002309109;
                                attribute Cz : Real = -76.55869051814079;
                                attribute 'σ_Cz' : Real = 29.057750463592832;
                                attribute Ixx : Real = 0.7744401753220163;
                                attribute 'σ_Ixx' : Real = 0.37074144170588635;
                                attribute Iyy : Real = 0.8091303297473567;
                                attribute 'σ_Iyy' : Real = 0.3723953238821935;
                                attribute Izz : Real = 0.7752726147253572;
                                attribute 'σ_Izz' : Real = 0.37017423652493897;
                                attribute Ixy : Real = 0.014912444861162326;
                                attribute 'σ_Ixy' : Real = 0.02351283871158888;
                                attribute Ixz : Real = -0.03203726823482057;
                                attribute 'σ_Ixz' : Real = 0.022566176940390956;
                                attribute Iyz : Real = 0.025091479071070885;
                                attribute 'σ_Iyz' : Real = 0.02209918015384651;
                            }
                            part <'C.1.1.4.4.3.3.2'> 'Part 653' {
                                attribute POIconv : String = "+";
                                attribute Ipoint : Boolean = false;
                                attribute mass : Real = 0.03884216252528131;
                                attribute 'σ_mass' : Real = 0.28909372274994966;
                                attribute Cx : Real = -67.52397250384092;
                                attribute 'σ_Cx' : Real = 28.721044428837228;
                                attribute Cy : Real = -62.76498571969569;
                                attribute 'σ_Cy' : Real = 28.23690002309109;
                                attribute Cz : Real = -10.758896358311176;
                                attribute 'σ_Cz' : Real = 29.057750463592832;
                                attribute Ixx : Real = 0.05230914465404922;
                                attribute 'σ_Ixx' : Real = 0.37074144170588635;
                                attribute Iyy : Real = 0.054008826850562894;
                                attribute 'σ_Iyy' : Real = 0.3723953238821935;
                                attribute Izz : Real = 0.05972875603266172;
                                attribute 'σ_Izz' : Real = 0.37017423652493897;
                                attribute Ixy : Real = -2.286942533325464e-5;
                                attribute 'σ_Ixy' : Real = 0.02351283871158888;
                                attribute Ixz : Real = -8.16954618559898e-5;
                                attribute 'σ_Ixz' : Real = 0.022566176940390956;
                                attribute Iyz : Real = 0.0033016698351556743;
                                attribute 'σ_Iyz' : Real = 0.02209918015384651;
                            }
                        }
                        part <'C.1.1.4.4.3.4'> 'Subassembly 188' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.3.4.1'> 'Part 654' {
                                attribute POIconv : String = "-";
                                attribute Ipoint : Boolean = false;
                                attribute mass : Real = 0.7294995150738396;
                                attribute 'σ_mass' : Real = 0.28909372274994966;
                                attribute Cx : Real = 20.80776821821928;
                                attribute 'σ_Cx' : Real = 28.721044428837228;
                                attribute Cy : Real = 56.439983658492565;
                                attribute 'σ_Cy' : Real = 28.23690002309109;
                                attribute Cz : Real = -18.41131648980081;
                                attribute 'σ_Cz' : Real = 29.057750463592832;
                                attribute Ixx : Real = 1.0885855727211162;
                                attribute 'σ_Ixx' : Real = 0.37074144170588635;
                                attribute Iyy : Real = 1.0362376835868075;
                                attribute 'σ_Iyy' : Real = 0.3723953238821935;
                                attribute Izz : Real = 1.1099342308146714;
                                attribute 'σ_Izz' : Real = 0.37017423652493897;
                                attribute Ixy : Real = -0.02262375998969255;
                                attribute 'σ_Ixy' : Real = 0.02351283871158888;
                                attribute Ixz : Real = -0.04306735791686042;
                                attribute 'σ_Ixz' : Real = 0.022566176940390956;
                                attribute Iyz : Real = -7.850062816412658e-4;
                                attribute 'σ_Iyz' : Real = 0.02209918015384651;
                            }
                            part <'C.1.1.4.4.3.4.2'> 'Part 655' {
                                attribute POIconv : String = "+";
                                attribute Ipoint : Boolean = false;
                                attribute mass : Real = 0.06647569054015912;
                                attribute 'σ_mass' : Real = 0.28909372274994966;
                                attribute Cx : Real = -54.38962164334953;
                                attribute 'σ_Cx' : Real = 28.721044428837228;
                                attribute Cy : Real = 96.47902818396688;
                                attribute 'σ_Cy' : Real = 28.23690002309109;
                                attribute Cz : Real = 54.403184819966555;
                                attribute 'σ_Cz' : Real = 29.057750463592832;
                                attribute Ixx : Real = 0.07493053501695036;
                                attribute 'σ_Ixx' : Real = 0.37074144170588635;
                                attribute Iyy : Real = 0.0696320207792127;
                                attribute 'σ_Iyy' : Real = 0.3723953238821935;
                                attribute Izz : Real = 0.07371307851929684;
                                attribute 'σ_Izz' : Real = 0.37017423652493897;
                                attribute Ixy : Real = -0.0013140496659008374;
                                attribute 'σ_Ixy' : Real = 0.02351283871158888;
                                attribute Ixz : Real = -0.0023899330591866884;
                                attribute 'σ_Ixz' : Real = 0.022566176940390956;
                                attribute Iyz : Real = 0.006571556739064629;
                                attribute 'σ_Iyz' : Real = 0.02209918015384651;
                            }
                            part <'C.1.1.4.4.3.4.3'> 'Part 656' {
                                attribute POIconv : String = "+";
                                attribute Ipoint : Boolean = false;
                                attribute mass : Real = 0.8293648636750877;
                                attribute 'σ_mass' : Real = 0.28909372274994966;
                                attribute Cx : Real = -99.7387720271945;
                                attribute 'σ_Cx' : Real = 28.721044428837228;
                                attribute Cy : Real = -10.832154704257846;
                                attribute 'σ_Cy' : Real = 28.23690002309109;
                                attribute Cz : Real = -3.8142846431583166;
                                attribute 'σ_Cz' : Real = 29.057750463592832;
                                attribute Ixx : Real = 1.1332402498766572;
                                attribute 'σ_Ixx' : Real = 0.37074144170588635;
                                attribute Iyy : Real = 1.0960864846989586;
                                attribute 'σ_Iyy' : Real = 0.3723953238821935;
                                attribute Izz : Real = 1.300113932983362;
                                attribute 'σ_Izz' : Real = 0.37017423652493897;
                                attribute Ixy : Real = -0.005475115002864709;
                                attribute 'σ_Ixy' : Real = 0.02351283871158888;
                                attribute Ixz : Real = -0.06413935635584692;
                                attribute 'σ_Ixz' : Real = 0.022566176940390956;
                                attribute Iyz : Real = 0.03647391340973194;
                                attribute 'σ_Iyz' : Real = 0.02209918015384651;
                            }
                            part <'C.1.1.4.4.3.4.4'> 'Part 657' {
                                attribute POIconv : String = "-";
                                attribute Ipoint : Boolean = false;
                                attribute mass : Real = 0.9732242669011466;
                                attribute 'σ_mass' : Real = 0.28909372274994966;
                                attribute Cx : Real = 63.64414384588599;
                                attribute 'σ_Cx' : Real = 28.721044428837228;
                                attribute Cy : Real = 18.035257700830698;
                                attribute 'σ_Cy' : Real = 28.23690002309109;
                                attribute Cz : Real = 30.359476525336504;
                                attribute 'σ_Cz' : Real = 29.057750463592832;
                                attribute Ixx : Real = 1.2583666517712888;
                                attribute 'σ_Ixx' : Real = 0.37074144170588635;
                                attribute Iyy : Real = 1.2702173104602115;
                                attribute 'σ_Iyy' : Real = 0.3723953238821935;
                                attribute Izz : Real = 1.254563463701605;
                                attribute 'σ_Izz' : Real = 0.37017423652493897;
                                attribute Ixy : Real = 0.006678955725010968;
                                attribute 'σ_Ixy' : Real = 0.02351283871158888;
                                attribute Ixz : Real = -0.0027418875649944715;
                                attribute 'σ_Ixz' : Real = 0.022566176940390956;
                                attribute Iyz : Real = -0.0034297498091773533;
                                attribute 'σ_Iyz' : Real = 0.02209918015384651;
                            }
                        }
                        part <'C.1.1.4.4.3.5'> 'Subassembly 189' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.3.5.1'> 'Part 658' {
                                attribute POIconv : String = "-";
                                attribute Ipoint : Boolean = false;
                                attribute mass : Real = 0.10381324536819012;
                                attribute 'σ_mass' : Real = 0.28909372274994966;
                                attribute Cx : Real = -64.93578017689288;
                                attribute 'σ_Cx' : Real = 28.721044428837228;
                                attribute Cy : Real = 77.90709142573178;
                                attribute 'σ_Cy' : Real = 28.23690002309109;
                                attribute Cz : Real = -41.95287162438035;
                                attribute 'σ_Cz' : Real = 29.057750463592832;
                                attribute Ixx : Real = 0.12236136238449359;
                                attribute 'σ_Ixx' : Real = 0.37074144170588635;
                                attribute Iyy : Real = 0.12755863882373125;
                                attribute 'σ_Iyy' : Real = 0.3723953238821935;
                                attribute Izz : Real = 0.1249036453282957;
                                attribute 'σ_Izz' : Real = 0.37017423652493897;
                                attribute Ixy : Real = 0.006525911589655946;
                                attribute 'σ_Ixy' : Real = 0.02351283871158888;
                                attribute Ixz : Real = 0.004752255211857944;
                                attribute 'σ_Ixz' : Real = 0.022566176940390956;
                                attribute Iyz : Real = 2.7050919682382237e-4;
                                attribute 'σ_Iyz' : Real = 0.02209918015384651;
                            }
                            part <'C.1.1.4.4.3.5.2'> 'Part 659' {
                                attribute POIconv : String = "-";
                                attribute Ipoint : Boolean = false;
                                attribute mass : Real = 0.6908058856886345;
                                attribute 'σ_mass' : Real = 0.28909372274994966;
                                attribute Cx : Real = 18.802362075075507;
                                attribute 'σ_Cx' : Real = 28.721044428837228;
                                attribute Cy : Real = 58.91342908143997;
                                attribute 'σ_Cy' : Real = 28.23690002309109;
                                attribute Cz : Real = -39.664994925260544;
                                attribute 'σ_Cz' : Real = 29.057750463592832;
                                attribute Ixx : Real = 0.760993359139941;
                                attribute 'σ_Ixx' : Real = 0.37074144170588635;
                                attribute Iyy : Real = 0.8961084879110146;
                                attribute 'σ_Iyy' : Real = 0.3723953238821935;
                                attribute Izz : Real = 0.8189816995968294;
                                attribute 'σ_Izz' : Real = 0.37017423652493897;
                                attribute Ixy : Real = -0.04462630736215295;
                                attribute 'σ_Ixy' : Real = 0.02351283871158888;
                                attribute Ixz : Real = 0.00923851624049183;
                                attribute 'σ_Ixz' : Real = 0.022566176940390956;
                                attribute Iyz : Real = -0.02284500772779672;
                                attribute 'σ_Iyz' : Real = 0.02209918015384651;
                            }
                            part <'C.1.1.4.4.3.5.3'> 'Part 660' {
                                attribute POIconv : String = "-";
                                attribute Ipoint : Boolean = false;
                                attribute mass : Real = 0.39716463511041367;
                                attribute 'σ_mass' : Real = 0.28909372274994966;
                                attribute Cx : Real = 56.3727430999279;
                                attribute 'σ_Cx' : Real = 28.721044428837228;
                                attribute Cy : Real = -63.765452057123184;
                                attribute 'σ_Cy' : Real = 28.23690002309109;
                                attribute Cz : Real = 14.837637869641185;
                                attribute 'σ_Cz' : Real = 29.057750463592832;
                                attribute Ixx : Real = 0.466276944649842;
                                attribute 'σ_Ixx' : Real = 0.37074144170588635;
                                attribute Iyy : Real = 0.47371364254354675;
                                attribute 'σ_Iyy' : Real = 0.3723953238821935;
                                attribute Izz : Real = 0.4521836449404636;
                                attribute 'σ_Izz' : Real = 0.37017423652493897;
                                attribute Ixy : Real = -0.020137304849106787;
                                attribute 'σ_Ixy' : Real = 0.02351283871158888;
                                attribute Ixz : Real = -0.03105040290991145;
                                attribute 'σ_Ixz' : Real = 0.022566176940390956;
                                attribute Iyz : Real = -0.03066280443231116;
                                attribute 'σ_Iyz' : Real = 0.02209918015384651;
                            }
                            part <'C.1.1.4.4.3.5.4'> 'Part 661' {
                                attribute POIconv : String = "-";
                                attribute Ipoint : Boolean = false;
                                attribute mass : Real = 0.9128130629851948;
                                attribute 'σ_mass' : Real = 0.28909372274994966;
                                attribute Cx : Real = -10.915799252688885;
                                attribute 'σ_Cx' : Real = 28.721044428837228;
                                attribute Cy : Real = 2.938470523804426;
                                attribute 'σ_Cy' : Real = 28.23690002309109;
                                attribute Cz : Real = -25.43125026859343;
                                attribute 'σ_Cz' : Real = 29.057750463592832;
                                attribute Ixx : Real = 1.3367298630637854;
                                attribute 'σ_Ixx' : Real = 0.37074144170588635;
                                attribute Iyy : Real = 1.2886982065698867;
                                attribute 'σ_Iyy' : Real = 0.3723953238821935;
                                attribute Izz : Real = 1.2776388207537794;
                                attribute 'σ_Izz' : Real = 0.37017423652493897;
                                attribute Ixy : Real = 0.004874802984346142;
                                attribute 'σ_Ixy' : Real = 0.02351283871158888;
                                attribute Ixz : Real = -0.008465364977057556;
                                attribute 'σ_Ixz' : Real = 0.022566176940390956;
                                attribute Iyz : Real = 0.040751973122049374;
                                attribute 'σ_Iyz' : Real = 0.02209918015384651;
                            }
                            part <'C.1.1.4.4.3.5.5'> 'Part 662' {
                                attribute POIconv : String = "-";
                                attribute Ipoint : Boolean = false;
                                attribute mass : Real = 0.48982419743412176;
                                attribute 'σ_mass' : Real = 0.28909372274994966;
                                attribute Cx : Real = 29.91551300510764;
                                attribute 'σ_Cx' : Real = 28.721044428837228;
                                attribute Cy : Real = 24.721557134762406;
                                attribute 'σ_Cy' : Real = 28.23690002309109;
                                attribute Cz : Real = -68.25380143709481;
                                attribute 'σ_Cz' : Real = 29.057750463592832;
                                attribute Ixx : Real = 0.579138393087451;
                                attribute 'σ_Ixx' : Real = 0.37074144170588635;
                                attribute Iyy : Real = 0.49805813778701313;
                                attribute 'σ_Iyy' : Real = 0.3723953238821935;
                                attribute Izz : Real = 0.5964203878052231;
                                attribute 'σ_Izz' : Real = 0.37017423652493897;
                                attribute Ixy : Real = 0.02367105169573768;
                                attribute 'σ_Ixy' : Real = 0.02351283871158888;
                                attribute Ixz : Real = 0.039714001707232674;
                                attribute 'σ_Ixz' : Real = 0.022566176940390956;
                                attribute Iyz : Real = -0.024897487731116177;
                                attribute 'σ_Iyz' : Real = 0.02209918015384651;
                            }
                        }
                    }
                    part <'C.1.1.4.4.4'> 'Assembly 53' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.4.4.1'> 'Subassembly 190' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.4.1.1'> 'Part 663' {
                                attribute POIconv : String = "+";
                                attribute Ipoint : Boolean = false;
                                attribute mass : Real = 0.7460370842069387;
                                attribute 'σ_mass' : Real = 0.28909372274994966;
                                attribute Cx : Real = 44.681803649291396;
                                attribute 'σ_Cx' : Real = 28.721044428837228;
                                attribute Cy : Real = -49.046736769378185;
                                attribute 'σ_Cy' : Real = 28.23690002309109;
                                attribute Cz : Real = 3.6335147451609373;
                                attribute 'σ_Cz' : Real = 29.057750463592832;
                                attribute Ixx : Real = 0.8206288609790491;
                                attribute 'σ_Ixx' : Real = 0.37074144170588635;
                                attribute Iyy : Real = 0.8240987708061448;
                                attribute 'σ_Iyy' : Real = 0.3723953238821935;
                                attribute Izz : Real = 0.9662463239274194;
                                attribute 'σ_Izz' : Real = 0.37017423652493897;
                                attribute Ixy : Real = -0.036969133585519925;
                                attribute 'σ_Ixy' : Real = 0.02351283871158888;
                                attribute Ixz : Real = -0.05189924401597873;
                                attribute 'σ_Ixz' : Real = 0.022566176940390956;
                                attribute Iyz : Real = -0.02170383463928574;
                                attribute 'σ_Iyz' : Real = 0.02209918015384651;
                            }
                            part <'C.1.1.4.4.4.1.2'> 'Part 664' {
                                attribute POIconv : String = "-";
                                attribute Ipoint : Boolean = false;
                                attribute mass : Real = 0.9950239433427341;
                                attribute 'σ_mass' : Real = 0.28909372274994966;
                                attribute Cx : Real = 49.79861541651189;
                                attribute 'σ_Cx' : Real = 28.721044428837228;
                                attribute Cy : Real = -27.88475281558931;
                                attribute 'σ_Cy' : Real = 28.23690002309109;
                                attribute Cz : Real = -11.094320099800825;
                                attribute 'σ_Cz' : Real = 29.057750463592832;
                                attribute Ixx : Real = 1.1398798164841484;
                                attribute 'σ_Ixx' : Real = 0.37074144170588635;
                                attribute Iyy : Real = 1.0205937981087359;
                                attribute 'σ_Iyy' : Real = 0.3723953238821935;
                                attribute Izz : Real = 1.262935207341279;
                                attribute 'σ_Izz' : Real = 0.37017423652493897;
                                attribute Ixy : Real = 0.04350959382729905;
                                attribute 'σ_Ixy' : Real = 0.02351283871158888;
                                attribute Ixz : Real = -0.01999228933925175;
                                attribute 'σ_Ixz' : Real = 0.022566176940390956;
                                attribute Iyz : Real = 0.05508174998057035;
                                attribute 'σ_Iyz' : Real = 0.02209918015384651;
                            }
                            part <'C.1.1.4.4.4.1.3'> 'Part 665' {
                                attribute POIconv : String = "+";
                                attribute Ipoint : Boolean = false;
                                attribute mass : Real = 0.6226469260763843;
                                attribute 'σ_mass' : Real = 0.28909372274994966;
                                attribute Cx : Real = 20.853755017742515;
                                attribute 'σ_Cx' : Real = 28.721044428837228;
                                attribute Cy : Real = -15.939851617440581;
                                attribute 'σ_Cy' : Real = 28.23690002309109;
                                attribute Cz : Real = 64.73429212346673;
                                attribute 'σ_Cz' : Real = 29.057750463592832;
                                attribute Ixx : Real = 0.975527632148426;
                                attribute 'σ_Ixx' : Real = 0.37074144170588635;
                                attribute Iyy : Real = 0.9603041646391267;
                                attribute 'σ_Iyy' : Real = 0.3723953238821935;
                                attribute Izz : Real = 0.9593930517425237;
                                attribute 'σ_Izz' : Real = 0.37017423652493897;
                                attribute Ixy : Real = -0.004335460860332886;
                                attribute 'σ_Ixy' : Real = 0.02351283871158888;
                                attribute Ixz : Real = -0.004265222686083687;
                                attribute 'σ_Ixz' : Real = 0.022566176940390956;
                                attribute Iyz : Real = -9.275286369879559e-4;
                                attribute 'σ_Iyz' : Real = 0.02209918015384651;
                            }
                            part <'C.1.1.4.4.4.1.4'> 'Part 666' {
                                attribute POIconv : String = "-";
                                attribute Ipoint : Boolean = false;
                                attribute mass : Real = 0.09171087645413355;
                                attribute 'σ_mass' : Real = 0.28909372274994966;
                                attribute Cx : Real = -66.38633105903864;
                                attribute 'σ_Cx' : Real = 28.721044428837228;
                                attribute Cy : Real = -21.641023317351937;
                                attribute 'σ_Cy' : Real = 28.23690002309109;
                                attribute Cz : Real = -36.29060350358486;
                                attribute 'σ_Cz' : Real = 29.057750463592832;
                                attribute Ixx : Real = 0.13385867241431623;
                                attribute 'σ_Ixx' : Real = 0.37074144170588635;
                                attribute Iyy : Real = 0.10629591196262331;
                                attribute 'σ_Iyy' : Real = 0.3723953238821935;
                                attribute Izz : Real = 0.12171634469903274;
                                attribute 'σ_Izz' : Real = 0.37017423652493897;
                                attribute Ixy : Real = -0.0016704420589676394;
                                attribute 'σ_Ixy' : Real = 0.02351283871158888;
                                attribute Ixz : Real = -0.0011132647127876506;
                                attribute 'σ_Ixz' : Real = 0.022566176940390956;
                                attribute Iyz : Real = -3.5043140685179694e-4;
                                attribute 'σ_Iyz' : Real = 0.02209918015384651;
                            }
                        }
                        part <'C.1.1.4.4.4.2'> 'Subassembly 191' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.4.2.1'> 'Part 667' {
                                attribute POIconv : String = "-";
                                attribute Ipoint : Boolean = false;
                                attribute mass : Real = 0.41442017414723525;
                                attribute 'σ_mass' : Real = 0.28909372274994966;
                                attribute Cx : Real = -41.24772152863443;
                                attribute 'σ_Cx' : Real = 28.721044428837228;
                                attribute Cy : Real = 16.03273069486022;
                                attribute 'σ_Cy' : Real = 28.23690002309109;
                                attribute Cz : Real = -1.5365771483629942;
                                attribute 'σ_Cz' : Real = 29.057750463592832;
                                attribute Ixx : Real = 0.463646018585574;
                                attribute 'σ_Ixx' : Real = 0.37074144170588635;
                                attribute Iyy : Real = 0.48390182259333736;
                                attribute 'σ_Iyy' : Real = 0.3723953238821935;
                                attribute Izz : Real = 0.4555758053168145;
                                attribute 'σ_Izz' : Real = 0.37017423652493897;
                                attribute Ixy : Real = 0.006764826690762742;
                                attribute 'σ_Ixy' : Real = 0.02351283871158888;
                                attribute Ixz : Real = -0.0028519594962106007;
                                attribute 'σ_Ixz' : Real = 0.022566176940390956;
                                attribute Iyz : Real = -0.007359256057349441;
                                attribute 'σ_Iyz' : Real = 0.02209918015384651;
                            }
                            part <'C.1.1.4.4.4.2.2'> 'Part 668' {
                                attribute POIconv : String = "-";
                                attribute Ipoint : Boolean = false;
                                attribute mass : Real = 0.9810561304318253;
                                attribute 'σ_mass' : Real = 0.28909372274994966;
                                attribute Cx : Real = -44.00698612444103;
                                attribute 'σ_Cx' : Real = 28.721044428837228;
                                attribute Cy : Real = -46.46273930557072;
                                attribute 'σ_Cy' : Real = 28.23690002309109;
                                attribute Cz : Real = 61.14027970470488;
                                attribute 'σ_Cz' : Real = 29.057750463592832;
                                attribute Ixx : Real = 1.2464724267746063;
                                attribute 'σ_Ixx' : Real = 0.37074144170588635;
                                attribute Iyy : Real = 1.3615500195266517;
                                attribute 'σ_Iyy' : Real = 0.3723953238821935;
                                attribute Izz : Real = 1.3210414589125157;
                                attribute 'σ_Izz' : Real = 0.37017423652493897;
                                attribute Ixy : Real = -0.008427737691065963;
                                attribute 'σ_Ixy' : Real = 0.02351283871158888;
                                attribute Ixz : Real = -0.07381658708078295;
                                attribute 'σ_Ixz' : Real = 0.022566176940390956;
                                attribute Iyz : Real = 0.04457754242755761;
                                attribute 'σ_Iyz' : Real = 0.02209918015384651;
                            }
                            part <'C.1.1.4.4.4.2.3'> 'Part 669' {
                                attribute POIconv : String = "+";
                                attribute Ipoint : Boolean = false;
                                attribute mass : Real = 0.2073239594688639;
                                attribute 'σ_mass' : Real = 0.28909372274994966;
                                attribute Cx : Real = 64.76589371450245;
                                attribute 'σ_Cx' : Real = 28.721044428837228;
                                attribute Cy : Real = -8.22969856671989;
                                attribute 'σ_Cy' : Real = 28.23690002309109;
                                attribute Cz : Real = -51.083578588441014;
                                attribute 'σ_Cz' : Real = 29.057750463592832;
                                attribute Ixx : Real = 0.2919851755944372;
                                attribute 'σ_Ixx' : Real = 0.37074144170588635;
                                attribute Iyy : Real = 0.24887200044581698;
                                attribute 'σ_Iyy' : Real = 0.3723953238821935;
                                attribute Izz : Real = 0.25149728812355837;
                                attribute 'σ_Izz' : Real = 0.37017423652493897;
                                attribute Ixy : Real = 0.0028152252170847198;
                                attribute 'σ_Ixy' : Real = 0.02351283871158888;
                                attribute Ixz : Real = 0.020272005236701897;
                                attribute 'σ_Ixz' : Real = 0.022566176940390956;
                                attribute Iyz : Real = -0.009147478898857185;
                                attribute 'σ_Iyz' : Real = 0.02209918015384651;
                            }
                            part <'C.1.1.4.4.4.2.4'> 'Part 670' {
                                attribute POIconv : String = "+";
                                attribute Ipoint : Boolean = false;
                                attribute mass : Real = 0.6598209148659371;
                                attribute 'σ_mass' : Real = 0.28909372274994966;
                                attribute Cx : Real = 55.72926583699882;
                                attribute 'σ_Cx' : Real = 28.721044428837228;
                                attribute Cy : Real = -51.02872885763645;
                                attribute 'σ_Cy' : Real = 28.23690002309109;
                                attribute Cz : Real = -59.8327518440783;
                                attribute 'σ_Cz' : Real = 29.057750463592832;
                                attribute Ixx : Real = 0.8713158024680474;
                                attribute 'σ_Ixx' : Real = 0.37074144170588635;
                                attribute Iyy : Real = 0.8588387056584211;
                                attribute 'σ_Iyy' : Real = 0.3723953238821935;
                                attribute Izz : Real = 0.8393741958348306;
                                attribute 'σ_Izz' : Real = 0.37017423652493897;
                                attribute Ixy : Real = 0.030829142776857887;
                                attribute 'σ_Ixy' : Real = 0.02351283871158888;
                                attribute Ixz : Real = 0.014233781497328632;
                                attribute 'σ_Ixz' : Real = 0.022566176940390956;
                                attribute Iyz : Real = -0.018059801260491077;
                                attribute 'σ_Iyz' : Real = 0.02209918015384651;
                            }
                        }
                        part <'C.1.1.4.4.4.3'> 'Subassembly 192' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.4.3.1'> 'Part 671' {
                                attribute POIconv : String = "-";
                                attribute Ipoint : Boolean = false;
                                attribute mass : Real = 0.9395295278353151;
                                attribute 'σ_mass' : Real = 0.28909372274994966;
                                attribute Cx : Real = 24.310704972594976;
                                attribute 'σ_Cx' : Real = 28.721044428837228;
                                attribute Cy : Real = 89.07412635162473;
                                attribute 'σ_Cy' : Real = 28.23690002309109;
                                attribute Cz : Real = -39.38687336631119;
                                attribute 'σ_Cz' : Real = 29.057750463592832;
                                attribute Ixx : Real = 1.1011973142032485;
                                attribute 'σ_Ixx' : Real = 0.37074144170588635;
                                attribute Iyy : Real = 1.014959160470996;
                                attribute 'σ_Iyy' : Real = 0.3723953238821935;
                                attribute Izz : Real = 1.0358922164723334;
                                attribute 'σ_Izz' : Real = 0.37017423652493897;
                                attribute Ixy : Real = -0.016391674255517817;
                                attribute 'σ_Ixy' : Real = 0.02351283871158888;
                                attribute Ixz : Real = 0.07970686107997438;
                                attribute 'σ_Ixz' : Real = 0.022566176940390956;
                                attribute Iyz : Real = -0.01540563887548016;
                                attribute 'σ_Iyz' : Real = 0.02209918015384651;
                            }
                            part <'C.1.1.4.4.4.3.2'> 'Part 672' {
                                attribute POIconv : String = "-";
                                attribute Ipoint : Boolean = false;
                                attribute mass : Real = 0.22989934752346017;
                                attribute 'σ_mass' : Real = 0.28909372274994966;
                                attribute Cx : Real = -74.94536084122956;
                                attribute 'σ_Cx' : Real = 28.721044428837228;
                                attribute Cy : Real = -35.33804030157626;
                                attribute 'σ_Cy' : Real = 28.23690002309109;
                                attribute Cz : Real = 64.7656999528408;
                                attribute 'σ_Cz' : Real = 29.057750463592832;
                                attribute Ixx : Real = 0.31644585538757936;
                                attribute 'σ_Ixx' : Real = 0.37074144170588635;
                                attribute Iyy : Real = 0.2935569695992459;
                                attribute 'σ_Iyy' : Real = 0.3723953238821935;
                                attribute Izz : Real = 0.2854106723993982;
                                attribute 'σ_Izz' : Real = 0.37017423652493897;
                                attribute Ixy : Real = 0.008772669929748275;
                                attribute 'σ_Ixy' : Real = 0.02351283871158888;
                                attribute Ixz : Real = 0.007897311757948057;
                                attribute 'σ_Ixz' : Real = 0.022566176940390956;
                                attribute Iyz : Real = 0.012721215288910126;
                                attribute 'σ_Iyz' : Real = 0.02209918015384651;
                            }
                            part <'C.1.1.4.4.4.3.3'> 'Part 673' {
                                attribute POIconv : String = "+";
                                attribute Ipoint : Boolean = false;
                                attribute mass : Real = 0.6448374005705119;
                                attribute 'σ_mass' : Real = 0.28909372274994966;
                                attribute Cx : Real = -47.73186882957816;
                                attribute 'σ_Cx' : Real = 28.721044428837228;
                                attribute Cy : Real = 75.10412405245006;
                                attribute 'σ_Cy' : Real = 28.23690002309109;
                                attribute Cz : Real = 98.51210243068635;
                                attribute 'σ_Cz' : Real = 29.057750463592832;
                                attribute Ixx : Real = 0.768810610390486;
                                attribute 'σ_Ixx' : Real = 0.37074144170588635;
                                attribute Iyy : Real = 0.7855635358213313;
                                attribute 'σ_Iyy' : Real = 0.3723953238821935;
                                attribute Izz : Real = 0.9019277139768106;
                                attribute 'σ_Izz' : Real = 0.37017423652493897;
                                attribute Ixy : Real = -0.039190964060222155;
                                attribute 'σ_Ixy' : Real = 0.02351283871158888;
                                attribute Ixz : Real = 0.0047140026305167206;
                                attribute 'σ_Ixz' : Real = 0.022566176940390956;
                                attribute Iyz : Real = 0.006334708608366373;
                                attribute 'σ_Iyz' : Real = 0.02209918015384651;
                            }
                            part <'C.1.1.4.4.4.3.4'> 'Part 674' {
                                attribute POIconv : String = "+";
                                attribute Ipoint : Boolean = false;
                                attribute mass : Real = 0.3924857693766244;
                                attribute 'σ_mass' : Real = 0.28909372274994966;
                                attribute Cx : Real = -24.58110828883946;
                                attribute 'σ_Cx' : Real = 28.721044428837228;
                                attribute Cy : Real = 85.84769736044109;
                                attribute 'σ_Cy' : Real = 28.23690002309109;
                                attribute Cz : Real = -19.588876515626907;
                                attribute 'σ_Cz' : Real = 29.057750463592832;
                                attribute Ixx : Real = 0.5337427465100959;
                                attribute 'σ_Ixx' : Real = 0.37074144170588635;
                                attribute Iyy : Real = 0.5582009971030575;
                                attribute 'σ_Iyy' : Real = 0.3723953238821935;
                                attribute Izz : Real = 0.6060182738584219;
                                attribute 'σ_Izz' : Real = 0.37017423652493897;
                                attribute Ixy : Real = 0.006485700900252028;
                                attribute 'σ_Ixy' : Real = 0.02351283871158888;
                                attribute Ixz : Real = 0.0010825429017011516;
                                attribute 'σ_Ixz' : Real = 0.022566176940390956;
                                attribute Iyz : Real = -0.010208972786856608;
                                attribute 'σ_Iyz' : Real = 0.02209918015384651;
                            }
                        }
                        part <'C.1.1.4.4.4.4'> 'Subassembly 193' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.4.4.4.1'> 'Part 675' {
                                attribute POIconv : String = "-";
                                attribute Ipoint : Boolean = false;
                                attribute mass : Real = 0.10299141077185049;
                                attribute 'σ_mass' : Real = 0.28909372274994966;
                                attribute Cx : Real = -76.77513929083943;
                                attribute 'σ_Cx' : Real = 28.721044428837228;
                                attribute Cy : Real = 52.76911025866866;
                                attribute 'σ_Cy' : Real = 28.23690002309109;
                                attribute Cz : Real = -85.07573287934065;
                                attribute 'σ_Cz' : Real = 29.057750463592832;
                                attribute Ixx : Real = 0.1406659143728044;
                                attribute 'σ_Ixx' : Real = 0.37074144170588635;
                                attribute Iyy : Real = 0.13552328218473658;
                                attribute 'σ_Iyy' : Real = 0.3723953238821935;
                                attribute Izz : Real = 0.15570786129877726;
                                attribute 'σ_Izz' : Real = 0.37017423652493897;
                                attribute Ixy : Real = -0.001132016907031185;
                                attribute 'σ_Ixy' : Real = 0.02351283871158888;
                                attribute Ixz : Real = -0.0035682786936119615;
                                attribute 'σ_Ixz' : Real = 0.022566176940390956;
                                attribute Iyz : Real = 0.003297623686421914;
                                attribute 'σ_Iyz' : Real = 0.02209918015384651;
                            }
                            part <'C.1.1.4.4.4.4.2'> 'Part 676' {
                                attribute POIconv : String = "-";
                                attribute Ipoint : Boolean = false;
                                attribute mass : Real = 0.43510476969531736;
                                attribute 'σ_mass' : Real = 0.28909372274994966;
                                attribute Cx : Real = -55.80467330291867;
                                attribute 'σ_Cx' : Real = 28.721044428837228;
                                attribute Cy : Real = 90.63829854130745;
                                attribute 'σ_Cy' : Real = 28.23690002309109;
                                attribute Cz : Real = -48.55994042009115;
                                attribute 'σ_Cz' : Real = 29.057750463592832;
                                attribute Ixx : Real = 0.6700441178951808;
                                attribute 'σ_Ixx' : Real = 0.37074144170588635;
                                attribute Iyy : Real = 0.608833254600094;
                                attribute 'σ_Iyy' : Real = 0.3723953238821935;
                                attribute Izz : Real = 0.5718316124111003;
                                attribute 'σ_Izz' : Real = 0.37017423652493897;
                                attribute Ixy : Real = 0.014189034826263084;
                                attribute 'σ_Ixy' : Real = 0.02351283871158888;
                                attribute Ixz : Real = 3.1911920674320034e-4;
                                attribute 'σ_Ixz' : Real = 0.022566176940390956;
                                attribute Iyz : Real = 3.1245873823186523e-4;
                                attribute 'σ_Iyz' : Real = 0.02209918015384651;
                            }
                            part <'C.1.1.4.4.4.4.3'> 'Part 677' {
                                attribute POIconv : String = "+";
                                attribute Ipoint : Boolean = false;
                                attribute mass : Real = 0.46932102445862256;
                                attribute 'σ_mass' : Real = 0.28909372274994966;
                                attribute Cx : Real = 49.872670974582434;
                                attribute 'σ_Cx' : Real = 28.721044428837228;
                                attribute Cy : Real = 49.70479113981128;
                                attribute 'σ_Cy' : Real = 28.23690002309109;
                                attribute Cz : Real = 92.74870436638594;
                                attribute 'σ_Cz' : Real = 29.057750463592832;
                                attribute Ixx : Real = 0.6086401932176692;
                                attribute 'σ_Ixx' : Real = 0.37074144170588635;
                                attribute Iyy : Real = 0.6293695796310088;
                                attribute 'σ_Iyy' : Real = 0.3723953238821935;
                                attribute Izz : Real = 0.5882568806472014;
                                attribute 'σ_Izz' : Real = 0.37017423652493897;
                                attribute Ixy : Real = 0.023473516841990366;
                                attribute 'σ_Ixy' : Real = 0.02351283871158888;
                                attribute Ixz : Real = -0.016705590820211773;
                                attribute 'σ_Ixz' : Real = 0.022566176940390956;
                                attribute Iyz : Real = 0.006308390406972531;
                                attribute 'σ_Iyz' : Real = 0.02209918015384651;
                            }
                            part <'C.1.1.4.4.4.4.4'> 'Part 678' {
                                attribute POIconv : String = "-";
                                attribute Ipoint : Boolean = false;
                                attribute mass : Real = 0.4553706926689483;
                                attribute 'σ_mass' : Real = 0.28909372274994966;
                                attribute Cx : Real = -57.37763452343643;
                                attribute 'σ_Cx' : Real = 28.721044428837228;
                                attribute Cy : Real = -68.77571525983512;
                                attribute 'σ_Cy' : Real = 28.23690002309109;
                                attribute Cz : Real = -14.912679279223084;
                                attribute 'σ_Cz' : Real = 29.057750463592832;
                                attribute Ixx : Real = 0.614334864629171;
                                attribute 'σ_Ixx' : Real = 0.37074144170588635;
                                attribute Iyy : Real = 0.609213258947741;
                                attribute 'σ_Iyy' : Real = 0.3723953238821935;
                                attribute Izz : Real = 0.618478745264341;
                                attribute 'σ_Izz' : Real = 0.37017423652493897;
                                attribute Ixy : Real = 0.0011198755793584724;
                                attribute 'σ_Ixy' : Real = 0.02351283871158888;
                                attribute Ixz : Real = -0.007517029843743193;
                                attribute 'σ_Ixz' : Real = 0.022566176940390956;
                                attribute Iyz : Real = -0.0013814228023789456;
                                attribute 'σ_Iyz' : Real = 0.02209918015384651;
                            }
                        }
                    }
                }
                part <'C.1.1.4.5'> 'Subsystem 15' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.1.4.5.1'> 'Assembly 54' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.5.1.1'> 'Subassembly 194' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.1.1.1'> 'Part 679' {
                                attribute POIconv : String = "-";
                                attribute Ipoint : Boolean = false;
                                attribute mass : Real = 0.5458585424774792;
                                attribute 'σ_mass' : Real = 0.28909372274994966;
                                attribute Cx : Real = 85.50647832453251;
                                attribute 'σ_Cx' : Real = 28.721044428837228;
                                attribute Cy : Real = -29.775803722441196;
                                attribute 'σ_Cy' : Real = 28.23690002309109;
                                attribute Cz : Real = 63.13854418694973;
                                attribute 'σ_Cz' : Real = 29.057750463592832;
                                attribute Ixx : Real = 0.4978284865589333;
                                attribute 'σ_Ixx' : Real = 0.37074144170588635;
                                attribute Iyy : Real = 0.68768193544253;
                                attribute 'σ_Iyy' : Real = 0.3723953238821935;
                                attribute Izz : Real = 0.6788463951038252;
                                attribute 'σ_Izz' : Real = 0.37017423652493897;
                                attribute Ixy : Real = 0.0262114329089291;
                                attribute 'σ_Ixy' : Real = 0.02351283871158888;
                                attribute Ixz : Real = -0.045881555638085866;
                                attribute 'σ_Ixz' : Real = 0.022566176940390956;
                                attribute Iyz : Real = 0.00793722402940337;
                                attribute 'σ_Iyz' : Real = 0.02209918015384651;
                            }
                            part <'C.1.1.4.5.1.1.2'> 'Part 680' {
                                attribute POIconv : String = "-";
                                attribute Ipoint : Boolean = false;
                                attribute mass : Real = 0.21352396419341677;
                                attribute 'σ_mass' : Real = 0.28909372274994966;
                                attribute Cx : Real = 16.390314605087042;
                                attribute 'σ_Cx' : Real = 28.721044428837228;
                                attribute Cy : Real = 72.85699057392776;
                                attribute 'σ_Cy' : Real = 28.23690002309109;
                                attribute Cz : Real = 35.691239358857274;
                                attribute 'σ_Cz' : Real = 29.057750463592832;
                                attribute Ixx : Real = 0.29291505594957146;
                                attribute 'σ_Ixx' : Real = 0.37074144170588635;
                                attribute Iyy : Real = 0.2901555971237649;
                                attribute 'σ_Iyy' : Real = 0.3723953238821935;
                                attribute Izz : Real = 0.3034414030770064;
                                attribute 'σ_Izz' : Real = 0.37017423652493897;
                                attribute Ixy : Real = -0.005479785696470594;
                                attribute 'σ_Ixy' : Real = 0.02351283871158888;
                                attribute Ixz : Real = 0.0028228698849508942;
                                attribute 'σ_Ixz' : Real = 0.022566176940390956;
                                attribute Iyz : Real = -7.937649056078236e-4;
                                attribute 'σ_Iyz' : Real = 0.02209918015384651;
                            }
                            part <'C.1.1.4.5.1.1.3'> 'Part 681' {
                                attribute POIconv : String = "+";
                                attribute Ipoint : Boolean = false;
                                attribute mass : Real = 0.18561021326552146;
                                attribute 'σ_mass' : Real = 0.28909372274994966;
                                attribute Cx : Real = 80.37407421506941;
                                attribute 'σ_Cx' : Real = 28.721044428837228;
                                attribute Cy : Real = 46.43285432830453;
                                attribute 'σ_Cy' : Real = 28.23690002309109;
                                attribute Cz : Real = -53.399051539599895;
                                attribute 'σ_Cz' : Real = 29.057750463592832;
                                attribute Ixx : Real = 0.20761213110324594;
                                attribute 'σ_Ixx' : Real = 0.37074144170588635;
                                attribute Iyy : Real = 0.23129726548037075;
                                attribute 'σ_Iyy' : Real = 0.3723953238821935;
                                attribute Izz : Real = 0.233063851590576;
                                attribute 'σ_Izz' : Real = 0.37017423652493897;
                                attribute Ixy : Real = -0.015489894223154296;
                                attribute 'σ_Ixy' : Real = 0.02351283871158888;
                                attribute Ixz : Real = -0.021740293077604673;
                                attribute 'σ_Ixz' : Real = 0.022566176940390956;
                                attribute Iyz : Real = 0.011055316450912936;
                                attribute 'σ_Iyz' : Real = 0.02209918015384651;
                            }
                            part <'C.1.1.4.5.1.1.4'> 'Part 682' {
                                attribute POIconv : String = "+";
                                attribute Ipoint : Boolean = false;
                                attribute mass : Real = 0.16669526490941644;
                                attribute 'σ_mass' : Real = 0.28909372274994966;
                                attribute Cx : Real = 47.57193187251687;
                                attribute 'σ_Cx' : Real = 28.721044428837228;
                                attribute Cy : Real = -32.69286481663585;
                                attribute 'σ_Cy' : Real = 28.23690002309109;
                                attribute Cz : Real = -92.84564526751637;
                                attribute 'σ_Cz' : Real = 29.057750463592832;
                                attribute Ixx : Real = 0.23316409424887946;
                                attribute 'σ_Ixx' : Real = 0.37074144170588635;
                                attribute Iyy : Real = 0.24638327040536862;
                                attribute 'σ_Iyy' : Real = 0.3723953238821935;
                                attribute Izz : Real = 0.2407007462312049;
                                attribute 'σ_Izz' : Real = 0.37017423652493897;
                                attribute Ixy : Real = -7.4615259516791e-5;
                                attribute 'σ_Ixy' : Real = 0.02351283871158888;
                                attribute Ixz : Real = -0.008670388867699982;
                                attribute 'σ_Ixz' : Real = 0.022566176940390956;
                                attribute Iyz : Real = -7.968590087718936e-5;
                                attribute 'σ_Iyz' : Real = 0.02209918015384651;
                            }
                            part <'C.1.1.4.5.1.1.5'> 'Part 683' {
                                attribute POIconv : String = "+";
                                attribute Ipoint : Boolean = false;
                                attribute mass : Real = 0.78601625076914206;
                                attribute 'σ_mass' : Real = 0.28909372274994966;
                                attribute Cx : Real = -49.19403796084225;
                                attribute 'σ_Cx' : Real = 28.721044428837228;
                                attribute Cy : Real = -53.781661577522755;
                                attribute 'σ_Cy' : Real = 28.23690002309109;
                                attribute Cz : Real = -8.823322132229805;
                                attribute 'σ_Cz' : Real = 29.057750463592832;
                                attribute Ixx : Real = 0.9099732314839822;
                                attribute 'σ_Ixx' : Real = 0.37074144170588635;
                                attribute Iyy : Real = 1.0094120574261891;
                                attribute 'σ_Iyy' : Real = 0.3723953238821935;
                                attribute Izz : Real = 0.8740660846495787;
                                attribute 'σ_Izz' : Real = 0.37017423652493897;
                                attribute Ixy : Real = 0.0076688710440139;
                                attribute 'σ_Ixy' : Real = 0.02351283871158888;
                                attribute Ixz : Real = 0.051714639174203436;
                                attribute 'σ_Ixz' : Real = 0.022566176940390956;
                                attribute Iyz : Real = -0.027952824305149584;
                                attribute 'σ_Iyz' : Real = 0.02209918015384651;
                            }
                        }
                        part <'C.1.1.4.5.1.2'> 'Subassembly 195' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.1.2.1'> 'Part 684' {
                                attribute POIconv : String = "+";
                                attribute Ipoint : Boolean = false;
                                attribute mass : Real = 0.11510431311046705;
                                attribute 'σ_mass' : Real = 0.28909372274994966;
                                attribute Cx : Real = -38.319445541128516;
                                attribute 'σ_Cx' : Real = 28.721044428837228;
                                attribute Cy : Real = 21.279124030843377;
                                attribute 'σ_Cy' : Real = 28.23690002309109;
                                attribute Cz : Real = -53.52545413188636;
                                attribute 'σ_Cz' : Real = 29.057750463592832;
                                attribute Ixx : Real = 0.1634008557308538;
                                attribute 'σ_Ixx' : Real = 0.37074144170588635;
                                attribute Iyy : Real = 0.17583565297390666;
                                attribute 'σ_Iyy' : Real = 0.3723953238821935;
                                attribute Izz : Real = 0.1487024348348355;
                                attribute 'σ_Izz' : Real = 0.37017423652493897;
                                attribute Ixy : Real = 0.01227083893178895;
                                attribute 'σ_Ixy' : Real = 0.02351283871158888;
                                attribute Ixz : Real = -1.5273900575365985e-4;
                                attribute 'σ_Ixz' : Real = 0.022566176940390956;
                                attribute Iyz : Real = -5.596919559221888e-4;
                                attribute 'σ_Iyz' : Real = 0.02209918015384651;
                            }
                            part <'C.1.1.4.5.1.2.2'> 'Part 685' {
                                attribute POIconv : String = "-";
                                attribute Ipoint : Boolean = false;
                                attribute mass : Real = 0.48765380095737054;
                                attribute 'σ_mass' : Real = 0.28909372274994966;
                                attribute Cx : Real = 88.75530292280018;
                                attribute 'σ_Cx' : Real = 28.721044428837228;
                                attribute Cy : Real = -53.729676781222224;
                                attribute 'σ_Cy' : Real = 28.23690002309109;
                                attribute Cz : Real = -29.083979642018676;
                                attribute 'σ_Cz' : Real = 29.057750463592832;
                                attribute Ixx : Real = 0.6681893971636667;
                                attribute 'σ_Ixx' : Real = 0.37074144170588635;
                                attribute Iyy : Real = 0.6474488050827316;
                                attribute 'σ_Iyy' : Real = 0.3723953238821935;
                                attribute Izz : Real = 0.7384423955373283;
                                attribute 'σ_Izz' : Real = 0.37017423652493897;
                                attribute Ixy : Real = 0.0016882295500983567;
                                attribute 'σ_Ixy' : Real = 0.02351283871158888;
                                attribute Ixz : Real = -0.03123287271292473;
                                attribute 'σ_Ixz' : Real = 0.022566176940390956;
                                attribute Iyz : Real = 0.011094145601315178;
                                attribute 'σ_Iyz' : Real = 0.02209918015384651;
                            }
                            part <'C.1.1.4.5.1.2.3'> 'Part 686' {
                                attribute POIconv : String = "-";
                                attribute Ipoint : Boolean = false;
                                attribute mass : Real = 0.07498787941411138;
                                attribute 'σ_mass' : Real = 0.28909372274994966;
                                attribute Cx : Real = 36.137044010683894;
                                attribute 'σ_Cx' : Real = 28.721044428837228;
                                attribute Cy : Real = -25.958018703386188;
                                attribute 'σ_Cy' : Real = 28.23690002309109;
                                attribute Cz : Real = 61.00114309228957;
                                attribute 'σ_Cz' : Real = 29.057750463592832;
                                attribute Ixx : Real = 0.08171020163059381;
                                attribute 'σ_Ixx' : Real = 0.37074144170588635;
                                attribute Iyy : Real = 0.08785904546882935;
                                attribute 'σ_Iyy' : Real = 0.3723953238821935;
                                attribute Izz : Real = 0.07613759001625761;
                                attribute 'σ_Izz' : Real = 0.37017423652493897;
                                attribute Ixy : Real = -0.0013674459016115273;
                                attribute 'σ_Ixy' : Real = 0.02351283871158888;
                                attribute Ixz : Real = 0.005853186686075328;
                                attribute 'σ_Ixz' : Real = 0.022566176940390956;
                                attribute Iyz : Real = 0.007034409904021212;
                                attribute 'σ_Iyz' : Real = 0.02209918015384651;
                            }
                            part <'C.1.1.4.5.1.2.4'> 'Part 687' {
                                attribute POIconv : String = "+";
                                attribute Ipoint : Boolean = false;
                                attribute mass : Real = 0.3603147188061848;
                                attribute 'σ_mass' : Real = 0.28909372274994966;
                                attribute Cx : Real = -0.9015227667987347;
                                attribute 'σ_Cx' : Real = 28.721044428837228;
                                attribute Cy : Real = -80.43021969497204;
                                attribute 'σ_Cy' : Real = 28.23690002309109;
                                attribute Cz : Real = -43.28553429804742;
                                attribute 'σ_Cz' : Real = 29.057750463592832;
                                attribute Ixx : Real = 0.42328771570847906;
                                attribute 'σ_Ixx' : Real = 0.37074144170588635;
                                attribute Iyy : Real = 0.49628968896180703;
                                attribute 'σ_Iyy' : Real = 0.3723953238821935;
                                attribute Izz : Real = 0.4152256140762518;
                                attribute 'σ_Izz' : Real = 0.37017423652493897;
                                attribute Ixy : Real = -0.00422843924200126;
                                attribute 'σ_Ixy' : Real = 0.02351283871158888;
                                attribute Ixz : Real = 0.017556848456288375;
                                attribute 'σ_Ixz' : Real = 0.022566176940390956;
                                attribute Iyz : Real = 0.02201346237109579;
                                attribute 'σ_Iyz' : Real = 0.02209918015384651;
                            }
                            part <'C.1.1.4.5.1.2.5'> 'Part 688' {
                                attribute POIconv : String = "-";
                                attribute Ipoint : Boolean = false;
                                attribute mass : Real = 0.055790534285828475;
                                attribute 'σ_mass' : Real = 0.28909372274994966;
                                attribute Cx : Real = -20.768115622922778;
                                attribute 'σ_Cx' : Real = 28.721044428837228;
                                attribute Cy : Real = -97.4263054318726;
                                attribute 'σ_Cy' : Real = 28.23690002309109;
                                attribute Cz : Real = -62.12288639508188;
                                attribute 'σ_Cz' : Real = 29.057750463592832;
                                attribute Ixx : Real = 0.06589443743307816;
                                attribute 'σ_Ixx' : Real = 0.37074144170588635;
                                attribute Iyy : Real = 0.07251637448648951;
                                attribute 'σ_Iyy' : Real = 0.3723953238821935;
                                attribute Izz : Real = 0.07593302708954004;
                                attribute 'σ_Izz' : Real = 0.37017423652493897;
                                attribute Ixy : Real = 0.005877918236308498;
                                attribute 'σ_Ixy' : Real = 0.02351283871158888;
                                attribute Ixz : Real = 0.0043300084157293205;
                                attribute 'σ_Ixz' : Real = 0.022566176940390956;
                                attribute Iyz : Real = -0.0014569351338486751;
                                attribute 'σ_Iyz' : Real = 0.02209918015384651;
                            }
                        }
                    }
                    part <'C.1.1.4.5.2'> 'Assembly 55' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.5.2.1'> 'Subassembly 196' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.2.1.1'> 'Part 689' {
                                attribute POIconv : String = "+";
                                attribute Ipoint : Boolean = false;
                                attribute mass : Real = 0.778733261555899;
                                attribute 'σ_mass' : Real = 0.28909372274994966;
                                attribute Cx : Real = 82.77139770798385;
                                attribute 'σ_Cx' : Real = 28.721044428837228;
                                attribute Cy : Real = 14.387979498133063;
                                attribute 'σ_Cy' : Real = 28.23690002309109;
                                attribute Cz : Real = 63.029924081638455;
                                attribute 'σ_Cz' : Real = 29.057750463592832;
                                attribute Ixx : Real = 0.9637121102912828;
                                attribute 'σ_Ixx' : Real = 0.37074144170588635;
                                attribute Iyy : Real = 0.9234867828364582;
                                attribute 'σ_Iyy' : Real = 0.3723953238821935;
                                attribute Izz : Real = 0.9462326990280726;
                                attribute 'σ_Izz' : Real = 0.37017423652493897;
                                attribute Ixy : Real = 0.014949304684276212;
                                attribute 'σ_Ixy' : Real = 0.02351283871158888;
                                attribute Ixz : Real = 0.01339002780609833;
                                attribute 'σ_Ixz' : Real = 0.022566176940390956;
                                attribute Iyz : Real = 0.034313812118543674;
                                attribute 'σ_Iyz' : Real = 0.02209918015384651;
                            }
                            part <'C.1.1.4.5.2.1.2'> 'Part 690' {
                                attribute POIconv : String = "+";
                                attribute Ipoint : Boolean = false;
                                attribute mass : Real = 0.9568621058263816;
                                attribute 'σ_mass' : Real = 0.28909372274994966;
                                attribute Cx : Real = -33.973609656095505;
                                attribute 'σ_Cx' : Real = 28.721044428837228;
                                attribute Cy : Real = 59.473318979144096;
                                attribute 'σ_Cy' : Real = 28.23690002309109;
                                attribute Cz : Real = 48.99963201023638;
                                attribute 'σ_Cz' : Real = 29.057750463592832;
                                attribute Ixx : Real = 1.1343299166749816;
                                attribute 'σ_Ixx' : Real = 0.37074144170588635;
                                attribute Iyy : Real = 1.2186767709521567;
                                attribute 'σ_Iyy' : Real = 0.3723953238821935;
                                attribute Izz : Real = 1.1159097953459405;
                                attribute 'σ_Izz' : Real = 0.37017423652493897;
                                attribute Ixy : Real = 0.013858432866820255;
                                attribute 'σ_Ixy' : Real = 0.02351283871158888;
                                attribute Ixz : Real = -0.08543633398883976;
                                attribute 'σ_Ixz' : Real = 0.022566176940390956;
                                attribute Iyz : Real = 0.00432979193668491;
                                attribute 'σ_Iyz' : Real = 0.02209918015384651;
                            }
                            part <'C.1.1.4.5.2.1.3'> 'Part 691' {
                                attribute POIconv : String = "+";
                                attribute Ipoint : Boolean = false;
                                attribute mass : Real = 0.4740491446400993;
                                attribute 'σ_mass' : Real = 0.28909372274994966;
                                attribute Cx : Real = 46.819713711738586;
                                attribute 'σ_Cx' : Real = 28.721044428837228;
                                attribute Cy : Real = -39.33364422991872;
                                attribute 'σ_Cy' : Real = 28.23690002309109;
                                attribute Cz : Real = -93.95119771361351;
                                attribute 'σ_Cz' : Real = 29.057750463592832;
                                attribute Ixx : Real = 0.5342479957281323;
                                attribute 'σ_Ixx' : Real = 0.37074144170588635;
                                attribute Iyy : Real = 0.5216757153673918;
                                attribute 'σ_Iyy' : Real = 0.3723953238821935;
                                attribute Izz : Real = 0.48682968142480904;
                                attribute 'σ_Izz' : Real = 0.37017423652493897;
                                attribute Ixy : Real = -0.003303742435147597;
                                attribute 'σ_Ixy' : Real = 0.02351283871158888;
                                attribute Ixz : Real = 0.03916557439190065;
                                attribute 'σ_Ixz' : Real = 0.022566176940390956;
                                attribute Iyz : Real = -0.0246545484429605;
                                attribute 'σ_Iyz' : Real = 0.02209918015384651;
                            }
                            part <'C.1.1.4.5.2.1.4'> 'Part 692' {
                                attribute POIconv : String = "-";
                                attribute Ipoint : Boolean = false;
                                attribute mass : Real = 0.45629805433447473;
                                attribute 'σ_mass' : Real = 0.28909372274994966;
                                attribute Cx : Real = -72.88461932912469;
                                attribute 'σ_Cx' : Real = 28.721044428837228;
                                attribute Cy : Real = -59.215825563296676;
                                attribute 'σ_Cy' : Real = 28.23690002309109;
                                attribute Cz : Real = -78.43862376175821;
                                attribute 'σ_Cz' : Real = 29.057750463592832;
                                attribute Ixx : Real = 0.5405471609747734;
                                attribute 'σ_Ixx' : Real = 0.37074144170588635;
                                attribute Iyy : Real = 0.6351644818589913;
                                attribute 'σ_Iyy' : Real = 0.3723953238821935;
                                attribute Izz : Real = 0.5921371356326721;
                                attribute 'σ_Izz' : Real = 0.37017423652493897;
                                attribute Ixy : Real = -0.061133062137915146;
                                attribute 'σ_Ixy' : Real = 0.02351283871158888;
                                attribute Ixz : Real = 0.0029286774257625105;
                                attribute 'σ_Ixz' : Real = 0.022566176940390956;
                                attribute Iyz : Real = 0.025116439907442695;
                                attribute 'σ_Iyz' : Real = 0.02209918015384651;
                            }
                        }
                        part <'C.1.1.4.5.2.2'> 'Subassembly 197' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.2.2.1'> 'Part 693' {
                                attribute POIconv : String = "-";
                                attribute Ipoint : Boolean = false;
                                attribute mass : Real = 0.176639727151487;
                                attribute 'σ_mass' : Real = 0.28909372274994966;
                                attribute Cx : Real = 90.512166172266;
                                attribute 'σ_Cx' : Real = 28.721044428837228;
                                attribute Cy : Real = -67.1765451785177;
                                attribute 'σ_Cy' : Real = 28.23690002309109;
                                attribute Cz : Real = -32.116163754835725;
                                attribute 'σ_Cz' : Real = 29.057750463592832;
                                attribute Ixx : Real = 0.1964134101628636;
                                attribute 'σ_Ixx' : Real = 0.37074144170588635;
                                attribute Iyy : Real = 0.18249680480064884;
                                attribute 'σ_Iyy' : Real = 0.3723953238821935;
                                attribute Izz : Real = 0.21192236259477626;
                                attribute 'σ_Izz' : Real = 0.37017423652493897;
                                attribute Ixy : Real = -0.006972638532967788;
                                attribute 'σ_Ixy' : Real = 0.02351283871158888;
                                attribute Ixz : Real = -7.993330649466419e-4;
                                attribute 'σ_Ixz' : Real = 0.022566176940390956;
                                attribute Iyz : Real = 0.014203366189068386;
                                attribute 'σ_Iyz' : Real = 0.02209918015384651;
                            }
                            part <'C.1.1.4.5.2.2.2'> 'Part 694' {
                                attribute POIconv : String = "-";
                                attribute Ipoint : Boolean = false;
                                attribute mass : Real = 0.1732897980902344;
                                attribute 'σ_mass' : Real = 0.28909372274994966;
                                attribute Cx : Real = -10.115628223866224;
                                attribute 'σ_Cx' : Real = 28.721044428837228;
                                attribute Cy : Real = 24.359602946788073;
                                attribute 'σ_Cy' : Real = 28.23690002309109;
                                attribute Cz : Real = -7.20491842366755;
                                attribute 'σ_Cz' : Real = 29.057750463592832;
                                attribute Ixx : Real = 0.19225071350698547;
                                attribute 'σ_Ixx' : Real = 0.37074144170588635;
                                attribute Iyy : Real = 0.18519781290997242;
                                attribute 'σ_Iyy' : Real = 0.3723953238821935;
                                attribute Izz : Real = 0.22102352453135873;
                                attribute 'σ_Izz' : Real = 0.37017423652493897;
                                attribute Ixy : Real = 0.0038856935081703872;
                                attribute 'σ_Ixy' : Real = 0.02351283871158888;
                                attribute Ixz : Real = -0.0019131659232851856;
                                attribute 'σ_Ixz' : Real = 0.022566176940390956;
                                attribute Iyz : Real = -0.011870926596134954;
                                attribute 'σ_Iyz' : Real = 0.02209918015384651;
                            }
                            part <'C.1.1.4.5.2.2.3'> 'Part 695' {
                                attribute POIconv : String = "-";
                                attribute Ipoint : Boolean = false;
                                attribute mass : Real = 0.6116996244110633;
                                attribute 'σ_mass' : Real = 0.28909372274994966;
                                attribute Cx : Real = -89.3896862398833;
                                attribute 'σ_Cx' : Real = 28.721044428837228;
                                attribute Cy : Real = 6.947811087593436;
                                attribute 'σ_Cy' : Real = 28.23690002309109;
                                attribute Cz : Real = -29.203622695058584;
                                attribute 'σ_Cz' : Real = 29.057750463592832;
                                attribute Ixx : Real = 0.7437495047419891;
                                attribute 'σ_Ixx' : Real = 0.37074144170588635;
                                attribute Iyy : Real = 0.7286839268660732;
                                attribute 'σ_Iyy' : Real = 0.3723953238821935;
                                attribute Izz : Real = 0.6947609493181452;
                                attribute 'σ_Izz' : Real = 0.37017423652493897;
                                attribute Ixy : Real = -7.689128615830149e-4;
                                attribute 'σ_Ixy' : Real = 0.02351283871158888;
                                attribute Ixz : Real = 0.001688171696741651;
                                attribute 'σ_Ixz' : Real = 0.022566176940390956;
                                attribute Iyz : Real = 0.02713605064301431;
                                attribute 'σ_Iyz' : Real = 0.02209918015384651;
                            }
                        }
                        part <'C.1.1.4.5.2.3'> 'Subassembly 198' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.2.3.1'> 'Part 696' {
                                attribute POIconv : String = "+";
                                attribute Ipoint : Boolean = false;
                                attribute mass : Real = 0.6614907957387622;
                                attribute 'σ_mass' : Real = 0.28909372274994966;
                                attribute Cx : Real = -43.55907682329416;
                                attribute 'σ_Cx' : Real = 28.721044428837228;
                                attribute Cy : Real = -15.579560492187738;
                                attribute 'σ_Cy' : Real = 28.23690002309109;
                                attribute Cz : Real = -65.22868028841913;
                                attribute 'σ_Cz' : Real = 29.057750463592832;
                                attribute Ixx : Real = 0.9727921600997239;
                                attribute 'σ_Ixx' : Real = 0.37074144170588635;
                                attribute Iyy : Real = 0.924180403152381;
                                attribute 'σ_Iyy' : Real = 0.3723953238821935;
                                attribute Izz : Real = 0.8204448402397868;
                                attribute 'σ_Izz' : Real = 0.37017423652493897;
                                attribute Ixy : Real = -0.11269090499769062;
                                attribute 'σ_Ixy' : Real = 0.02351283871158888;
                                attribute Ixz : Real = -0.009794734069918251;
                                attribute 'σ_Ixz' : Real = 0.022566176940390956;
                                attribute Iyz : Real = -0.010126621874253807;
                                attribute 'σ_Iyz' : Real = 0.02209918015384651;
                            }
                            part <'C.1.1.4.5.2.3.2'> 'Part 697' {
                                attribute POIconv : String = "+";
                                attribute Ipoint : Boolean = false;
                                attribute mass : Real = 0.7561861641407013;
                                attribute 'σ_mass' : Real = 0.28909372274994966;
                                attribute Cx : Real = 83.52324776351452;
                                attribute 'σ_Cx' : Real = 28.721044428837228;
                                attribute Cy : Real = -76.49587052874267;
                                attribute 'σ_Cy' : Real = 28.23690002309109;
                                attribute Cz : Real = -39.48756381869316;
                                attribute 'σ_Cz' : Real = 29.057750463592832;
                                attribute Ixx : Real = 0.8969279359394727;
                                attribute 'σ_Ixx' : Real = 0.37074144170588635;
                                attribute Iyy : Real = 0.9597142287606878;
                                attribute 'σ_Iyy' : Real = 0.3723953238821935;
                                attribute Izz : Real = 1.1408890955432698;
                                attribute 'σ_Izz' : Real = 0.37017423652493897;
                                attribute Ixy : Real = -0.022682979675318883;
                                attribute 'σ_Ixy' : Real = 0.02351283871158888;
                                attribute Ixz : Real = -0.011863204884777661;
                                attribute 'σ_Ixz' : Real = 0.022566176940390956;
                                attribute Iyz : Real = 0.02362798455896486;
                                attribute 'σ_Iyz' : Real = 0.02209918015384651;
                            }
                            part <'C.1.1.4.5.2.3.3'> 'Part 698' {
                                attribute POIconv : String = "+";
                                attribute Ipoint : Boolean = false;
                                attribute mass : Real = 0.6198430245679337;
                                attribute 'σ_mass' : Real = 0.28909372274994966;
                                attribute Cx : Real = -46.22788834385574;
                                attribute 'σ_Cx' : Real = 28.721044428837228;
                                attribute Cy : Real = -80.63847618177533;
                                attribute 'σ_Cy' : Real = 28.23690002309109;
                                attribute Cz : Real = -69.16550188325346;
                                attribute 'σ_Cz' : Real = 29.057750463592832;
                                attribute Ixx : Real = 0.8143033547565512;
                                attribute 'σ_Ixx' : Real = 0.37074144170588635;
                                attribute Iyy : Real = 0.8159492862870545;
                                attribute 'σ_Iyy' : Real = 0.3723953238821935;
                                attribute Izz : Real = 0.7647472353363632;
                                attribute 'σ_Izz' : Real = 0.37017423652493897;
                                attribute Ixy : Real = -0.036055034929605496;
                                attribute 'σ_Ixy' : Real = 0.02351283871158888;
                                attribute Ixz : Real = -0.0017598684973048487;
                                attribute 'σ_Ixz' : Real = 0.022566176940390956;
                                attribute Iyz : Real = -0.0053525253364198385;
                                attribute 'σ_Iyz' : Real = 0.02209918015384651;
                            }
                            part <'C.1.1.4.5.2.3.4'> 'Part 699' {
                                attribute POIconv : String = "-";
                                attribute Ipoint : Boolean = false;
                                attribute mass : Real = 0.9360021412963979;
                                attribute 'σ_mass' : Real = 0.28909372274994966;
                                attribute Cx : Real = -94.25285863690078;
                                attribute 'σ_Cx' : Real = 28.721044428837228;
                                attribute Cy : Real = -47.94981596060097;
                                attribute 'σ_Cy' : Real = 28.23690002309109;
                                attribute Cz : Real = -88.74891842715442;
                                attribute 'σ_Cz' : Real = 29.057750463592832;
                                attribute Ixx : Real = 1.034879848746387;
                                attribute 'σ_Ixx' : Real = 0.37074144170588635;
                                attribute Iyy : Real = 1.053463114362619;
                                attribute 'σ_Iyy' : Real = 0.3723953238821935;
                                attribute Izz : Real = 1.1720665682033824;
                                attribute 'σ_Izz' : Real = 0.37017423652493897;
                                attribute Ixy : Real = 0.11517385564587376;
                                attribute 'σ_Ixy' : Real = 0.02351283871158888;
                                attribute Ixz : Real = -0.03666029813430868;
                                attribute 'σ_Ixz' : Real = 0.022566176940390956;
                                attribute Iyz : Real = 0.02651653028966892;
                                attribute 'σ_Iyz' : Real = 0.02209918015384651;
                            }
                            part <'C.1.1.4.5.2.3.5'> 'Part 700' {
                                attribute POIconv : String = "-";
                                attribute Ipoint : Boolean = false;
                                attribute mass : Real = 0.7034139408560004;
                                attribute 'σ_mass' : Real = 0.28909372274994966;
                                attribute Cx : Real = -43.51687952876091;
                                attribute 'σ_Cx' : Real = 28.721044428837228;
                                attribute Cy : Real = 57.71491201594472;
                                attribute 'σ_Cy' : Real = 28.23690002309109;
                                attribute Cz : Real = 27.91465916670859;
                                attribute 'σ_Cz' : Real = 29.057750463592832;
                                attribute Ixx : Real = 0.817711499665778;
                                attribute 'σ_Ixx' : Real = 0.37074144170588635;
                                attribute Iyy : Real = 0.8675304354241302;
                                attribute 'σ_Iyy' : Real = 0.3723953238821935;
                                attribute Izz : Real = 0.8085704785353787;
                                attribute 'σ_Izz' : Real = 0.37017423652493897;
                                attribute Ixy : Real = 0.016806881986910507;
                                attribute 'σ_Ixy' : Real = 0.02351283871158888;
                                attribute Ixz : Real = -0.006094909929318314;
                                attribute 'σ_Ixz' : Real = 0.022566176940390956;
                                attribute Iyz : Real = -0.023328592166564986;
                                attribute 'σ_Iyz' : Real = 0.02209918015384651;
                            }
                        }
                        part <'C.1.1.4.5.2.4'> 'Subassembly 199' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.2.4.1'> 'Part 701' {
                                attribute POIconv : String = "+";
                                attribute Ipoint : Boolean = false;
                                attribute mass : Real = 0.21574145847093315;
                                attribute 'σ_mass' : Real = 0.28909372274994966;
                                attribute Cx : Real = 66.00678227841854;
                                attribute 'σ_Cx' : Real = 28.721044428837228;
                                attribute Cy : Real = 45.6171250436455;
                                attribute 'σ_Cy' : Real = 28.23690002309109;
                                attribute Cz : Real = 21.227593533694744;
                                attribute 'σ_Cz' : Real = 29.057750463592832;
                                attribute Ixx : Real = 0.31183894636364573;
                                attribute 'σ_Ixx' : Real = 0.37074144170588635;
                                attribute Iyy : Real = 0.3431571151566759;
                                attribute 'σ_Iyy' : Real = 0.3723953238821935;
                                attribute Izz : Real = 0.3032670903373876;
                                attribute 'σ_Izz' : Real = 0.37017423652493897;
                                attribute Ixy : Real = 0.021770134391957525;
                                attribute 'σ_Ixy' : Real = 0.02351283871158888;
                                attribute Ixz : Real = 0.00259655354499567;
                                attribute 'σ_Ixz' : Real = 0.022566176940390956;
                                attribute Iyz : Real = -7.534296556114815e-4;
                                attribute 'σ_Iyz' : Real = 0.02209918015384651;
                            }
                            part <'C.1.1.4.5.2.4.2'> 'Part 702' {
                                attribute POIconv : String = "-";
                                attribute Ipoint : Boolean = false;
                                attribute mass : Real = 0.952474264848046;
                                attribute 'σ_mass' : Real = 0.28909372274994966;
                                attribute Cx : Real = -37.06433824263513;
                                attribute 'σ_Cx' : Real = 28.721044428837228;
                                attribute Cy : Real = 7.076812628656626;
                                attribute 'σ_Cy' : Real = 28.23690002309109;
                                attribute Cz : Real = 87.21284228377044;
                                attribute 'σ_Cz' : Real = 29.057750463592832;
                                attribute Ixx : Real = 0.891986830749284;
                                attribute 'σ_Ixx' : Real = 0.37074144170588635;
                                attribute Iyy : Real = 0.8684200016430845;
                                attribute 'σ_Iyy' : Real = 0.3723953238821935;
                                attribute Izz : Real = 0.8690985685725223;
                                attribute 'σ_Izz' : Real = 0.37017423652493897;
                                attribute Ixy : Real = 0.0016582478297530044;
                                attribute 'σ_Ixy' : Real = 0.02351283871158888;
                                attribute Ixz : Real = 0.004895732437623076;
                                attribute 'σ_Ixz' : Real = 0.022566176940390956;
                                attribute Iyz : Real = 3.60654029876336e-4;
                                attribute 'σ_Iyz' : Real = 0.02209918015384651;
                            }
                            part <'C.1.1.4.5.2.4.3'> 'Part 703' {
                                attribute POIconv : String = "-";
                                attribute Ipoint : Boolean = false;
                                attribute mass : Real = 0.5700481246972923;
                                attribute 'σ_mass' : Real = 0.28909372274994966;
                                attribute Cx : Real = -27.204722445458174;
                                attribute 'σ_Cx' : Real = 28.721044428837228;
                                attribute Cy : Real = 97.97604377381504;
                                attribute 'σ_Cy' : Real = 28.23690002309109;
                                attribute Cz : Real = 45.102889044210315;
                                attribute 'σ_Cz' : Real = 29.057750463592832;
                                attribute Ixx : Real = 0.8122376664768497;
                                attribute 'σ_Ixx' : Real = 0.37074144170588635;
                                attribute Iyy : Real = 0.8027276521243892;
                                attribute 'σ_Iyy' : Real = 0.3723953238821935;
                                attribute Izz : Real = 0.8276223382317585;
                                attribute 'σ_Izz' : Real = 0.37017423652493897;
                                attribute Ixy : Real = -0.00364346393596255;
                                attribute 'σ_Ixy' : Real = 0.02351283871158888;
                                attribute Ixz : Real = 0.020482219314112825;
                                attribute 'σ_Ixz' : Real = 0.022566176940390956;
                                attribute Iyz : Real = -0.003240294290503124;
                                attribute 'σ_Iyz' : Real = 0.02209918015384651;
                            }
                        }
                    }
                    part <'C.1.1.4.5.3'> 'Assembly 56' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.5.3.1'> 'Subassembly 200' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.3.1.1'> 'Part 704' {
                                attribute POIconv : String = "-";
                                attribute Ipoint : Boolean = false;
                                attribute mass : Real = 0.6181363071794622;
                                attribute 'σ_mass' : Real = 0.28909372274994966;
                                attribute Cx : Real = -88.38436212390661;
                                attribute 'σ_Cx' : Real = 28.721044428837228;
                                attribute Cy : Real = -54.767060512676835;
                                attribute 'σ_Cy' : Real = 28.23690002309109;
                                attribute Cz : Real = 0.7699199020862579;
                                attribute 'σ_Cz' : Real = 29.057750463592832;
                                attribute Ixx : Real = 0.7105811457485497;
                                attribute 'σ_Ixx' : Real = 0.37074144170588635;
                                attribute Iyy : Real = 0.7058748745836105;
                                attribute 'σ_Iyy' : Real = 0.3723953238821935;
                                attribute Izz : Real = 0.8218448367932933;
                                attribute 'σ_Izz' : Real = 0.37017423652493897;
                                attribute Ixy : Real = -0.0024425930359994723;
                                attribute 'σ_Ixy' : Real = 0.02351283871158888;
                                attribute Ixz : Real = 0.05619118465805949;
                                attribute 'σ_Ixz' : Real = 0.022566176940390956;
                                attribute Iyz : Real = 0.007311057667664491;
                                attribute 'σ_Iyz' : Real = 0.02209918015384651;
                            }
                            part <'C.1.1.4.5.3.1.2'> 'Part 705' {
                                attribute POIconv : String = "+";
                                attribute Ipoint : Boolean = false;
                                attribute mass : Real = 0.01861351730534807;
                                attribute 'σ_mass' : Real = 0.28909372274994966;
                                attribute Cx : Real = -28.513810643926263;
                                attribute 'σ_Cx' : Real = 28.721044428837228;
                                attribute Cy : Real = 21.655534906312823;
                                attribute 'σ_Cy' : Real = 28.23690002309109;
                                attribute Cz : Real = 36.31605035625398;
                                attribute 'σ_Cz' : Real = 29.057750463592832;
                                attribute Ixx : Real = 0.022980722775626284;
                                attribute 'σ_Ixx' : Real = 0.37074144170588635;
                                attribute Iyy : Real = 0.023646280808303666;
                                attribute 'σ_Iyy' : Real = 0.3723953238821935;
                                attribute Izz : Real = 0.020702241025586227;
                                attribute 'σ_Izz' : Real = 0.37017423652493897;
                                attribute Ixy : Real = 0.001743042595745284;
                                attribute 'σ_Ixy' : Real = 0.02351283871158888;
                                attribute Ixz : Real = -9.144028456923883e-4;
                                attribute 'σ_Ixz' : Real = 0.022566176940390956;
                                attribute Iyz : Real = -5.6003885499551e-5;
                                attribute 'σ_Iyz' : Real = 0.02209918015384651;
                            }
                            part <'C.1.1.4.5.3.1.3'> 'Part 706' {
                                attribute POIconv : String = "-";
                                attribute Ipoint : Boolean = false;
                                attribute mass : Real = 0.24543188220774756;
                                attribute 'σ_mass' : Real = 0.28909372274994966;
                                attribute Cx : Real = -38.11907307244837;
                                attribute 'σ_Cx' : Real = 28.721044428837228;
                                attribute Cy : Real = -80.86219783872366;
                                attribute 'σ_Cy' : Real = 28.23690002309109;
                                attribute Cz : Real = 18.341547856107354;
                                attribute 'σ_Cz' : Real = 29.057750463592832;
                                attribute Ixx : Real = 0.2960881970694699;
                                attribute 'σ_Ixx' : Real = 0.37074144170588635;
                                attribute Iyy : Real = 0.2820275713494834;
                                attribute 'σ_Iyy' : Real = 0.3723953238821935;
                                attribute Izz : Real = 0.26660346410223534;
                                attribute 'σ_Izz' : Real = 0.37017423652493897;
                                attribute Ixy : Real = 0.0014772203017352108;
                                attribute 'σ_Ixy' : Real = 0.02351283871158888;
                                attribute Ixz : Real = 0.007203635064748598;
                                attribute 'σ_Ixz' : Real = 0.022566176940390956;
                                attribute Iyz : Real = 0.020799571811916773;
                                attribute 'σ_Iyz' : Real = 0.02209918015384651;
                            }
                            part <'C.1.1.4.5.3.1.4'> 'Part 707' {
                                attribute POIconv : String = "+";
                                attribute Ipoint : Boolean = false;
                                attribute mass : Real = 0.9872217106800526;
                                attribute 'σ_mass' : Real = 0.28909372274994966;
                                attribute Cx : Real = -35.02365229651332;
                                attribute 'σ_Cx' : Real = 28.721044428837228;
                                attribute Cy : Real = -54.62926956824958;
                                attribute 'σ_Cy' : Real = 28.23690002309109;
                                attribute Cz : Real = -49.230253556743264;
                                attribute 'σ_Cz' : Real = 29.057750463592832;
                                attribute Ixx : Real = 1.311390835126343;
                                attribute 'σ_Ixx' : Real = 0.37074144170588635;
                                attribute Iyy : Real = 1.3590790973440527;
                                attribute 'σ_Iyy' : Real = 0.3723953238821935;
                                attribute Izz : Real = 1.2927278947398129;
                                attribute 'σ_Izz' : Real = 0.37017423652493897;
                                attribute Ixy : Real = 0.020626965163901993;
                                attribute 'σ_Ixy' : Real = 0.02351283871158888;
                                attribute Ixz : Real = -0.05513576322599253;
                                attribute 'σ_Ixz' : Real = 0.022566176940390956;
                                attribute Iyz : Real = 0.13572115752784122;
                                attribute 'σ_Iyz' : Real = 0.02209918015384651;
                            }
                        }
                        part <'C.1.1.4.5.3.2'> 'Subassembly 201' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.3.2.1'> 'Part 708' {
                                attribute POIconv : String = "-";
                                attribute Ipoint : Boolean = false;
                                attribute mass : Real = 0.5766528496164829;
                                attribute 'σ_mass' : Real = 0.28909372274994966;
                                attribute Cx : Real = 63.95033188164234;
                                attribute 'σ_Cx' : Real = 28.721044428837228;
                                attribute Cy : Real = -8.190266601741314;
                                attribute 'σ_Cy' : Real = 28.23690002309109;
                                attribute Cz : Real = -14.481313759461045;
                                attribute 'σ_Cz' : Real = 29.057750463592832;
                                attribute Ixx : Real = 0.734019955825562;
                                attribute 'σ_Ixx' : Real = 0.37074144170588635;
                                attribute Iyy : Real = 0.7977772828222424;
                                attribute 'σ_Iyy' : Real = 0.3723953238821935;
                                attribute Izz : Real = 0.6566883170093378;
                                attribute 'σ_Izz' : Real = 0.37017423652493897;
                                attribute Ixy : Real = -0.050267614553132646;
                                attribute 'σ_Ixy' : Real = 0.02351283871158888;
                                attribute Ixz : Real = 0.020581594802523813;
                                attribute 'σ_Ixz' : Real = 0.022566176940390956;
                                attribute Iyz : Real = -0.020762292104751327;
                                attribute 'σ_Iyz' : Real = 0.02209918015384651;
                            }
                            part <'C.1.1.4.5.3.2.2'> 'Part 709' {
                                attribute POIconv : String = "-";
                                attribute Ipoint : Boolean = false;
                                attribute mass : Real = 0.11901163538405672;
                                attribute 'σ_mass' : Real = 0.28909372274994966;
                                attribute Cx : Real = -64.35482897795737;
                                attribute 'σ_Cx' : Real = 28.721044428837228;
                                attribute Cy : Real = 75.11381502263248;
                                attribute 'σ_Cy' : Real = 28.23690002309109;
                                attribute Cz : Real = 81.48970929905772;
                                attribute 'σ_Cz' : Real = 29.057750463592832;
                                attribute Ixx : Real = 0.1444977929943766;
                                attribute 'σ_Ixx' : Real = 0.37074144170588635;
                                attribute Iyy : Real = 0.15691711235480899;
                                attribute 'σ_Iyy' : Real = 0.3723953238821935;
                                attribute Izz : Real = 0.15886247791679445;
                                attribute 'σ_Izz' : Real = 0.37017423652493897;
                                attribute Ixy : Real = 0.004017344344703303;
                                attribute 'σ_Ixy' : Real = 0.02351283871158888;
                                attribute Ixz : Real = -0.002251255957500059;
                                attribute 'σ_Ixz' : Real = 0.022566176940390956;
                                attribute Iyz : Real = 0.0015117292708002733;
                                attribute 'σ_Iyz' : Real = 0.02209918015384651;
                            }
                            part <'C.1.1.4.5.3.2.3'> 'Part 710' {
                                attribute POIconv : String = "+";
                                attribute Ipoint : Boolean = false;
                                attribute mass : Real = 0.6408512641561683;
                                attribute 'σ_mass' : Real = 0.28909372274994966;
                                attribute Cx : Real = 44.71265971660614;
                                attribute 'σ_Cx' : Real = 28.721044428837228;
                                attribute Cy : Real = -77.49618762172759;
                                attribute 'σ_Cy' : Real = 28.23690002309109;
                                attribute Cz : Real = -30.110358400270343;
                                attribute 'σ_Cz' : Real = 29.057750463592832;
                                attribute Ixx : Real = 0.7779300632193954;
                                attribute 'σ_Ixx' : Real = 0.37074144170588635;
                                attribute Iyy : Real = 0.7586447735828574;
                                attribute 'σ_Iyy' : Real = 0.3723953238821935;
                                attribute Izz : Real = 0.8495913707678654;
                                attribute 'σ_Izz' : Real = 0.37017423652493897;
                                attribute Ixy : Real = -0.08973762475708297;
                                attribute 'σ_Ixy' : Real = 0.02351283871158888;
                                attribute Ixz : Real = 0.03242582577274904;
                                attribute 'σ_Ixz' : Real = 0.022566176940390956;
                                attribute Iyz : Real = -0.03169693861486331;
                                attribute 'σ_Iyz' : Real = 0.02209918015384651;
                            }
                        }
                        part <'C.1.1.4.5.3.3'> 'Subassembly 202' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.3.3.1'> 'Part 711' {
                                attribute POIconv : String = "-";
                                attribute Ipoint : Boolean = false;
                                attribute mass : Real = 0.5243686088677496;
                                attribute 'σ_mass' : Real = 0.28909372274994966;
                                attribute Cx : Real = 77.82237767241895;
                                attribute 'σ_Cx' : Real = 28.721044428837228;
                                attribute Cy : Real = 50.653414241969585;
                                attribute 'σ_Cy' : Real = 28.23690002309109;
                                attribute Cz : Real = 24.862894974648952;
                                attribute 'σ_Cz' : Real = 29.057750463592832;
                                attribute Ixx : Real = 0.49970700822072517;
                                attribute 'σ_Ixx' : Real = 0.37074144170588635;
                                attribute Iyy : Real = 0.6667928010168054;
                                attribute 'σ_Iyy' : Real = 0.3723953238821935;
                                attribute Izz : Real = 0.6677517834265364;
                                attribute 'σ_Izz' : Real = 0.37017423652493897;
                                attribute Ixy : Real = 0.011275203244257423;
                                attribute 'σ_Ixy' : Real = 0.02351283871158888;
                                attribute Ixz : Real = -0.04956096849399768;
                                attribute 'σ_Ixz' : Real = 0.022566176940390956;
                                attribute Iyz : Real = 0.0037794841444387553;
                                attribute 'σ_Iyz' : Real = 0.02209918015384651;
                            }
                            part <'C.1.1.4.5.3.3.2'> 'Part 712' {
                                attribute POIconv : String = "+";
                                attribute Ipoint : Boolean = false;
                                attribute mass : Real = 0.48151264068833555;
                                attribute 'σ_mass' : Real = 0.28909372274994966;
                                attribute Cx : Real = 28.952090302482247;
                                attribute 'σ_Cx' : Real = 28.721044428837228;
                                attribute Cy : Real = -74.66428801417351;
                                attribute 'σ_Cy' : Real = 28.23690002309109;
                                attribute Cz : Real = 68.38612584397197;
                                attribute 'σ_Cz' : Real = 29.057750463592832;
                                attribute Ixx : Real = 0.6724347046816052;
                                attribute 'σ_Ixx' : Real = 0.37074144170588635;
                                attribute Iyy : Real = 0.6909920992351701;
                                attribute 'σ_Iyy' : Real = 0.3723953238821935;
                                attribute Izz : Real = 0.6457045914620532;
                                attribute 'σ_Izz' : Real = 0.37017423652493897;
                                attribute Ixy : Real = 0.03989488917460356;
                                attribute 'σ_Ixy' : Real = 0.02351283871158888;
                                attribute Ixz : Real = 0.01916526523264779;
                                attribute 'σ_Ixz' : Real = 0.022566176940390956;
                                attribute Iyz : Real = -0.021892412248756182;
                                attribute 'σ_Iyz' : Real = 0.02209918015384651;
                            }
                            part <'C.1.1.4.5.3.3.3'> 'Part 713' {
                                attribute POIconv : String = "+";
                                attribute Ipoint : Boolean = false;
                                attribute mass : Real = 0.4320334558309987;
                                attribute 'σ_mass' : Real = 0.28909372274994966;
                                attribute Cx : Real = -82.25429663434625;
                                attribute 'σ_Cx' : Real = 28.721044428837228;
                                attribute Cy : Real = -49.94864575564861;
                                attribute 'σ_Cy' : Real = 28.23690002309109;
                                attribute Cz : Real = 45.12386843562126;
                                attribute 'σ_Cz' : Real = 29.057750463592832;
                                attribute Ixx : Real = 0.5504236931337213;
                                attribute 'σ_Ixx' : Real = 0.37074144170588635;
                                attribute Iyy : Real = 0.5954264153655042;
                                attribute 'σ_Iyy' : Real = 0.3723953238821935;
                                attribute Izz : Real = 0.5897405377989049;
                                attribute 'σ_Izz' : Real = 0.37017423652493897;
                                attribute Ixy : Real = -0.02403321325698159;
                                attribute 'σ_Ixy' : Real = 0.02351283871158888;
                                attribute Ixz : Real = -0.022635029975796445;
                                attribute 'σ_Ixz' : Real = 0.022566176940390956;
                                attribute Iyz : Real = -0.05257036239153015;
                                attribute 'σ_Iyz' : Real = 0.02209918015384651;
                            }
                            part <'C.1.1.4.5.3.3.4'> 'Part 714' {
                                attribute POIconv : String = "-";
                                attribute Ipoint : Boolean = false;
                                attribute mass : Real = 0.11030147460312582;
                                attribute 'σ_mass' : Real = 0.28909372274994966;
                                attribute Cx : Real = 93.77060569822788;
                                attribute 'σ_Cx' : Real = 28.721044428837228;
                                attribute Cy : Real = -43.02244698628783;
                                attribute 'σ_Cy' : Real = 28.23690002309109;
                                attribute Cz : Real = -95.5415905918926;
                                attribute 'σ_Cz' : Real = 29.057750463592832;
                                attribute Ixx : Real = 0.13421399962043973;
                                attribute 'σ_Ixx' : Real = 0.37074144170588635;
                                attribute Iyy : Real = 0.13585396760505633;
                                attribute 'σ_Iyy' : Real = 0.3723953238821935;
                                attribute Izz : Real = 0.1324101159940624;
                                attribute 'σ_Izz' : Real = 0.37017423652493897;
                                attribute Ixy : Real = 0.002863968184362945;
                                attribute 'σ_Ixy' : Real = 0.02351283871158888;
                                attribute Ixz : Real = 0.004003239108246807;
                                attribute 'σ_Ixz' : Real = 0.022566176940390956;
                                attribute Iyz : Real = -0.0014841627506211623;
                                attribute 'σ_Iyz' : Real = 0.02209918015384651;
                            }
                            part <'C.1.1.4.5.3.3.5'> 'Part 715' {
                                attribute POIconv : String = "+";
                                attribute Ipoint : Boolean = false;
                                attribute mass : Real = 0.27610465652425775;
                                attribute 'σ_mass' : Real = 0.28909372274994966;
                                attribute Cx : Real = 55.59043143875897;
                                attribute 'σ_Cx' : Real = 28.721044428837228;
                                attribute Cy : Real = -96.5466033667326;
                                attribute 'σ_Cy' : Real = 28.23690002309109;
                                attribute Cz : Real = -91.17348100990057;
                                attribute 'σ_Cz' : Real = 29.057750463592832;
                                attribute Ixx : Real = 0.37362899423571533;
                                attribute 'σ_Ixx' : Real = 0.37074144170588635;
                                attribute Iyy : Real = 0.3594112917653221;
                                attribute 'σ_Iyy' : Real = 0.3723953238821935;
                                attribute Izz : Real = 0.30049652543813105;
                                attribute 'σ_Izz' : Real = 0.37017423652493897;
                                attribute Ixy : Real = 0.0020822286970982053;
                                attribute 'σ_Ixy' : Real = 0.02351283871158888;
                                attribute Ixz : Real = -0.009048158731498458;
                                attribute 'σ_Ixz' : Real = 0.022566176940390956;
                                attribute Iyz : Real = 0.013549022159672273;
                                attribute 'σ_Iyz' : Real = 0.02209918015384651;
                            }
                        }
                    }
                    part <'C.1.1.4.5.4'> 'Assembly 57' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.1.4.5.4.1'> 'Subassembly 203' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.4.1.1'> 'Part 716' {
                                attribute POIconv : String = "-";
                                attribute Ipoint : Boolean = false;
                                attribute mass : Real = 0.9259354616964701;
                                attribute 'σ_mass' : Real = 0.28909372274994966;
                                attribute Cx : Real = -51.72942406497896;
                                attribute 'σ_Cx' : Real = 28.721044428837228;
                                attribute Cy : Real = -43.71386934071779;
                                attribute 'σ_Cy' : Real = 28.23690002309109;
                                attribute Cz : Real = -16.282848082482815;
                                attribute 'σ_Cz' : Real = 29.057750463592832;
                                attribute Ixx : Real = 1.0924638848352082;
                                attribute 'σ_Ixx' : Real = 0.37074144170588635;
                                attribute Iyy : Real = 1.211918824464876;
                                attribute 'σ_Iyy' : Real = 0.3723953238821935;
                                attribute Izz : Real = 1.271129048401201;
                                attribute 'σ_Izz' : Real = 0.37017423652493897;
                                attribute Ixy : Real = 0.006718772955328196;
                                attribute 'σ_Ixy' : Real = 0.02351283871158888;
                                attribute Ixz : Real = 0.02603137210770866;
                                attribute 'σ_Ixz' : Real = 0.022566176940390956;
                                attribute Iyz : Real = 0.03153346825570205;
                                attribute 'σ_Iyz' : Real = 0.02209918015384651;
                            }
                            part <'C.1.1.4.5.4.1.2'> 'Part 717' {
                                attribute POIconv : String = "-";
                                attribute Ipoint : Boolean = false;
                                attribute mass : Real = 0.9072328777022194;
                                attribute 'σ_mass' : Real = 0.28909372274994966;
                                attribute Cx : Real = -76.86035190708935;
                                attribute 'σ_Cx' : Real = 28.721044428837228;
                                attribute Cy : Real = -47.28317493572831;
                                attribute 'σ_Cy' : Real = 28.23690002309109;
                                attribute Cz : Real = -20.996416732668877;
                                attribute 'σ_Cz' : Real = 29.057750463592832;
                                attribute Ixx : Real = 1.2367202334305931;
                                attribute 'σ_Ixx' : Real = 0.37074144170588635;
                                attribute Iyy : Real = 1.2286135826014641;
                                attribute 'σ_Iyy' : Real = 0.3723953238821935;
                                attribute Izz : Real = 1.034130595483409;
                                attribute 'σ_Izz' : Real = 0.37017423652493897;
                                attribute Ixy : Real = 0.0024152447610838717;
                                attribute 'σ_Ixy' : Real = 0.02351283871158888;
                                attribute Ixz : Real = -0.015981770434105085;
                                attribute 'σ_Ixz' : Real = 0.022566176940390956;
                                attribute Iyz : Real = 0.039729520205721056;
                                attribute 'σ_Iyz' : Real = 0.02209918015384651;
                            }
                            part <'C.1.1.4.5.4.1.3'> 'Part 718' {
                                attribute POIconv : String = "-";
                                attribute Ipoint : Boolean = false;
                                attribute mass : Real = 0.1147620219362434;
                                attribute 'σ_mass' : Real = 0.28909372274994966;
                                attribute Cx : Real = 99.79253225028515;
                                attribute 'σ_Cx' : Real = 28.721044428837228;
                                attribute Cy : Real = 51.211427338421345;
                                attribute 'σ_Cy' : Real = 28.23690002309109;
                                attribute Cz : Real = 48.40501071885228;
                                attribute 'σ_Cz' : Real = 29.057750463592832;
                                attribute Ixx : Real = 0.12662861052477048;
                                attribute 'σ_Ixx' : Real = 0.37074144170588635;
                                attribute Iyy : Real = 0.1600645038280774;
                                attribute 'σ_Iyy' : Real = 0.3723953238821935;
                                attribute Izz : Real = 0.14479687869142938;
                                attribute 'σ_Izz' : Real = 0.37017423652493897;
                                attribute Ixy : Real = -0.008291928043095746;
                                attribute 'σ_Ixy' : Real = 0.02351283871158888;
                                attribute Ixz : Real = -1.8345692514096145e-5;
                                attribute 'σ_Ixz' : Real = 0.022566176940390956;
                                attribute Iyz : Real = 0.0021275951646355174;
                                attribute 'σ_Iyz' : Real = 0.02209918015384651;
                            }
                        }
                        part <'C.1.1.4.5.4.2'> 'Subassembly 204' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.4.2.1'> 'Part 719' {
                                attribute POIconv : String = "-";
                                attribute Ipoint : Boolean = false;
                                attribute mass : Real = 0.028702711908379572;
                                attribute 'σ_mass' : Real = 0.28909372274994966;
                                attribute Cx : Real = 24.50151718221605;
                                attribute 'σ_Cx' : Real = 28.721044428837228;
                                attribute Cy : Real = 79.14099269546568;
                                attribute 'σ_Cy' : Real = 28.23690002309109;
                                attribute Cz : Real = 50.49227578565478;
                                attribute 'σ_Cz' : Real = 29.057750463592832;
                                attribute Ixx : Real = 0.036951328468088664;
                                attribute 'σ_Ixx' : Real = 0.37074144170588635;
                                attribute Iyy : Real = 0.03882815193442854;
                                attribute 'σ_Iyy' : Real = 0.3723953238821935;
                                attribute Izz : Real = 0.0373987646627077;
                                attribute 'σ_Izz' : Real = 0.37017423652493897;
                                attribute Ixy : Real = -0.0028158179495523837;
                                attribute 'σ_Ixy' : Real = 0.02351283871158888;
                                attribute Ixz : Real = 5.120233063638329e-4;
                                attribute 'σ_Ixz' : Real = 0.022566176940390956;
                                attribute Iyz : Real = -5.901302212767127e-4;
                                attribute 'σ_Iyz' : Real = 0.02209918015384651;
                            }
                            part <'C.1.1.4.5.4.2.2'> 'Part 720' {
                                attribute POIconv : String = "-";
                                attribute Ipoint : Boolean = false;
                                attribute mass : Real = 0.928666933874134;
                                attribute 'σ_mass' : Real = 0.28909372274994966;
                                attribute Cx : Real = 8.624161453917623;
                                attribute 'σ_Cx' : Real = 28.721044428837228;
                                attribute Cy : Real = 30.25789698585868;
                                attribute 'σ_Cy' : Real = 28.23690002309109;
                                attribute Cz : Real = 74.44659322500229;
                                attribute 'σ_Cz' : Real = 29.057750463592832;
                                attribute Ixx : Real = 0.8939526394370166;
                                attribute 'σ_Ixx' : Real = 0.37074144170588635;
                                attribute Iyy : Real = 0.9895436094298773;
                                attribute 'σ_Iyy' : Real = 0.3723953238821935;
                                attribute Izz : Real = 1.058939498548267;
                                attribute 'σ_Izz' : Real = 0.37017423652493897;
                                attribute Ixy : Real = -0.06481420555728551;
                                attribute 'σ_Ixy' : Real = 0.02351283871158888;
                                attribute Ixz : Real = 0.023580854704829582;
                                attribute 'σ_Ixz' : Real = 0.022566176940390956;
                                attribute Iyz : Real = 0.04182024600706466;
                                attribute 'σ_Iyz' : Real = 0.02209918015384651;
                            }
                            part <'C.1.1.4.5.4.2.3'> 'Part 721' {
                                attribute POIconv : String = "+";
                                attribute Ipoint : Boolean = false;
                                attribute mass : Real = 0.9005303944807965;
                                attribute 'σ_mass' : Real = 0.28909372274994966;
                                attribute Cx : Real = 36.270047817379236;
                                attribute 'σ_Cx' : Real = 28.721044428837228;
                                attribute Cy : Real = 77.9579265974462;
                                attribute 'σ_Cy' : Real = 28.23690002309109;
                                attribute Cz : Real = 63.555475417524576;
                                attribute 'σ_Cz' : Real = 29.057750463592832;
                                attribute Ixx : Real = 1.0151262404443149;
                                attribute 'σ_Ixx' : Real = 0.37074144170588635;
                                attribute Iyy : Real = 1.19067801315242;
                                attribute 'σ_Iyy' : Real = 0.3723953238821935;
                                attribute Izz : Real = 1.0297584526064287;
                                attribute 'σ_Izz' : Real = 0.37017423652493897;
                                attribute Ixy : Real = -0.02691426775585533;
                                attribute 'σ_Ixy' : Real = 0.02351283871158888;
                                attribute Ixz : Real = -0.007695531168624236;
                                attribute 'σ_Ixz' : Real = 0.022566176940390956;
                                attribute Iyz : Real = -0.05802696207369526;
                                attribute 'σ_Iyz' : Real = 0.02209918015384651;
                            }
                            part <'C.1.1.4.5.4.2.4'> 'Part 722' {
                                attribute POIconv : String = "+";
                                attribute Ipoint : Boolean = false;
                                attribute mass : Real = 0.9725461800792254;
                                attribute 'σ_mass' : Real = 0.28909372274994966;
                                attribute Cx : Real = -23.739759856835008;
                                attribute 'σ_Cx' : Real = 28.721044428837228;
                                attribute Cy : Real = 84.33448066934943;
                                attribute 'σ_Cy' : Real = 28.23690002309109;
                                attribute Cz : Real = -62.785498797893524;
                                attribute 'σ_Cz' : Real = 29.057750463592832;
                                attribute Ixx : Real = 1.135198949647473;
                                attribute 'σ_Ixx' : Real = 0.37074144170588635;
                                attribute Iyy : Real = 1.0366610196989163;
                                attribute 'σ_Iyy' : Real = 0.3723953238821935;
                                attribute Izz : Real = 1.034243141762496;
                                attribute 'σ_Izz' : Real = 0.37017423652493897;
                                attribute Ixy : Real = 0.04517955457035574;
                                attribute 'σ_Ixy' : Real = 0.02351283871158888;
                                attribute Ixz : Real = -0.052405426816877675;
                                attribute 'σ_Ixz' : Real = 0.022566176940390956;
                                attribute Iyz : Real = 0.02511730996482605;
                                attribute 'σ_Iyz' : Real = 0.02209918015384651;
                            }
                            part <'C.1.1.4.5.4.2.5'> 'Part 723' {
                                attribute POIconv : String = "-";
                                attribute Ipoint : Boolean = false;
                                attribute mass : Real = 0.11174813228519634;
                                attribute 'σ_mass' : Real = 0.28909372274994966;
                                attribute Cx : Real = -25.62098721973598;
                                attribute 'σ_Cx' : Real = 28.721044428837228;
                                attribute Cy : Real = -67.84275793470442;
                                attribute 'σ_Cy' : Real = 28.23690002309109;
                                attribute Cz : Real = -73.60694906674325;
                                attribute 'σ_Cz' : Real = 29.057750463592832;
                                attribute Ixx : Real = 0.1268050948982667;
                                attribute 'σ_Ixx' : Real = 0.37074144170588635;
                                attribute Iyy : Real = 0.1285769699437629;
                                attribute 'σ_Iyy' : Real = 0.3723953238821935;
                                attribute Izz : Real = 0.12524686835849153;
                                attribute 'σ_Izz' : Real = 0.37017423652493897;
                                attribute Ixy : Real = -6.688257820647342e-4;
                                attribute 'σ_Ixy' : Real = 0.02351283871158888;
                                attribute Ixz : Real = 0.014219180141157113;
                                attribute 'σ_Ixz' : Real = 0.022566176940390956;
                                attribute Iyz : Real = -0.004739797753517275;
                                attribute 'σ_Iyz' : Real = 0.02209918015384651;
                            }
                        }
                        part <'C.1.1.4.5.4.3'> 'Subassembly 205' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.4.3.1'> 'Part 724' {
                                attribute POIconv : String = "+";
                                attribute Ipoint : Boolean = false;
                                attribute mass : Real = 0.4168300075104926;
                                attribute 'σ_mass' : Real = 0.28909372274994966;
                                attribute Cx : Real = -14.283385733142495;
                                attribute 'σ_Cx' : Real = 28.721044428837228;
                                attribute Cy : Real = -99.07091353088617;
                                attribute 'σ_Cy' : Real = 28.23690002309109;
                                attribute Cz : Real = -48.003824427723885;
                                attribute 'σ_Cz' : Real = 29.057750463592832;
                                attribute Ixx : Real = 0.5497097266084952;
                                attribute 'σ_Ixx' : Real = 0.37074144170588635;
                                attribute Iyy : Real = 0.4692175753310004;
                                attribute 'σ_Iyy' : Real = 0.3723953238821935;
                                attribute Izz : Real = 0.5430888928451009;
                                attribute 'σ_Izz' : Real = 0.37017423652493897;
                                attribute Ixy : Real = 0.03498809085352045;
                                attribute 'σ_Ixy' : Real = 0.02351283871158888;
                                attribute Ixz : Real = -0.014878268435043179;
                                attribute 'σ_Ixz' : Real = 0.022566176940390956;
                                attribute Iyz : Real = -0.04478471650908063;
                                attribute 'σ_Iyz' : Real = 0.02209918015384651;
                            }
                            part <'C.1.1.4.5.4.3.2'> 'Part 725' {
                                attribute POIconv : String = "+";
                                attribute Ipoint : Boolean = false;
                                attribute mass : Real = 0.05277869777567685;
                                attribute 'σ_mass' : Real = 0.28909372274994966;
                                attribute Cx : Real = -76.45711689256132;
                                attribute 'σ_Cx' : Real = 28.721044428837228;
                                attribute Cy : Real = 34.03611145913601;
                                attribute 'σ_Cy' : Real = 28.23690002309109;
                                attribute Cz : Real = -33.76581915654242;
                                attribute 'σ_Cz' : Real = 29.057750463592832;
                                attribute Ixx : Real = 0.07567515528552089;
                                attribute 'σ_Ixx' : Real = 0.37074144170588635;
                                attribute Iyy : Real = 0.07567744386322818;
                                attribute 'σ_Iyy' : Real = 0.3723953238821935;
                                attribute Izz : Real = 0.08759773308281037;
                                attribute 'σ_Izz' : Real = 0.37017423652493897;
                                attribute Ixy : Real = 1.1607197599555166e-6;
                                attribute 'σ_Ixy' : Real = 0.02351283871158888;
                                attribute Ixz : Real = 1.7214346146315752e-4;
                                attribute 'σ_Ixz' : Real = 0.022566176940390956;
                                attribute Iyz : Real = -1.5290859179811018e-4;
                                attribute 'σ_Iyz' : Real = 0.02209918015384651;
                            }
                            part <'C.1.1.4.5.4.3.3'> 'Part 726' {
                                attribute POIconv : String = "+";
                                attribute Ipoint : Boolean = false;
                                attribute mass : Real = 0.9820598490748089;
                                attribute 'σ_mass' : Real = 0.28909372274994966;
                                attribute Cx : Real = 76.58592541702092;
                                attribute 'σ_Cx' : Real = 28.721044428837228;
                                attribute Cy : Real = 10.32382482662797;
                                attribute 'σ_Cy' : Real = 28.23690002309109;
                                attribute Cz : Real = 11.086071189492941;
                                attribute 'σ_Cz' : Real = 29.057750463592832;
                                attribute Ixx : Real = 1.2352330856583003;
                                attribute 'σ_Ixx' : Real = 0.37074144170588635;
                                attribute Iyy : Real = 1.319911151793171;
                                attribute 'σ_Iyy' : Real = 0.3723953238821935;
                                attribute Izz : Real = 1.2463314898424065;
                                attribute 'σ_Izz' : Real = 0.37017423652493897;
                                attribute Ixy : Real = 0.056891119545845095;
                                attribute 'σ_Ixy' : Real = 0.02351283871158888;
                                attribute Ixz : Real = -0.05919706189432759;
                                attribute 'σ_Ixz' : Real = 0.022566176940390956;
                                attribute Iyz : Real = 0.07792969714656524;
                                attribute 'σ_Iyz' : Real = 0.02209918015384651;
                            }
                        }
                        part <'C.1.1.4.5.4.4'> 'Subassembly 206' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.1.4.5.4.4.1'> 'Part 727' {
                                attribute POIconv : String = "-";
                                attribute Ipoint : Boolean = false;
                                attribute mass : Real = 0.9679883005630691;
                                attribute 'σ_mass' : Real = 0.28909372274994966;
                                attribute Cx : Real = -23.69741532020271;
                                attribute 'σ_Cx' : Real = 28.721044428837228;
                                attribute Cy : Real = -28.017089562490582;
                                attribute 'σ_Cy' : Real = 28.23690002309109;
                                attribute Cz : Real = -62.21753763966262;
                                attribute 'σ_Cz' : Real = 29.057750463592832;
                                attribute Ixx : Real = 1.3383063645782607;
                                attribute 'σ_Ixx' : Real = 0.37074144170588635;
                                attribute Iyy : Real = 1.255114206859061;
                                attribute 'σ_Iyy' : Real = 0.3723953238821935;
                                attribute Izz : Real = 1.2460074778371693;
                                attribute 'σ_Izz' : Real = 0.37017423652493897;
                                attribute Ixy : Real = 0.06867246262344523;
                                attribute 'σ_Ixy' : Real = 0.02351283871158888;
                                attribute Ixz : Real = -0.06883853919434785;
                                attribute 'σ_Ixz' : Real = 0.022566176940390956;
                                attribute Iyz : Real = 0.07667324795403546;
                                attribute 'σ_Iyz' : Real = 0.02209918015384651;
                            }
                            part <'C.1.1.4.5.4.4.2'> 'Part 728' {
                                attribute POIconv : String = "-";
                                attribute Ipoint : Boolean = false;
                                attribute mass : Real = 0.5458135985324625;
                                attribute 'σ_mass' : Real = 0.28909372274994966;
                                attribute Cx : Real = -97.94251257553697;
                                attribute 'σ_Cx' : Real = 28.721044428837228;
                                attribute Cy : Real = -88.97118531167507;
                                attribute 'σ_Cy' : Real = 28.23690002309109;
                                attribute Cz : Real = 41.8939096853137;
                                attribute 'σ_Cz' : Real = 29.057750463592832;
                                attribute Ixx : Real = 0.5382167557069855;
                                attribute 'σ_Ixx' : Real = 0.37074144170588635;
                                attribute Iyy : Real = 0.6619471992858849;
                                attribute 'σ_Iyy' : Real = 0.3723953238821935;
                                attribute Izz : Real = 0.6689725073341343;
                                attribute 'σ_Izz' : Real = 0.37017423652493897;
                                attribute Ixy : Real = 0.03512038716917919;
                                attribute 'σ_Ixy' : Real = 0.02351283871158888;
                                attribute Ixz : Real = 0.059161951153099884;
                                attribute 'σ_Ixz' : Real = 0.022566176940390956;
                                attribute Iyz : Real = -0.02083720483697001;
                                attribute 'σ_Iyz' : Real = 0.02209918015384651;
                            }
                            part <'C.1.1.4.5.4.4.3'> 'Part 729' {
                                attribute POIconv : String = "-";
                                attribute Ipoint : Boolean = false;
                                attribute mass : Real = 0.6791087179814931;
                                attribute 'σ_mass' : Real = 0.28909372274994966;
                                attribute Cx : Real = 92.34358565881848;
                                attribute 'σ_Cx' : Real = 28.721044428837228;
                                attribute Cy : Real = 44.98140406794846;
                                attribute 'σ_Cy' : Real = 28.23690002309109;
                                attribute Cz : Real = -82.79626253060997;
                                attribute 'σ_Cz' : Real = 29.057750463592832;
                                attribute Ixx : Real = 0.9166713651258287;
                                attribute 'σ_Ixx' : Real = 0.37074144170588635;
                                attribute Iyy : Real = 0.9950820915552686;
                                attribute 'σ_Iyy' : Real = 0.3723953238821935;
                                attribute Izz : Real = 0.8846571007402796;
                                attribute 'σ_Izz' : Real = 0.37017423652493897;
                                attribute Ixy : Real = -0.05896341081210538;
                                attribute 'σ_Ixy' : Real = 0.02351283871158888;
                                attribute Ixz : Real = 0.0010311795524071917;
                                attribute 'σ_Ixz' : Real = 0.022566176940390956;
                                attribute Iyz : Real = -0.0072754479997270355;
                                attribute 'σ_Iyz' : Real = 0.02209918015384651;
                            }
                            part <'C.1.1.4.5.4.4.4'> 'Part 730' {
                                attribute POIconv : String = "-";
                                attribute Ipoint : Boolean = false;
                                attribute mass : Real = 0.057369901813101025;
                                attribute 'σ_mass' : Real = 0.28909372274994966;
                                attribute Cx : Real = 76.80482738651335;
                                attribute 'σ_Cx' : Real = 28.721044428837228;
                                attribute Cy : Real = -31.74225827679038;
                                attribute 'σ_Cy' : Real = 28.23690002309109;
                                attribute Cz : Real = -49.01925986632705;
                                attribute 'σ_Cz' : Real = 29.057750463592832;
                                attribute Ixx : Real = 0.06952625605585436;
                                attribute 'σ_Ixx' : Real = 0.37074144170588635;
                                attribute Iyy : Real = 0.08069026843191593;
                                attribute 'σ_Iyy' : Real = 0.3723953238821935;
                                attribute Izz : Real = 0.06871774520129935;
                                attribute 'σ_Izz' : Real = 0.37017423652493897;
                                attribute Ixy : Real = 0.005131710382125855;
                                attribute 'σ_Ixy' : Real = 0.02351283871158888;
                                attribute Ixz : Real = 2.3080825890815342e-4;
                                attribute 'σ_Ixz' : Real = 0.022566176940390956;
                                attribute Iyz : Real = 7.136671413002496e-4;
                                attribute 'σ_Iyz' : Real = 0.02209918015384651;
                            }
                        }
                    }
                }
            }
        }
        part <'C.1.2'> 'Segment 2' {
            attribute POIconv : String = "-";
            attribute Ipoint : Boolean;
            attribute mass : Real;
            attribute 'σ_mass' : Real;
            attribute Cx : Real;
            attribute 'σ_Cx' : Real;
            attribute Cy : Real;
            attribute 'σ_Cy' : Real;
            attribute Cz : Real;
            attribute 'σ_Cz' : Real;
            attribute Ixx : Real;
            attribute 'σ_Ixx' : Real;
            attribute Iyy : Real;
            attribute 'σ_Iyy' : Real;
            attribute Izz : Real;
            attribute 'σ_Izz' : Real;
            attribute Ixy : Real;
            attribute 'σ_Ixy' : Real;
            attribute Ixz : Real;
            attribute 'σ_Ixz' : Real;
            attribute Iyz : Real;
            attribute 'σ_Iyz' : Real;
            part <'C.1.2.1'> 'Element 5' {
                attribute POIconv : String = "-";
                attribute Ipoint : Boolean;
                attribute mass : Real;
                attribute 'σ_mass' : Real;
                attribute Cx : Real;
                attribute 'σ_Cx' : Real;
                attribute Cy : Real;
                attribute 'σ_Cy' : Real;
                attribute Cz : Real;
                attribute 'σ_Cz' : Real;
                attribute Ixx : Real;
                attribute 'σ_Ixx' : Real;
                attribute Iyy : Real;
                attribute 'σ_Iyy' : Real;
                attribute Izz : Real;
                attribute 'σ_Izz' : Real;
                attribute Ixy : Real;
                attribute 'σ_Ixy' : Real;
                attribute Ixz : Real;
                attribute 'σ_Ixz' : Real;
                attribute Iyz : Real;
                attribute 'σ_Iyz' : Real;
                part <'C.1.2.1.1'> 'Subsystem 16' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.2.1.1.1'> 'Assembly 58' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.1.1.1'> 'Subassembly 207' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.1.1.1'> 'Part 731' {
                                attribute POIconv : String = "+";
                                attribute Ipoint : Boolean = false;
                                attribute mass : Real = 0.6804637058416847;
                                attribute 'σ_mass' : Real = 0.28909372274994966;
                                attribute Cx : Real = -82.76614844799042;
                                attribute 'σ_Cx' : Real = 28.721044428837228;
                                attribute Cy : Real = -47.76298082433641;
                                attribute 'σ_Cy' : Real = 28.23690002309109;
                                attribute Cz : Real = 63.294122368097305;
                                attribute 'σ_Cz' : Real = 29.057750463592832;
                                attribute Ixx : Real = 0.7629432285981665;
                                attribute 'σ_Ixx' : Real = 0.37074144170588635;
                                attribute Iyy : Real = 0.8421712701444337;
                                attribute 'σ_Iyy' : Real = 0.3723953238821935;
                                attribute Izz : Real = 0.7932281294553125;
                                attribute 'σ_Izz' : Real = 0.37017423652493897;
                                attribute Ixy : Real = -0.040747429195994375;
                                attribute 'σ_Ixy' : Real = 0.02351283871158888;
                                attribute Ixz : Real = 0.07982067472193621;
                                attribute 'σ_Ixz' : Real = 0.022566176940390956;
                                attribute Iyz : Real = -0.03702446897993501;
                                attribute 'σ_Iyz' : Real = 0.02209918015384651;
                            }
                            part <'C.1.2.1.1.1.1.2'> 'Part 732' {
                                attribute POIconv : String = "+";
                                attribute Ipoint : Boolean = false;
                                attribute mass : Real = 0.0872471402049996;
                                attribute 'σ_mass' : Real = 0.28909372274994966;
                                attribute Cx : Real = 82.55250179208815;
                                attribute 'σ_Cx' : Real = 28.721044428837228;
                                attribute Cy : Real = -5.411630170419812;
                                attribute 'σ_Cy' : Real = 28.23690002309109;
                                attribute Cz : Real = -71.15427576936781;
                                attribute 'σ_Cz' : Real = 29.057750463592832;
                                attribute Ixx : Real = 0.11257619230429793;
                                attribute 'σ_Ixx' : Real = 0.37074144170588635;
                                attribute Iyy : Real = 0.1246403998381112;
                                attribute 'σ_Iyy' : Real = 0.3723953238821935;
                                attribute Izz : Real = 0.11991330708654552;
                                attribute 'σ_Izz' : Real = 0.37017423652493897;
                                attribute Ixy : Real = -0.0032220311242106107;
                                attribute 'σ_Ixy' : Real = 0.02351283871158888;
                                attribute Ixz : Real = 0.0026909518310395584;
                                attribute 'σ_Ixz' : Real = 0.022566176940390956;
                                attribute Iyz : Real = -0.0017268308576099392;
                                attribute 'σ_Iyz' : Real = 0.02209918015384651;
                            }
                            part <'C.1.2.1.1.1.1.3'> 'Part 733' {
                                attribute POIconv : String = "-";
                                attribute Ipoint : Boolean = false;
                                attribute mass : Real = 0.37708795348485;
                                attribute 'σ_mass' : Real = 0.28909372274994966;
                                attribute Cx : Real = -3.4473955165594816;
                                attribute 'σ_Cx' : Real = 28.721044428837228;
                                attribute Cy : Real = 43.91561853699386;
                                attribute 'σ_Cy' : Real = 28.23690002309109;
                                attribute Cz : Real = -98.94797829911113;
                                attribute 'σ_Cz' : Real = 29.057750463592832;
                                attribute Ixx : Real = 0.49265900196150153;
                                attribute 'σ_Ixx' : Real = 0.37074144170588635;
                                attribute Iyy : Real = 0.3794068111394347;
                                attribute 'σ_Iyy' : Real = 0.3723953238821935;
                                attribute Izz : Real = 0.46816149458660183;
                                attribute 'σ_Izz' : Real = 0.37017423652493897;
                                attribute Ixy : Real = 0.022108336751683156;
                                attribute 'σ_Ixy' : Real = 0.02351283871158888;
                                attribute Ixz : Real = -0.010211977595304967;
                                attribute 'σ_Ixz' : Real = 0.022566176940390956;
                                attribute Iyz : Real = 0.04406619851694948;
                                attribute 'σ_Iyz' : Real = 0.02209918015384651;
                            }
                        }
                        part <'C.1.2.1.1.1.2'> 'Subassembly 208' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.1.2.1'> 'Part 734' {
                                attribute POIconv : String = "+";
                                attribute Ipoint : Boolean = false;
                                attribute mass : Real = 0.5951115685270634;
                                attribute 'σ_mass' : Real = 0.28909372274994966;
                                attribute Cx : Real = 5.548908468335867;
                                attribute 'σ_Cx' : Real = 28.721044428837228;
                                attribute Cy : Real = 92.18274871818721;
                                attribute 'σ_Cy' : Real = 28.23690002309109;
                                attribute Cz : Real = -86.23134288936853;
                                attribute 'σ_Cz' : Real = 29.057750463592832;
                                attribute Ixx : Real = 0.6239526384625814;
                                attribute 'σ_Ixx' : Real = 0.37074144170588635;
                                attribute Iyy : Real = 0.5989152296145334;
                                attribute 'σ_Iyy' : Real = 0.3723953238821935;
                                attribute Izz : Real = 0.6269662989457233;
                                attribute 'σ_Izz' : Real = 0.37017423652493897;
                                attribute Ixy : Real = -0.004337172890690839;
                                attribute 'σ_Ixy' : Real = 0.02351283871158888;
                                attribute Ixz : Real = 0.021114383488938397;
                                attribute 'σ_Ixz' : Real = 0.022566176940390956;
                                attribute Iyz : Real = 0.016508367062713213;
                                attribute 'σ_Iyz' : Real = 0.02209918015384651;
                            }
                            part <'C.1.2.1.1.1.2.2'> 'Part 735' {
                                attribute POIconv : String = "+";
                                attribute Ipoint : Boolean = false;
                                attribute mass : Real = 0.872108902297914;
                                attribute 'σ_mass' : Real = 0.28909372274994966;
                                attribute Cx : Real = -6.520798243582249;
                                attribute 'σ_Cx' : Real = 28.721044428837228;
                                attribute Cy : Real = 29.035241017118096;
                                attribute 'σ_Cy' : Real = 28.23690002309109;
                                attribute Cz : Real = 23.73237246647477;
                                attribute 'σ_Cz' : Real = 29.057750463592832;
                                attribute Ixx : Real = 0.8805630776543457;
                                attribute 'σ_Ixx' : Real = 0.37074144170588635;
                                attribute Iyy : Real = 0.8999397241871576;
                                attribute 'σ_Iyy' : Real = 0.3723953238821935;
                                attribute Izz : Real = 0.8894808707558973;
                                attribute 'σ_Izz' : Real = 0.37017423652493897;
                                attribute Ixy : Real = -0.017241277974757066;
                                attribute 'σ_Ixy' : Real = 0.02351283871158888;
                                attribute Ixz : Real = -0.03328122971330339;
                                attribute 'σ_Ixz' : Real = 0.022566176940390956;
                                attribute Iyz : Real = 0.02604022754460038;
                                attribute 'σ_Iyz' : Real = 0.02209918015384651;
                            }
                        }
                        part <'C.1.2.1.1.1.3'> 'Subassembly 209' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.1.3.1'> 'Part 736' {
                                attribute POIconv : String = "+";
                                attribute Ipoint : Boolean = false;
                                attribute mass : Real = 0.008498315708246083;
                                attribute 'σ_mass' : Real = 0.28909372274994966;
                                attribute Cx : Real = 95.8209665492177;
                                attribute 'σ_Cx' : Real = 28.721044428837228;
                                attribute Cy : Real = 10.03832914866507;
                                attribute 'σ_Cy' : Real = 28.23690002309109;
                                attribute Cz : Real = -85.71276320144534;
                                attribute 'σ_Cz' : Real = 29.057750463592832;
                                attribute Ixx : Real = 0.01010350024606598;
                                attribute 'σ_Ixx' : Real = 0.37074144170588635;
                                attribute Iyy : Real = 0.00820784706025794;
                                attribute 'σ_Iyy' : Real = 0.3723953238821935;
                                attribute Izz : Real = 0.010515066389495425;
                                attribute 'σ_Izz' : Real = 0.37017423652493897;
                                attribute Ixy : Real = 2.3126819134562212e-4;
                                attribute 'σ_Ixy' : Real = 0.02351283871158888;
                                attribute Ixz : Real = 1.2528071019289914e-4;
                                attribute 'σ_Ixz' : Real = 0.022566176940390956;
                                attribute Iyz : Real = 4.255321773142125e-4;
                                attribute 'σ_Iyz' : Real = 0.02209918015384651;
                            }
                            part <'C.1.2.1.1.1.3.2'> 'Part 737' {
                                attribute POIconv : String = "+";
                                attribute Ipoint : Boolean = false;
                                attribute mass : Real = 0.4892256704615429;
                                attribute 'σ_mass' : Real = 0.28909372274994966;
                                attribute Cx : Real = 17.618257645517588;
                                attribute 'σ_Cx' : Real = 28.721044428837228;
                                attribute Cy : Real = 27.53212545067072;
                                attribute 'σ_Cy' : Real = 28.23690002309109;
                                attribute Cz : Real = -96.17204638198018;
                                attribute 'σ_Cz' : Real = 29.057750463592832;
                                attribute Ixx : Real = 0.4969958259508533;
                                attribute 'σ_Ixx' : Real = 0.37074144170588635;
                                attribute Iyy : Real = 0.5265120312163792;
                                attribute 'σ_Iyy' : Real = 0.3723953238821935;
                                attribute Izz : Real = 0.5355846342958775;
                                attribute 'σ_Izz' : Real = 0.37017423652493897;
                                attribute Ixy : Real = 0.0190510341032654;
                                attribute 'σ_Ixy' : Real = 0.02351283871158888;
                                attribute Ixz : Real = 0.008945837549478563;
                                attribute 'σ_Ixz' : Real = 0.022566176940390956;
                                attribute Iyz : Real = 0.0060182447598878894;
                                attribute 'σ_Iyz' : Real = 0.02209918015384651;
                            }
                            part <'C.1.2.1.1.1.3.3'> 'Part 738' {
                                attribute POIconv : String = "-";
                                attribute Ipoint : Boolean = false;
                                attribute mass : Real = 0.4114048428549431;
                                attribute 'σ_mass' : Real = 0.28909372274994966;
                                attribute Cx : Real = 81.30457135848701;
                                attribute 'σ_Cx' : Real = 28.721044428837228;
                                attribute Cy : Real = -71.8050632160157;
                                attribute 'σ_Cy' : Real = 28.23690002309109;
                                attribute Cz : Real = -91.16176166571677;
                                attribute 'σ_Cz' : Real = 29.057750463592832;
                                attribute Ixx : Real = 0.44402303017076217;
                                attribute 'σ_Ixx' : Real = 0.37074144170588635;
                                attribute Iyy : Real = 0.4763219719018769;
                                attribute 'σ_Iyy' : Real = 0.3723953238821935;
                                attribute Izz : Real = 0.41585003026945555;
                                attribute 'σ_Izz' : Real = 0.37017423652493897;
                                attribute Ixy : Real = -0.02162839523967402;
                                attribute 'σ_Ixy' : Real = 0.02351283871158888;
                                attribute Ixz : Real = -0.053712151596749094;
                                attribute 'σ_Ixz' : Real = 0.022566176940390956;
                                attribute Iyz : Real = -0.014969335860785337;
                                attribute 'σ_Iyz' : Real = 0.02209918015384651;
                            }
                            part <'C.1.2.1.1.1.3.4'> 'Part 739' {
                                attribute POIconv : String = "+";
                                attribute Ipoint : Boolean = false;
                                attribute mass : Real = 0.9858494289398659;
                                attribute 'σ_mass' : Real = 0.28909372274994966;
                                attribute Cx : Real = -48.487570974975824;
                                attribute 'σ_Cx' : Real = 28.721044428837228;
                                attribute Cy : Real = 31.294124433770776;
                                attribute 'σ_Cy' : Real = 28.23690002309109;
                                attribute Cz : Real = 55.107109947130084;
                                attribute 'σ_Cz' : Real = 29.057750463592832;
                                attribute Ixx : Real = 1.1757576125781801;
                                attribute 'σ_Ixx' : Real = 0.37074144170588635;
                                attribute Iyy : Real = 1.0082079378489615;
                                attribute 'σ_Iyy' : Real = 0.3723953238821935;
                                attribute Izz : Real = 1.1376475595997482;
                                attribute 'σ_Izz' : Real = 0.37017423652493897;
                                attribute Ixy : Real = -0.07972945487492622;
                                attribute 'σ_Ixy' : Real = 0.02351283871158888;
                                attribute Ixz : Real = -0.03983517562227505;
                                attribute 'σ_Ixz' : Real = 0.022566176940390956;
                                attribute Iyz : Real = 0.049635722526859744;
                                attribute 'σ_Iyz' : Real = 0.02209918015384651;
                            }
                        }
                    }
                    part <'C.1.2.1.1.2'> 'Assembly 59' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.1.2.1'> 'Subassembly 210' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.2.1.1'> 'Part 740' {
                                attribute POIconv : String = "-";
                                attribute Ipoint : Boolean = false;
                                attribute mass : Real = 0.3524647980094887;
                                attribute 'σ_mass' : Real = 0.28909372274994966;
                                attribute Cx : Real = 17.589840944856405;
                                attribute 'σ_Cx' : Real = 28.721044428837228;
                                attribute Cy : Real = -98.27087316662073;
                                attribute 'σ_Cy' : Real = 28.23690002309109;
                                attribute Cz : Real = 38.97576960735023;
                                attribute 'σ_Cz' : Real = 29.057750463592832;
                                attribute Ixx : Real = 0.4258627296014497;
                                attribute 'σ_Ixx' : Real = 0.37074144170588635;
                                attribute Iyy : Real = 0.4110435441094528;
                                attribute 'σ_Iyy' : Real = 0.3723953238821935;
                                attribute Izz : Real = 0.4137752782792825;
                                attribute 'σ_Izz' : Real = 0.37017423652493897;
                                attribute Ixy : Real = -0.002382145990967037;
                                attribute 'σ_Ixy' : Real = 0.02351283871158888;
                                attribute Ixz : Real = 0.007633384612226931;
                                attribute 'σ_Ixz' : Real = 0.022566176940390956;
                                attribute Iyz : Real = 0.00929356051204898;
                                attribute 'σ_Iyz' : Real = 0.02209918015384651;
                            }
                            part <'C.1.2.1.1.2.1.2'> 'Part 741' {
                                attribute POIconv : String = "-";
                                attribute Ipoint : Boolean = false;
                                attribute mass : Real = 0.3731747709093615;
                                attribute 'σ_mass' : Real = 0.28909372274994966;
                                attribute Cx : Real = -11.087685823440552;
                                attribute 'σ_Cx' : Real = 28.721044428837228;
                                attribute Cy : Real = 57.89243211038411;
                                attribute 'σ_Cy' : Real = 28.23690002309109;
                                attribute Cz : Real = 62.26490465924144;
                                attribute 'σ_Cz' : Real = 29.057750463592832;
                                attribute Ixx : Real = 0.3509286307150823;
                                attribute 'σ_Ixx' : Real = 0.37074144170588635;
                                attribute Iyy : Real = 0.35218270227074583;
                                attribute 'σ_Iyy' : Real = 0.3723953238821935;
                                attribute Izz : Real = 0.3515830593384509;
                                attribute 'σ_Izz' : Real = 0.37017423652493897;
                                attribute Ixy : Real = 0.0048160232423513066;
                                attribute 'σ_Ixy' : Real = 0.02351283871158888;
                                attribute Ixz : Real = 8.138250968522599e-4;
                                attribute 'σ_Ixz' : Real = 0.022566176940390956;
                                attribute Iyz : Real = -0.0017294838101161493;
                                attribute 'σ_Iyz' : Real = 0.02209918015384651;
                            }
                            part <'C.1.2.1.1.2.1.3'> 'Part 742' {
                                attribute POIconv : String = "+";
                                attribute Ipoint : Boolean = false;
                                attribute mass : Real = 0.7001743357286323;
                                attribute 'σ_mass' : Real = 0.28909372274994966;
                                attribute Cx : Real = 84.57673550583422;
                                attribute 'σ_Cx' : Real = 28.721044428837228;
                                attribute Cy : Real = 3.156300587579608;
                                attribute 'σ_Cy' : Real = 28.23690002309109;
                                attribute Cz : Real = -73.20337975397706;
                                attribute 'σ_Cz' : Real = 29.057750463592832;
                                attribute Ixx : Real = 1.0666391176590142;
                                attribute 'σ_Ixx' : Real = 0.37074144170588635;
                                attribute Iyy : Real = 0.9689360931603728;
                                attribute 'σ_Iyy' : Real = 0.3723953238821935;
                                attribute Izz : Real = 1.0040021375078358;
                                attribute 'σ_Izz' : Real = 0.37017423652493897;
                                attribute Ixy : Real = 0.01753679927963258;
                                attribute 'σ_Ixy' : Real = 0.02351283871158888;
                                attribute Ixz : Real = 0.061439194178128806;
                                attribute 'σ_Ixz' : Real = 0.022566176940390956;
                                attribute Iyz : Real = -0.02060570819559051;
                                attribute 'σ_Iyz' : Real = 0.02209918015384651;
                            }
                            part <'C.1.2.1.1.2.1.4'> 'Part 743' {
                                attribute POIconv : String = "+";
                                attribute Ipoint : Boolean = false;
                                attribute mass : Real = 0.3578815421590116;
                                attribute 'σ_mass' : Real = 0.28909372274994966;
                                attribute Cx : Real = -0.09536426514387131;
                                attribute 'σ_Cx' : Real = 28.721044428837228;
                                attribute Cy : Real = -22.71536346524954;
                                attribute 'σ_Cy' : Real = 28.23690002309109;
                                attribute Cz : Real = 82.86153981462121;
                                attribute 'σ_Cz' : Real = 29.057750463592832;
                                attribute Ixx : Real = 0.4564375566026807;
                                attribute 'σ_Ixx' : Real = 0.37074144170588635;
                                attribute Iyy : Real = 0.46100574731399746;
                                attribute 'σ_Iyy' : Real = 0.3723953238821935;
                                attribute Izz : Real = 0.5164296956069518;
                                attribute 'σ_Izz' : Real = 0.37017423652493897;
                                attribute Ixy : Real = 0.0018357401942787263;
                                attribute 'σ_Ixy' : Real = 0.02351283871158888;
                                attribute Ixz : Real = 0.018394305828290897;
                                attribute 'σ_Ixz' : Real = 0.022566176940390956;
                                attribute Iyz : Real = -0.02495232358022128;
                                attribute 'σ_Iyz' : Real = 0.02209918015384651;
                            }
                        }
                        part <'C.1.2.1.1.2.2'> 'Subassembly 211' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.2.2.1'> 'Part 744' {
                                attribute POIconv : String = "-";
                                attribute Ipoint : Boolean = false;
                                attribute mass : Real = 0.6776843973651994;
                                attribute 'σ_mass' : Real = 0.28909372274994966;
                                attribute Cx : Real = 21.6790278442204;
                                attribute 'σ_Cx' : Real = 28.721044428837228;
                                attribute Cy : Real = -37.29653721675277;
                                attribute 'σ_Cy' : Real = 28.23690002309109;
                                attribute Cz : Real = -19.07854271121323;
                                attribute 'σ_Cz' : Real = 29.057750463592832;
                                attribute Ixx : Real = 0.9764823301807641;
                                attribute 'σ_Ixx' : Real = 0.37074144170588635;
                                attribute Iyy : Real = 0.9432967659398266;
                                attribute 'σ_Iyy' : Real = 0.3723953238821935;
                                attribute Izz : Real = 0.8389583984732274;
                                attribute 'σ_Izz' : Real = 0.37017423652493897;
                                attribute Ixy : Real = 0.03668961292485377;
                                attribute 'σ_Ixy' : Real = 0.02351283871158888;
                                attribute Ixz : Real = 0.02635295473512606;
                                attribute 'σ_Ixz' : Real = 0.022566176940390956;
                                attribute Iyz : Real = 0.0019964469050437164;
                                attribute 'σ_Iyz' : Real = 0.02209918015384651;
                            }
                            part <'C.1.2.1.1.2.2.2'> 'Part 745' {
                                attribute POIconv : String = "-";
                                attribute Ipoint : Boolean = false;
                                attribute mass : Real = 0.8189852579096332;
                                attribute 'σ_mass' : Real = 0.28909372274994966;
                                attribute Cx : Real = 13.485083356499672;
                                attribute 'σ_Cx' : Real = 28.721044428837228;
                                attribute Cy : Real = 47.51953762024641;
                                attribute 'σ_Cy' : Real = 28.23690002309109;
                                attribute Cz : Real = 72.01477042399347;
                                attribute 'σ_Cz' : Real = 29.057750463592832;
                                attribute Ixx : Real = 0.9866077048101372;
                                attribute 'σ_Ixx' : Real = 0.37074144170588635;
                                attribute Iyy : Real = 0.8188473953264852;
                                attribute 'σ_Iyy' : Real = 0.3723953238821935;
                                attribute Izz : Real = 0.9672519572000952;
                                attribute 'σ_Izz' : Real = 0.37017423652493897;
                                attribute Ixy : Real = 0.09962186153086014;
                                attribute 'σ_Ixy' : Real = 0.02351283871158888;
                                attribute Ixz : Real = -0.036196655509834606;
                                attribute 'σ_Ixz' : Real = 0.022566176940390956;
                                attribute Iyz : Real = 0.09620780002706718;
                                attribute 'σ_Iyz' : Real = 0.02209918015384651;
                            }
                        }
                        part <'C.1.2.1.1.2.3'> 'Subassembly 212' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.2.3.1'> 'Part 746' {
                                attribute POIconv : String = "-";
                                attribute Ipoint : Boolean = false;
                                attribute mass : Real = 0.8998692514791619;
                                attribute 'σ_mass' : Real = 0.28909372274994966;
                                attribute Cx : Real = -58.5591247305274;
                                attribute 'σ_Cx' : Real = 28.721044428837228;
                                attribute Cy : Real = 46.724122390151024;
                                attribute 'σ_Cy' : Real = 28.23690002309109;
                                attribute Cz : Real = -31.836828589439392;
                                attribute 'σ_Cz' : Real = 29.057750463592832;
                                attribute Ixx : Real = 1.1177223875317448;
                                attribute 'σ_Ixx' : Real = 0.37074144170588635;
                                attribute Iyy : Real = 1.0022752527058716;
                                attribute 'σ_Iyy' : Real = 0.3723953238821935;
                                attribute Izz : Real = 1.2520463243671025;
                                attribute 'σ_Izz' : Real = 0.37017423652493897;
                                attribute Ixy : Real = -0.05281833187798392;
                                attribute 'σ_Ixy' : Real = 0.02351283871158888;
                                attribute Ixz : Real = 0.002811801961034743;
                                attribute 'σ_Ixz' : Real = 0.022566176940390956;
                                attribute Iyz : Real = -0.0022142105824800914;
                                attribute 'σ_Iyz' : Real = 0.02209918015384651;
                            }
                            part <'C.1.2.1.1.2.3.2'> 'Part 747' {
                                attribute POIconv : String = "-";
                                attribute Ipoint : Boolean = false;
                                attribute mass : Real = 0.9499364645415918;
                                attribute 'σ_mass' : Real = 0.28909372274994966;
                                attribute Cx : Real = -79.34043616987765;
                                attribute 'σ_Cx' : Real = 28.721044428837228;
                                attribute Cy : Real = -33.98116189055145;
                                attribute 'σ_Cy' : Real = 28.23690002309109;
                                attribute Cz : Real = -35.99375756457448;
                                attribute 'σ_Cz' : Real = 29.057750463592832;
                                attribute Ixx : Real = 1.142982380782115;
                                attribute 'σ_Ixx' : Real = 0.37074144170588635;
                                attribute Iyy : Real = 1.3086528638228532;
                                attribute 'σ_Iyy' : Real = 0.3723953238821935;
                                attribute Izz : Real = 1.1386084378401995;
                                attribute 'σ_Izz' : Real = 0.37017423652493897;
                                attribute Ixy : Real = -0.08531444657742686;
                                attribute 'σ_Ixy' : Real = 0.02351283871158888;
                                attribute Ixz : Real = -0.03938223383212878;
                                attribute 'σ_Ixz' : Real = 0.022566176940390956;
                                attribute Iyz : Real = 0.0860008952847964;
                                attribute 'σ_Iyz' : Real = 0.02209918015384651;
                            }
                        }
                    }
                    part <'C.1.2.1.1.3'> 'Assembly 60' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.1.3.1'> 'Subassembly 213' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.3.1.1'> 'Part 748' {
                                attribute POIconv : String = "+";
                                attribute Ipoint : Boolean = false;
                                attribute mass : Real = 0.39689005199656824;
                                attribute 'σ_mass' : Real = 0.28909372274994966;
                                attribute Cx : Real = -23.252603830769658;
                                attribute 'σ_Cx' : Real = 28.721044428837228;
                                attribute Cy : Real = -24.79836782440543;
                                attribute 'σ_Cy' : Real = 28.23690002309109;
                                attribute Cz : Real = -75.31434493139386;
                                attribute 'σ_Cz' : Real = 29.057750463592832;
                                attribute Ixx : Real = 0.4334524829250718;
                                attribute 'σ_Ixx' : Real = 0.37074144170588635;
                                attribute Iyy : Real = 0.4286218616998627;
                                attribute 'σ_Iyy' : Real = 0.3723953238821935;
                                attribute Izz : Real = 0.42020117894506914;
                                attribute 'σ_Izz' : Real = 0.37017423652493897;
                                attribute Ixy : Real = -0.003096940950002379;
                                attribute 'σ_Ixy' : Real = 0.02351283871158888;
                                attribute Ixz : Real = -0.009915462050657891;
                                attribute 'σ_Ixz' : Real = 0.022566176940390956;
                                attribute Iyz : Real = 0.0038362948562042382;
                                attribute 'σ_Iyz' : Real = 0.02209918015384651;
                            }
                            part <'C.1.2.1.1.3.1.2'> 'Part 749' {
                                attribute POIconv : String = "-";
                                attribute Ipoint : Boolean = false;
                                attribute mass : Real = 0.36715233089006505;
                                attribute 'σ_mass' : Real = 0.28909372274994966;
                                attribute Cx : Real = 32.00223217718303;
                                attribute 'σ_Cx' : Real = 28.721044428837228;
                                attribute Cy : Real = -89.40441003069282;
                                attribute 'σ_Cy' : Real = 28.23690002309109;
                                attribute Cz : Real = -54.3915722053498;
                                attribute 'σ_Cz' : Real = 29.057750463592832;
                                attribute Ixx : Real = 0.4719654567221899;
                                attribute 'σ_Ixx' : Real = 0.37074144170588635;
                                attribute Iyy : Real = 0.460320418295716;
                                attribute 'σ_Iyy' : Real = 0.3723953238821935;
                                attribute Izz : Real = 0.46101187755155804;
                                attribute 'σ_Izz' : Real = 0.37017423652493897;
                                attribute Ixy : Real = -0.00251825365628728;
                                attribute 'σ_Ixy' : Real = 0.02351283871158888;
                                attribute Ixz : Real = -0.0049723586261868095;
                                attribute 'σ_Ixz' : Real = 0.022566176940390956;
                                attribute Iyz : Real = 0.003343582954485104;
                                attribute 'σ_Iyz' : Real = 0.02209918015384651;
                            }
                            part <'C.1.2.1.1.3.1.3'> 'Part 750' {
                                attribute POIconv : String = "-";
                                attribute Ipoint : Boolean = false;
                                attribute mass : Real = 0.2973035856145434;
                                attribute 'σ_mass' : Real = 0.28909372274994966;
                                attribute Cx : Real = 56.80312239564955;
                                attribute 'σ_Cx' : Real = 28.721044428837228;
                                attribute Cy : Real = 20.184138836339116;
                                attribute 'σ_Cy' : Real = 28.23690002309109;
                                attribute Cz : Real = 16.486272821202874;
                                attribute 'σ_Cz' : Real = 29.057750463592832;
                                attribute Ixx : Real = 0.4165385188469107;
                                attribute 'σ_Ixx' : Real = 0.37074144170588635;
                                attribute Iyy : Real = 0.41021507699301324;
                                attribute 'σ_Iyy' : Real = 0.3723953238821935;
                                attribute Izz : Real = 0.4321250382861898;
                                attribute 'σ_Izz' : Real = 0.37017423652493897;
                                attribute Ixy : Real = 0.01599767566384614;
                                attribute 'σ_Ixy' : Real = 0.02351283871158888;
                                attribute Ixz : Real = 0.0016296869304939594;
                                attribute 'σ_Ixz' : Real = 0.022566176940390956;
                                attribute Iyz : Real = 0.0025697867139138717;
                                attribute 'σ_Iyz' : Real = 0.02209918015384651;
                            }
                            part <'C.1.2.1.1.3.1.4'> 'Part 751' {
                                attribute POIconv : String = "-";
                                attribute Ipoint : Boolean = false;
                                attribute mass : Real = 0.11068734925775789;
                                attribute 'σ_mass' : Real = 0.28909372274994966;
                                attribute Cx : Real = -96.00051855668426;
                                attribute 'σ_Cx' : Real = 28.721044428837228;
                                attribute Cy : Real = 29.335967730730772;
                                attribute 'σ_Cy' : Real = 28.23690002309109;
                                attribute Cz : Real = 86.86235672794282;
                                attribute 'σ_Cz' : Real = 29.057750463592832;
                                attribute Ixx : Real = 0.13287541940067435;
                                attribute 'σ_Ixx' : Real = 0.37074144170588635;
                                attribute Iyy : Real = 0.1493999821924077;
                                attribute 'σ_Iyy' : Real = 0.3723953238821935;
                                attribute Izz : Real = 0.13480151636001594;
                                attribute 'σ_Izz' : Real = 0.37017423652493897;
                                attribute Ixy : Real = 5.346451701485279e-4;
                                attribute 'σ_Ixy' : Real = 0.02351283871158888;
                                attribute Ixz : Real = 0.016063611740379388;
                                attribute 'σ_Ixz' : Real = 0.022566176940390956;
                                attribute Iyz : Real = -0.003326603736358102;
                                attribute 'σ_Iyz' : Real = 0.02209918015384651;
                            }
                        }
                        part <'C.1.2.1.1.3.2'> 'Subassembly 214' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.3.2.1'> 'Part 752' {
                                attribute POIconv : String = "+";
                                attribute Ipoint : Boolean = false;
                                attribute mass : Real = 0.2992536970761139;
                                attribute 'σ_mass' : Real = 0.28909372274994966;
                                attribute Cx : Real = 85.29202463105321;
                                attribute 'σ_Cx' : Real = 28.721044428837228;
                                attribute Cy : Real = 63.26323663815856;
                                attribute 'σ_Cy' : Real = 28.23690002309109;
                                attribute Cz : Real = 67.95464907772839;
                                attribute 'σ_Cz' : Real = 29.057750463592832;
                                attribute Ixx : Real = 0.38744432852985544;
                                attribute 'σ_Ixx' : Real = 0.37074144170588635;
                                attribute Iyy : Real = 0.4356089676417009;
                                attribute 'σ_Iyy' : Real = 0.3723953238821935;
                                attribute Izz : Real = 0.3900464582805366;
                                attribute 'σ_Izz' : Real = 0.37017423652493897;
                                attribute Ixy : Real = -0.034687679455557854;
                                attribute 'σ_Ixy' : Real = 0.02351283871158888;
                                attribute Ixz : Real = 6.856327784017383e-4;
                                attribute 'σ_Ixz' : Real = 0.022566176940390956;
                                attribute Iyz : Real = -0.024857684271430862;
                                attribute 'σ_Iyz' : Real = 0.02209918015384651;
                            }
                            part <'C.1.2.1.1.3.2.2'> 'Part 753' {
                                attribute POIconv : String = "-";
                                attribute Ipoint : Boolean = false;
                                attribute mass : Real = 0.4824196958669927;
                                attribute 'σ_mass' : Real = 0.28909372274994966;
                                attribute Cx : Real = 75.37926463410258;
                                attribute 'σ_Cx' : Real = 28.721044428837228;
                                attribute Cy : Real = 86.7199407890439;
                                attribute 'σ_Cy' : Real = 28.23690002309109;
                                attribute Cz : Real = -51.597818080335855;
                                attribute 'σ_Cz' : Real = 29.057750463592832;
                                attribute Ixx : Real = 0.5972836744420277;
                                attribute 'σ_Ixx' : Real = 0.37074144170588635;
                                attribute Iyy : Real = 0.6088349565192258;
                                attribute 'σ_Iyy' : Real = 0.3723953238821935;
                                attribute Izz : Real = 0.4651221313919162;
                                attribute 'σ_Izz' : Real = 0.37017423652493897;
                                attribute Ixy : Real = -0.005143026305932856;
                                attribute 'σ_Ixy' : Real = 0.02351283871158888;
                                attribute Ixz : Real = 0.02245609712122978;
                                attribute 'σ_Ixz' : Real = 0.022566176940390956;
                                attribute Iyz : Real = -0.002820177434061783;
                                attribute 'σ_Iyz' : Real = 0.02209918015384651;
                            }
                            part <'C.1.2.1.1.3.2.3'> 'Part 754' {
                                attribute POIconv : String = "-";
                                attribute Ipoint : Boolean = false;
                                attribute mass : Real = 0.731420080100419;
                                attribute 'σ_mass' : Real = 0.28909372274994966;
                                attribute Cx : Real = -87.23915270529687;
                                attribute 'σ_Cx' : Real = 28.721044428837228;
                                attribute Cy : Real = -75.01831972040236;
                                attribute 'σ_Cy' : Real = 28.23690002309109;
                                attribute Cz : Real = 72.04496175982058;
                                attribute 'σ_Cz' : Real = 29.057750463592832;
                                attribute Ixx : Real = 1.0759963707122355;
                                attribute 'σ_Ixx' : Real = 0.37074144170588635;
                                attribute Iyy : Real = 0.9533618149858826;
                                attribute 'σ_Iyy' : Real = 0.3723953238821935;
                                attribute Izz : Real = 0.9150329569349791;
                                attribute 'σ_Izz' : Real = 0.37017423652493897;
                                attribute Ixy : Real = -0.09269870400481497;
                                attribute 'σ_Ixy' : Real = 0.02351283871158888;
                                attribute Ixz : Real = -0.013819817713409153;
                                attribute 'σ_Ixz' : Real = 0.022566176940390956;
                                attribute Iyz : Real = -0.01576985372709947;
                                attribute 'σ_Iyz' : Real = 0.02209918015384651;
                            }
                            part <'C.1.2.1.1.3.2.4'> 'Part 755' {
                                attribute POIconv : String = "-";
                                attribute Ipoint : Boolean = false;
                                attribute mass : Real = 0.8046920785717666;
                                attribute 'σ_mass' : Real = 0.28909372274994966;
                                attribute Cx : Real = -21.137832244858146;
                                attribute 'σ_Cx' : Real = 28.721044428837228;
                                attribute Cy : Real = -3.009476698935032;
                                attribute 'σ_Cy' : Real = 28.23690002309109;
                                attribute Cz : Real = 86.59949153661728;
                                attribute 'σ_Cz' : Real = 29.057750463592832;
                                attribute Ixx : Real = 0.8875065574219388;
                                attribute 'σ_Ixx' : Real = 0.37074144170588635;
                                attribute Iyy : Real = 0.8774204459401267;
                                attribute 'σ_Iyy' : Real = 0.3723953238821935;
                                attribute Izz : Real = 0.9706186754508619;
                                attribute 'σ_Izz' : Real = 0.37017423652493897;
                                attribute Ixy : Real = -2.1913966782130648e-4;
                                attribute 'σ_Ixy' : Real = 0.02351283871158888;
                                attribute Ixz : Real = -0.0036418256558426315;
                                attribute 'σ_Ixz' : Real = 0.022566176940390956;
                                attribute Iyz : Real = -0.00294138001072363;
                                attribute 'σ_Iyz' : Real = 0.02209918015384651;
                            }
                            part <'C.1.2.1.1.3.2.5'> 'Part 756' {
                                attribute POIconv : String = "+";
                                attribute Ipoint : Boolean = false;
                                attribute mass : Real = 0.38625357567332685;
                                attribute 'σ_mass' : Real = 0.28909372274994966;
                                attribute Cx : Real = 87.66397093422711;
                                attribute 'σ_Cx' : Real = 28.721044428837228;
                                attribute Cy : Real = 86.19044567458332;
                                attribute 'σ_Cy' : Real = 28.23690002309109;
                                attribute Cz : Real = -70.07079608738422;
                                attribute 'σ_Cz' : Real = 29.057750463592832;
                                attribute Ixx : Real = 0.5604927172738877;
                                attribute 'σ_Ixx' : Real = 0.37074144170588635;
                                attribute Iyy : Real = 0.5651094200121082;
                                attribute 'σ_Iyy' : Real = 0.3723953238821935;
                                attribute Izz : Real = 0.6038361024888986;
                                attribute 'σ_Izz' : Real = 0.37017423652493897;
                                attribute Ixy : Real = 0.0028351004458055575;
                                attribute 'σ_Ixy' : Real = 0.02351283871158888;
                                attribute Ixz : Real = 0.008843891778887662;
                                attribute 'σ_Ixz' : Real = 0.022566176940390956;
                                attribute Iyz : Real = -0.019213378798346857;
                                attribute 'σ_Iyz' : Real = 0.02209918015384651;
                            }
                        }
                    }
                    part <'C.1.2.1.1.4'> 'Assembly 61' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.1.4.1'> 'Subassembly 215' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.4.1.1'> 'Part 757' {
                                attribute POIconv : String = "+";
                                attribute Ipoint : Boolean = false;
                                attribute mass : Real = 0.5277951386689674;
                                attribute 'σ_mass' : Real = 0.28909372274994966;
                                attribute Cx : Real = -22.000057948753238;
                                attribute 'σ_Cx' : Real = 28.721044428837228;
                                attribute Cy : Real = 73.35792551748455;
                                attribute 'σ_Cy' : Real = 28.23690002309109;
                                attribute Cz : Real = 92.66872312873602;
                                attribute 'σ_Cz' : Real = 29.057750463592832;
                                attribute Ixx : Real = 0.6599775728875614;
                                attribute 'σ_Ixx' : Real = 0.37074144170588635;
                                attribute Iyy : Real = 0.6729828603777622;
                                attribute 'σ_Iyy' : Real = 0.3723953238821935;
                                attribute Izz : Real = 0.6721468524486317;
                                attribute 'σ_Izz' : Real = 0.37017423652493897;
                                attribute Ixy : Real = 0.012797544881179762;
                                attribute 'σ_Ixy' : Real = 0.02351283871158888;
                                attribute Ixz : Real = 0.04098930642177462;
                                attribute 'σ_Ixz' : Real = 0.022566176940390956;
                                attribute Iyz : Real = 0.013045679529243823;
                                attribute 'σ_Iyz' : Real = 0.02209918015384651;
                            }
                            part <'C.1.2.1.1.4.1.2'> 'Part 758' {
                                attribute POIconv : String = "+";
                                attribute Ipoint : Boolean = false;
                                attribute mass : Real = 0.8053474915262777;
                                attribute 'σ_mass' : Real = 0.28909372274994966;
                                attribute Cx : Real = 37.55772658623755;
                                attribute 'σ_Cx' : Real = 28.721044428837228;
                                attribute Cy : Real = -2.7468798216432333;
                                attribute 'σ_Cy' : Real = 28.23690002309109;
                                attribute Cz : Real = 28.147784527391195;
                                attribute 'σ_Cz' : Real = 29.057750463592832;
                                attribute Ixx : Real = 0.980439222471684;
                                attribute 'σ_Ixx' : Real = 0.37074144170588635;
                                attribute Iyy : Real = 1.041424184657024;
                                attribute 'σ_Iyy' : Real = 0.3723953238821935;
                                attribute Izz : Real = 1.0076098768063189;
                                attribute 'σ_Izz' : Real = 0.37017423652493897;
                                attribute Ixy : Real = -0.010019175134829465;
                                attribute 'σ_Ixy' : Real = 0.02351283871158888;
                                attribute Ixz : Real = -0.007402587072056047;
                                attribute 'σ_Ixz' : Real = 0.022566176940390956;
                                attribute Iyz : Real = 0.005689361431303748;
                                attribute 'σ_Iyz' : Real = 0.02209918015384651;
                            }
                            part <'C.1.2.1.1.4.1.3'> 'Part 759' {
                                attribute POIconv : String = "-";
                                attribute Ipoint : Boolean = false;
                                attribute mass : Real = 0.2798572542674374;
                                attribute 'σ_mass' : Real = 0.28909372274994966;
                                attribute Cx : Real = -1.8543540965765715;
                                attribute 'σ_Cx' : Real = 28.721044428837228;
                                attribute Cy : Real = -38.02656470797956;
                                attribute 'σ_Cy' : Real = 28.23690002309109;
                                attribute Cz : Real = 8.29140255227685;
                                attribute 'σ_Cz' : Real = 29.057750463592832;
                                attribute Ixx : Real = 0.319043573662642;
                                attribute 'σ_Ixx' : Real = 0.37074144170588635;
                                attribute Iyy : Real = 0.3612154677599895;
                                attribute 'σ_Iyy' : Real = 0.3723953238821935;
                                attribute Izz : Real = 0.36260014519152894;
                                attribute 'σ_Izz' : Real = 0.37017423652493897;
                                attribute Ixy : Real = 0.004002795928620026;
                                attribute 'σ_Ixy' : Real = 0.02351283871158888;
                                attribute Ixz : Real = 0.0049391579486995334;
                                attribute 'σ_Ixz' : Real = 0.022566176940390956;
                                attribute Iyz : Real = -0.0216381314967697;
                                attribute 'σ_Iyz' : Real = 0.02209918015384651;
                            }
                            part <'C.1.2.1.1.4.1.4'> 'Part 760' {
                                attribute POIconv : String = "+";
                                attribute Ipoint : Boolean = false;
                                attribute mass : Real = 0.9471244623491075;
                                attribute 'σ_mass' : Real = 0.28909372274994966;
                                attribute Cx : Real = -51.52808767743409;
                                attribute 'σ_Cx' : Real = 28.721044428837228;
                                attribute Cy : Real = -10.05314807407558;
                                attribute 'σ_Cy' : Real = 28.23690002309109;
                                attribute Cz : Real = -74.55631201155484;
                                attribute 'σ_Cz' : Real = 29.057750463592832;
                                attribute Ixx : Real = 1.2448887865830731;
                                attribute 'σ_Ixx' : Real = 0.37074144170588635;
                                attribute Iyy : Real = 1.219913015585758;
                                attribute 'σ_Iyy' : Real = 0.3723953238821935;
                                attribute Izz : Real = 1.2360221746950788;
                                attribute 'σ_Izz' : Real = 0.37017423652493897;
                                attribute Ixy : Real = -0.010508502236888088;
                                attribute 'σ_Ixy' : Real = 0.02351283871158888;
                                attribute Ixz : Real = -0.0014892940963207291;
                                attribute 'σ_Ixz' : Real = 0.022566176940390956;
                                attribute Iyz : Real = 0.01337938894965738;
                                attribute 'σ_Iyz' : Real = 0.02209918015384651;
                            }
                            part <'C.1.2.1.1.4.1.5'> 'Part 761' {
                                attribute POIconv : String = "-";
                                attribute Ipoint : Boolean = false;
                                attribute mass : Real = 0.1391759812645614;
                                attribute 'σ_mass' : Real = 0.28909372274994966;
                                attribute Cx : Real = -32.136630872264504;
                                attribute 'σ_Cx' : Real = 28.721044428837228;
                                attribute Cy : Real = -29.095242777839303;
                                attribute 'σ_Cy' : Real = 28.23690002309109;
                                attribute Cz : Real = -1.727196853607893;
                                attribute 'σ_Cz' : Real = 29.057750463592832;
                                attribute Ixx : Real = 0.15586377958796008;
                                attribute 'σ_Ixx' : Real = 0.37074144170588635;
                                attribute Iyy : Real = 0.1790932487070789;
                                attribute 'σ_Iyy' : Real = 0.3723953238821935;
                                attribute Izz : Real = 0.16947107755359206;
                                attribute 'σ_Izz' : Real = 0.37017423652493897;
                                attribute Ixy : Real = -0.0020703784647289935;
                                attribute 'σ_Ixy' : Real = 0.02351283871158888;
                                attribute Ixz : Real = 0.007364274583466635;
                                attribute 'σ_Ixz' : Real = 0.022566176940390956;
                                attribute Iyz : Real = 0.018147694171923696;
                                attribute 'σ_Iyz' : Real = 0.02209918015384651;
                            }
                        }
                        part <'C.1.2.1.1.4.2'> 'Subassembly 216' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.4.2.1'> 'Part 762' {
                                attribute POIconv : String = "-";
                                attribute Ipoint : Boolean = false;
                                attribute mass : Real = 0.24065079136332498;
                                attribute 'σ_mass' : Real = 0.28909372274994966;
                                attribute Cx : Real = -19.398300489410758;
                                attribute 'σ_Cx' : Real = 28.721044428837228;
                                attribute Cy : Real = 13.430628506466746;
                                attribute 'σ_Cy' : Real = 28.23690002309109;
                                attribute Cz : Real = -36.78402896039188;
                                attribute 'σ_Cz' : Real = 29.057750463592832;
                                attribute Ixx : Real = 0.32285130454318084;
                                attribute 'σ_Ixx' : Real = 0.37074144170588635;
                                attribute Iyy : Real = 0.3022483775826096;
                                attribute 'σ_Iyy' : Real = 0.3723953238821935;
                                attribute Izz : Real = 0.34521169758474934;
                                attribute 'σ_Izz' : Real = 0.37017423652493897;
                                attribute Ixy : Real = -1.0714679072289656e-4;
                                attribute 'σ_Ixy' : Real = 0.02351283871158888;
                                attribute Ixz : Real = -0.01540431113764842;
                                attribute 'σ_Ixz' : Real = 0.022566176940390956;
                                attribute Iyz : Real = 0.003224401918999439;
                                attribute 'σ_Iyz' : Real = 0.02209918015384651;
                            }
                            part <'C.1.2.1.1.4.2.2'> 'Part 763' {
                                attribute POIconv : String = "+";
                                attribute Ipoint : Boolean = false;
                                attribute mass : Real = 0.6926015382464975;
                                attribute 'σ_mass' : Real = 0.28909372274994966;
                                attribute Cx : Real = 27.922243298962712;
                                attribute 'σ_Cx' : Real = 28.721044428837228;
                                attribute Cy : Real = -15.271924389526248;
                                attribute 'σ_Cy' : Real = 28.23690002309109;
                                attribute Cz : Real = -97.4251854699105;
                                attribute 'σ_Cz' : Real = 29.057750463592832;
                                attribute Ixx : Real = 0.7579189228996535;
                                attribute 'σ_Ixx' : Real = 0.37074144170588635;
                                attribute Iyy : Real = 0.7762027341634707;
                                attribute 'σ_Iyy' : Real = 0.3723953238821935;
                                attribute Izz : Real = 0.747914059974558;
                                attribute 'σ_Izz' : Real = 0.37017423652493897;
                                attribute Ixy : Real = -0.012381074577790929;
                                attribute 'σ_Ixy' : Real = 0.02351283871158888;
                                attribute Ixz : Real = -0.007272485362996863;
                                attribute 'σ_Ixz' : Real = 0.022566176940390956;
                                attribute Iyz : Real = -0.013261630503456993;
                                attribute 'σ_Iyz' : Real = 0.02209918015384651;
                            }
                            part <'C.1.2.1.1.4.2.3'> 'Part 764' {
                                attribute POIconv : String = "+";
                                attribute Ipoint : Boolean = false;
                                attribute mass : Real = 0.09721460776636377;
                                attribute 'σ_mass' : Real = 0.28909372274994966;
                                attribute Cx : Real = 34.01378854177892;
                                attribute 'σ_Cx' : Real = 28.721044428837228;
                                attribute Cy : Real = 8.866165345534682;
                                attribute 'σ_Cy' : Real = 28.23690002309109;
                                attribute Cz : Real = -20.01916980370879;
                                attribute 'σ_Cz' : Real = 29.057750463592832;
                                attribute Ixx : Real = 0.12628605288038988;
                                attribute 'σ_Ixx' : Real = 0.37074144170588635;
                                attribute Iyy : Real = 0.1331928710910463;
                                attribute 'σ_Iyy' : Real = 0.3723953238821935;
                                attribute Izz : Real = 0.1302974547031479;
                                attribute 'σ_Izz' : Real = 0.37017423652493897;
                                attribute Ixy : Real = -0.0034043748472266933;
                                attribute 'σ_Ixy' : Real = 0.02351283871158888;
                                attribute Ixz : Real = -0.00744904209373886;
                                attribute 'σ_Ixz' : Real = 0.022566176940390956;
                                attribute Iyz : Real = -3.5498980847123993e-4;
                                attribute 'σ_Iyz' : Real = 0.02209918015384651;
                            }
                            part <'C.1.2.1.1.4.2.4'> 'Part 765' {
                                attribute POIconv : String = "+";
                                attribute Ipoint : Boolean = false;
                                attribute mass : Real = 0.8070877520779614;
                                attribute 'σ_mass' : Real = 0.28909372274994966;
                                attribute Cx : Real = -56.81523885577917;
                                attribute 'σ_Cx' : Real = 28.721044428837228;
                                attribute Cy : Real = -56.775956274941564;
                                attribute 'σ_Cy' : Real = 28.23690002309109;
                                attribute Cz : Real = 73.24771415442228;
                                attribute 'σ_Cz' : Real = 29.057750463592832;
                                attribute Ixx : Real = 0.8549413265791542;
                                attribute 'σ_Ixx' : Real = 0.37074144170588635;
                                attribute Iyy : Real = 0.8487442864754311;
                                attribute 'σ_Iyy' : Real = 0.3723953238821935;
                                attribute Izz : Real = 0.696494459273452;
                                attribute 'σ_Izz' : Real = 0.37017423652493897;
                                attribute Ixy : Real = 9.494314552722415e-4;
                                attribute 'σ_Ixy' : Real = 0.02351283871158888;
                                attribute Ixz : Real = 0.003463092506280538;
                                attribute 'σ_Ixz' : Real = 0.022566176940390956;
                                attribute Iyz : Real = -0.03778196418151167;
                                attribute 'σ_Iyz' : Real = 0.02209918015384651;
                            }
                            part <'C.1.2.1.1.4.2.5'> 'Part 766' {
                                attribute POIconv : String = "-";
                                attribute Ipoint : Boolean = false;
                                attribute mass : Real = 0.3055442237523384;
                                attribute 'σ_mass' : Real = 0.28909372274994966;
                                attribute Cx : Real = 1.8936157692223787;
                                attribute 'σ_Cx' : Real = 28.721044428837228;
                                attribute Cy : Real = 16.410128958523273;
                                attribute 'σ_Cy' : Real = 28.23690002309109;
                                attribute Cz : Real = -86.61358072422445;
                                attribute 'σ_Cz' : Real = 29.057750463592832;
                                attribute Ixx : Real = 0.3064496150515967;
                                attribute 'σ_Ixx' : Real = 0.37074144170588635;
                                attribute Iyy : Real = 0.3242030123640101;
                                attribute 'σ_Iyy' : Real = 0.3723953238821935;
                                attribute Izz : Real = 0.32837305119860355;
                                attribute 'σ_Izz' : Real = 0.37017423652493897;
                                attribute Ixy : Real = 0.011985892578234516;
                                attribute 'σ_Ixy' : Real = 0.02351283871158888;
                                attribute Ixz : Real = -0.012883036497250819;
                                attribute 'σ_Ixz' : Real = 0.022566176940390956;
                                attribute Iyz : Real = -0.018099896429694087;
                                attribute 'σ_Iyz' : Real = 0.02209918015384651;
                            }
                        }
                    }
                    part <'C.1.2.1.1.5'> 'Assembly 62' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.1.5.1'> 'Subassembly 217' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.5.1.1'> 'Part 767' {
                                attribute POIconv : String = "+";
                                attribute Ipoint : Boolean = false;
                                attribute mass : Real = 0.3013742657515686;
                                attribute 'σ_mass' : Real = 0.28909372274994966;
                                attribute Cx : Real = 95.47040383331478;
                                attribute 'σ_Cx' : Real = 28.721044428837228;
                                attribute Cy : Real = 25.583136966452003;
                                attribute 'σ_Cy' : Real = 28.23690002309109;
                                attribute Cz : Real = 14.539825124666095;
                                attribute 'σ_Cz' : Real = 29.057750463592832;
                                attribute Ixx : Real = 0.4577300568244157;
                                attribute 'σ_Ixx' : Real = 0.37074144170588635;
                                attribute Iyy : Real = 0.43506241096384446;
                                attribute 'σ_Iyy' : Real = 0.3723953238821935;
                                attribute Izz : Real = 0.4522514845491837;
                                attribute 'σ_Izz' : Real = 0.37017423652493897;
                                attribute Ixy : Real = 0.010077297957306877;
                                attribute 'σ_Ixy' : Real = 0.02351283871158888;
                                attribute Ixz : Real = -0.02689692338783546;
                                attribute 'σ_Ixz' : Real = 0.022566176940390956;
                                attribute Iyz : Real = 0.015255887571808577;
                                attribute 'σ_Iyz' : Real = 0.02209918015384651;
                            }
                            part <'C.1.2.1.1.5.1.2'> 'Part 768' {
                                attribute POIconv : String = "-";
                                attribute Ipoint : Boolean = false;
                                attribute mass : Real = 0.7623726509781554;
                                attribute 'σ_mass' : Real = 0.28909372274994966;
                                attribute Cx : Real = 69.47185345925391;
                                attribute 'σ_Cx' : Real = 28.721044428837228;
                                attribute Cy : Real = -2.0173172000795603;
                                attribute 'σ_Cy' : Real = 28.23690002309109;
                                attribute Cz : Real = -86.9432061444968;
                                attribute 'σ_Cz' : Real = 29.057750463592832;
                                attribute Ixx : Real = 0.8576376699327082;
                                attribute 'σ_Ixx' : Real = 0.37074144170588635;
                                attribute Iyy : Real = 0.8397148979056432;
                                attribute 'σ_Iyy' : Real = 0.3723953238821935;
                                attribute Izz : Real = 0.8724622839788563;
                                attribute 'σ_Izz' : Real = 0.37017423652493897;
                                attribute Ixy : Real = -5.638058209259089e-4;
                                attribute 'σ_Ixy' : Real = 0.02351283871158888;
                                attribute Ixz : Real = -0.037207320753214354;
                                attribute 'σ_Ixz' : Real = 0.022566176940390956;
                                attribute Iyz : Real = 0.007065152923579082;
                                attribute 'σ_Iyz' : Real = 0.02209918015384651;
                            }
                            part <'C.1.2.1.1.5.1.3'> 'Part 769' {
                                attribute POIconv : String = "+";
                                attribute Ipoint : Boolean = false;
                                attribute mass : Real = 0.8892537194259931;
                                attribute 'σ_mass' : Real = 0.28909372274994966;
                                attribute Cx : Real = -64.19002362526953;
                                attribute 'σ_Cx' : Real = 28.721044428837228;
                                attribute Cy : Real = -53.05831846781075;
                                attribute 'σ_Cy' : Real = 28.23690002309109;
                                attribute Cz : Real = -96.73349955119193;
                                attribute 'σ_Cz' : Real = 29.057750463592832;
                                attribute Ixx : Real = 1.2116187826435152;
                                attribute 'σ_Ixx' : Real = 0.37074144170588635;
                                attribute Iyy : Real = 1.2584359351323027;
                                attribute 'σ_Iyy' : Real = 0.3723953238821935;
                                attribute Izz : Real = 1.1302634331857786;
                                attribute 'σ_Izz' : Real = 0.37017423652493897;
                                attribute Ixy : Real = 0.1341589230066552;
                                attribute 'σ_Ixy' : Real = 0.02351283871158888;
                                attribute Ixz : Real = -0.043961895459784996;
                                attribute 'σ_Ixz' : Real = 0.022566176940390956;
                                attribute Iyz : Real = 0.0583613139433051;
                                attribute 'σ_Iyz' : Real = 0.02209918015384651;
                            }
                            part <'C.1.2.1.1.5.1.4'> 'Part 770' {
                                attribute POIconv : String = "+";
                                attribute Ipoint : Boolean = false;
                                attribute mass : Real = 0.9904575951728039;
                                attribute 'σ_mass' : Real = 0.28909372274994966;
                                attribute Cx : Real = 61.228467524051666;
                                attribute 'σ_Cx' : Real = 28.721044428837228;
                                attribute Cy : Real = -57.03651010990143;
                                attribute 'σ_Cy' : Real = 28.23690002309109;
                                attribute Cz : Real = -75.83242342807353;
                                attribute 'σ_Cz' : Real = 29.057750463592832;
                                attribute Ixx : Real = 1.450999436849402;
                                attribute 'σ_Ixx' : Real = 0.37074144170588635;
                                attribute Iyy : Real = 1.4465851973513726;
                                attribute 'σ_Iyy' : Real = 0.3723953238821935;
                                attribute Izz : Real = 1.3892521103541877;
                                attribute 'σ_Izz' : Real = 0.37017423652493897;
                                attribute Ixy : Real = 0.052761326607632594;
                                attribute 'σ_Ixy' : Real = 0.02351283871158888;
                                attribute Ixz : Real = -0.026873505293566823;
                                attribute 'σ_Ixz' : Real = 0.022566176940390956;
                                attribute Iyz : Real = 0.04661180770760234;
                                attribute 'σ_Iyz' : Real = 0.02209918015384651;
                            }
                        }
                        part <'C.1.2.1.1.5.2'> 'Subassembly 218' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.5.2.1'> 'Part 771' {
                                attribute POIconv : String = "-";
                                attribute Ipoint : Boolean = false;
                                attribute mass : Real = 0.44893197653046807;
                                attribute 'σ_mass' : Real = 0.28909372274994966;
                                attribute Cx : Real = -82.07687162794173;
                                attribute 'σ_Cx' : Real = 28.721044428837228;
                                attribute Cy : Real = -22.418993525207043;
                                attribute 'σ_Cy' : Real = 28.23690002309109;
                                attribute Cz : Real = 44.156579952687025;
                                attribute 'σ_Cz' : Real = 29.057750463592832;
                                attribute Ixx : Real = 0.5267818403123529;
                                attribute 'σ_Ixx' : Real = 0.37074144170588635;
                                attribute Iyy : Real = 0.5375664968353558;
                                attribute 'σ_Iyy' : Real = 0.3723953238821935;
                                attribute Izz : Real = 0.5297466495891611;
                                attribute 'σ_Izz' : Real = 0.37017423652493897;
                                attribute Ixy : Real = 0.06213713452967075;
                                attribute 'σ_Ixy' : Real = 0.02351283871158888;
                                attribute Ixz : Real = 0.011125821022531384;
                                attribute 'σ_Ixz' : Real = 0.022566176940390956;
                                attribute Iyz : Real = 0.0032525252110808655;
                                attribute 'σ_Iyz' : Real = 0.02209918015384651;
                            }
                            part <'C.1.2.1.1.5.2.2'> 'Part 772' {
                                attribute POIconv : String = "-";
                                attribute Ipoint : Boolean = false;
                                attribute mass : Real = 0.10964515079557896;
                                attribute 'σ_mass' : Real = 0.28909372274994966;
                                attribute Cx : Real = -78.54775837622583;
                                attribute 'σ_Cx' : Real = 28.721044428837228;
                                attribute Cy : Real = 5.75883281417191;
                                attribute 'σ_Cy' : Real = 28.23690002309109;
                                attribute Cz : Real = 69.36393277719617;
                                attribute 'σ_Cz' : Real = 29.057750463592832;
                                attribute Ixx : Real = 0.16545610425835094;
                                attribute 'σ_Ixx' : Real = 0.37074144170588635;
                                attribute Iyy : Real = 0.1653972942144043;
                                attribute 'σ_Iyy' : Real = 0.3723953238821935;
                                attribute Izz : Real = 0.16613567936764315;
                                attribute 'σ_Izz' : Real = 0.37017423652493897;
                                attribute Ixy : Real = -0.0015699121439025992;
                                attribute 'σ_Ixy' : Real = 0.02351283871158888;
                                attribute Ixz : Real = -4.238479312110214e-4;
                                attribute 'σ_Ixz' : Real = 0.022566176940390956;
                                attribute Iyz : Real = -1.6084089021757016e-4;
                                attribute 'σ_Iyz' : Real = 0.02209918015384651;
                            }
                            part <'C.1.2.1.1.5.2.3'> 'Part 773' {
                                attribute POIconv : String = "+";
                                attribute Ipoint : Boolean = false;
                                attribute mass : Real = 0.9363493835476693;
                                attribute 'σ_mass' : Real = 0.28909372274994966;
                                attribute Cx : Real = -71.53889937326312;
                                attribute 'σ_Cx' : Real = 28.721044428837228;
                                attribute Cy : Real = 49.92168517783284;
                                attribute 'σ_Cy' : Real = 28.23690002309109;
                                attribute Cz : Real = -59.19090276584029;
                                attribute 'σ_Cz' : Real = 29.057750463592832;
                                attribute Ixx : Real = 1.1456403850620283;
                                attribute 'σ_Ixx' : Real = 0.37074144170588635;
                                attribute Iyy : Real = 1.0428318413211264;
                                attribute 'σ_Iyy' : Real = 0.3723953238821935;
                                attribute Izz : Real = 1.2169378553798562;
                                attribute 'σ_Izz' : Real = 0.37017423652493897;
                                attribute Ixy : Real = 0.0285679258404769;
                                attribute 'σ_Ixy' : Real = 0.02351283871158888;
                                attribute Ixz : Real = 0.013028664946784282;
                                attribute 'σ_Ixz' : Real = 0.022566176940390956;
                                attribute Iyz : Real = -0.12759449934227868;
                                attribute 'σ_Iyz' : Real = 0.02209918015384651;
                            }
                        }
                        part <'C.1.2.1.1.5.3'> 'Subassembly 219' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.1.5.3.1'> 'Part 774' {
                                attribute POIconv : String = "-";
                                attribute Ipoint : Boolean = false;
                                attribute mass : Real = 0.22822092658933252;
                                attribute 'σ_mass' : Real = 0.28909372274994966;
                                attribute Cx : Real = -42.45407823473215;
                                attribute 'σ_Cx' : Real = 28.721044428837228;
                                attribute Cy : Real = 65.19768619909883;
                                attribute 'σ_Cy' : Real = 28.23690002309109;
                                attribute Cz : Real = 68.07190831750631;
                                attribute 'σ_Cz' : Real = 29.057750463592832;
                                attribute Ixx : Real = 0.2519599745029747;
                                attribute 'σ_Ixx' : Real = 0.37074144170588635;
                                attribute Iyy : Real = 0.2849329417934086;
                                attribute 'σ_Iyy' : Real = 0.3723953238821935;
                                attribute Izz : Real = 0.2544985260512138;
                                attribute 'σ_Izz' : Real = 0.37017423652493897;
                                attribute Ixy : Real = 0.008337022183107324;
                                attribute 'σ_Ixy' : Real = 0.02351283871158888;
                                attribute Ixz : Real = 0.002969449483961998;
                                attribute 'σ_Ixz' : Real = 0.022566176940390956;
                                attribute Iyz : Real = -0.016146147023346737;
                                attribute 'σ_Iyz' : Real = 0.02209918015384651;
                            }
                            part <'C.1.2.1.1.5.3.2'> 'Part 775' {
                                attribute POIconv : String = "-";
                                attribute Ipoint : Boolean = false;
                                attribute mass : Real = 0.104783451550873;
                                attribute 'σ_mass' : Real = 0.28909372274994966;
                                attribute Cx : Real = 99.49730103835464;
                                attribute 'σ_Cx' : Real = 28.721044428837228;
                                attribute Cy : Real = -41.50637527927756;
                                attribute 'σ_Cy' : Real = 28.23690002309109;
                                attribute Cz : Real = 24.398598726838827;
                                attribute 'σ_Cz' : Real = 29.057750463592832;
                                attribute Ixx : Real = 0.15946042967904428;
                                attribute 'σ_Ixx' : Real = 0.37074144170588635;
                                attribute Iyy : Real = 0.1360520345405073;
                                attribute 'σ_Iyy' : Real = 0.3723953238821935;
                                attribute Izz : Real = 0.1404153103220111;
                                attribute 'σ_Izz' : Real = 0.37017423652493897;
                                attribute Ixy : Real = -0.003013201887400724;
                                attribute 'σ_Ixy' : Real = 0.02351283871158888;
                                attribute Ixz : Real = -0.010874443877669969;
                                attribute 'σ_Ixz' : Real = 0.022566176940390956;
                                attribute Iyz : Real = 0.003281610730306406;
                                attribute 'σ_Iyz' : Real = 0.02209918015384651;
                            }
                            part <'C.1.2.1.1.5.3.3'> 'Part 776' {
                                attribute POIconv : String = "+";
                                attribute Ipoint : Boolean = false;
                                attribute mass : Real = 0.9823710635530297;
                                attribute 'σ_mass' : Real = 0.28909372274994966;
                                attribute Cx : Real = -42.41316132247448;
                                attribute 'σ_Cx' : Real = 28.721044428837228;
                                attribute Cy : Real = 16.09321190044284;
                                attribute 'σ_Cy' : Real = 28.23690002309109;
                                attribute Cz : Real = 67.75510092265904;
                                attribute 'σ_Cz' : Real = 29.057750463592832;
                                attribute Ixx : Real = 1.2763381627499564;
                                attribute 'σ_Ixx' : Real = 0.37074144170588635;
                                attribute Iyy : Real = 1.1808771402304434;
                                attribute 'σ_Iyy' : Real = 0.3723953238821935;
                                attribute Izz : Real = 1.2707901107618664;
                                attribute 'σ_Izz' : Real = 0.37017423652493897;
                                attribute Ixy : Real = 0.02686755004193902;
                                attribute 'σ_Ixy' : Real = 0.02351283871158888;
                                attribute Ixz : Real = 0.13115652833312072;
                                attribute 'σ_Ixz' : Real = 0.022566176940390956;
                                attribute Iyz : Real = -0.0013094827294243363;
                                attribute 'σ_Iyz' : Real = 0.02209918015384651;
                            }
                            part <'C.1.2.1.1.5.3.4'> 'Part 777' {
                                attribute POIconv : String = "+";
                                attribute Ipoint : Boolean = false;
                                attribute mass : Real = 0.7311486817158293;
                                attribute 'σ_mass' : Real = 0.28909372274994966;
                                attribute Cx : Real = -80.91749688610435;
                                attribute 'σ_Cx' : Real = 28.721044428837228;
                                attribute Cy : Real = 31.412918213754892;
                                attribute 'σ_Cy' : Real = 28.23690002309109;
                                attribute Cz : Real = -90.84783890284598;
                                attribute 'σ_Cz' : Real = 29.057750463592832;
                                attribute Ixx : Real = 0.9980395740991406;
                                attribute 'σ_Ixx' : Real = 0.37074144170588635;
                                attribute Iyy : Real = 1.053134739700956;
                                attribute 'σ_Iyy' : Real = 0.3723953238821935;
                                attribute Izz : Real = 0.9662200240424487;
                                attribute 'σ_Izz' : Real = 0.37017423652493897;
                                attribute Ixy : Real = 0.00528769245190217;
                                attribute 'σ_Ixy' : Real = 0.02351283871158888;
                                attribute Ixz : Real = -0.06299754912570033;
                                attribute 'σ_Ixz' : Real = 0.022566176940390956;
                                attribute Iyz : Real = -0.007697997122978592;
                                attribute 'σ_Iyz' : Real = 0.02209918015384651;
                            }
                        }
                    }
                }
                part <'C.1.2.1.2'> 'Subsystem 17' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.2.1.2.1'> 'Assembly 63' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.2.1.1'> 'Subassembly 220' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.1.1.1'> 'Part 778' {
                                attribute POIconv : String = "+";
                                attribute Ipoint : Boolean = false;
                                attribute mass : Real = 0.41286444995505733;
                                attribute 'σ_mass' : Real = 0.28909372274994966;
                                attribute Cx : Real = -80.11870658956468;
                                attribute 'σ_Cx' : Real = 28.721044428837228;
                                attribute Cy : Real = -9.176073502749205;
                                attribute 'σ_Cy' : Real = 28.23690002309109;
                                attribute Cz : Real = -93.96118237636983;
                                attribute 'σ_Cz' : Real = 29.057750463592832;
                                attribute Ixx : Real = 0.5006014442701897;
                                attribute 'σ_Ixx' : Real = 0.37074144170588635;
                                attribute Iyy : Real = 0.5613260149464682;
                                attribute 'σ_Iyy' : Real = 0.3723953238821935;
                                attribute Izz : Real = 0.5083341661142695;
                                attribute 'σ_Izz' : Real = 0.37017423652493897;
                                attribute Ixy : Real = -0.008335125569639095;
                                attribute 'σ_Ixy' : Real = 0.02351283871158888;
                                attribute Ixz : Real = -0.0011739496303814223;
                                attribute 'σ_Ixz' : Real = 0.022566176940390956;
                                attribute Iyz : Real = 0.011941151418716867;
                                attribute 'σ_Iyz' : Real = 0.02209918015384651;
                            }
                            part <'C.1.2.1.2.1.1.2'> 'Part 779' {
                                attribute POIconv : String = "+";
                                attribute Ipoint : Boolean = false;
                                attribute mass : Real = 0.6349201471554116;
                                attribute 'σ_mass' : Real = 0.28909372274994966;
                                attribute Cx : Real = -42.936782632023096;
                                attribute 'σ_Cx' : Real = 28.721044428837228;
                                attribute Cy : Real = 84.37530072405934;
                                attribute 'σ_Cy' : Real = 28.23690002309109;
                                attribute Cz : Real = 6.909901229664683;
                                attribute 'σ_Cz' : Real = 29.057750463592832;
                                attribute Ixx : Real = 0.8262026797328038;
                                attribute 'σ_Ixx' : Real = 0.37074144170588635;
                                attribute Iyy : Real = 0.7573006946951042;
                                attribute 'σ_Iyy' : Real = 0.3723953238821935;
                                attribute Izz : Real = 0.7951284252119959;
                                attribute 'σ_Izz' : Real = 0.37017423652493897;
                                attribute Ixy : Real = -0.017584851290701836;
                                attribute 'σ_Ixy' : Real = 0.02351283871158888;
                                attribute Ixz : Real = 0.0555827345314092;
                                attribute 'σ_Ixz' : Real = 0.022566176940390956;
                                attribute Iyz : Real = 0.01313166517758729;
                                attribute 'σ_Iyz' : Real = 0.02209918015384651;
                            }
                            part <'C.1.2.1.2.1.1.3'> 'Part 780' {
                                attribute POIconv : String = "-";
                                attribute Ipoint : Boolean = false;
                                attribute mass : Real = 0.8232423624026124;
                                attribute 'σ_mass' : Real = 0.28909372274994966;
                                attribute Cx : Real = 44.8974197730422;
                                attribute 'σ_Cx' : Real = 28.721044428837228;
                                attribute Cy : Real = -14.16948288679123;
                                attribute 'σ_Cy' : Real = 28.23690002309109;
                                attribute Cz : Real = 18.04359396919608;
                                attribute 'σ_Cz' : Real = 29.057750463592832;
                                attribute Ixx : Real = 0.8529543994773128;
                                attribute 'σ_Ixx' : Real = 0.37074144170588635;
                                attribute Iyy : Real = 1.0005047722865716;
                                attribute 'σ_Iyy' : Real = 0.3723953238821935;
                                attribute Izz : Real = 0.8875006861511404;
                                attribute 'σ_Izz' : Real = 0.37017423652493897;
                                attribute Ixy : Real = 0.03742509760428832;
                                attribute 'σ_Ixy' : Real = 0.02351283871158888;
                                attribute Ixz : Real = -0.0202389373245859;
                                attribute 'σ_Ixz' : Real = 0.022566176940390956;
                                attribute Iyz : Real = -0.04347066600767492;
                                attribute 'σ_Iyz' : Real = 0.02209918015384651;
                            }
                        }
                        part <'C.1.2.1.2.1.2'> 'Subassembly 221' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.1.2.1'> 'Part 781' {
                                attribute POIconv : String = "+";
                                attribute Ipoint : Boolean = false;
                                attribute mass : Real = 0.8406150858458131;
                                attribute 'σ_mass' : Real = 0.28909372274994966;
                                attribute Cx : Real = 28.289434034377337;
                                attribute 'σ_Cx' : Real = 28.721044428837228;
                                attribute Cy : Real = -92.75471246801317;
                                attribute 'σ_Cy' : Real = 28.23690002309109;
                                attribute Cz : Real = 54.273062804713845;
                                attribute 'σ_Cz' : Real = 29.057750463592832;
                                attribute Ixx : Real = 1.0377826440673519;
                                attribute 'σ_Ixx' : Real = 0.37074144170588635;
                                attribute Iyy : Real = 0.9991675080828684;
                                attribute 'σ_Iyy' : Real = 0.3723953238821935;
                                attribute Izz : Real = 0.9348811901149295;
                                attribute 'σ_Izz' : Real = 0.37017423652493897;
                                attribute Ixy : Real = 0.08029893263442443;
                                attribute 'σ_Ixy' : Real = 0.02351283871158888;
                                attribute Ixz : Real = -0.021818523502584213;
                                attribute 'σ_Ixz' : Real = 0.022566176940390956;
                                attribute Iyz : Real = 0.02859973497923255;
                                attribute 'σ_Iyz' : Real = 0.02209918015384651;
                            }
                            part <'C.1.2.1.2.1.2.2'> 'Part 782' {
                                attribute POIconv : String = "+";
                                attribute Ipoint : Boolean = false;
                                attribute mass : Real = 0.41138457311852833;
                                attribute 'σ_mass' : Real = 0.28909372274994966;
                                attribute Cx : Real = -60.38090195506811;
                                attribute 'σ_Cx' : Real = 28.721044428837228;
                                attribute Cy : Real = -74.73182738758624;
                                attribute 'σ_Cy' : Real = 28.23690002309109;
                                attribute Cz : Real = -70.47930038534105;
                                attribute 'σ_Cz' : Real = 29.057750463592832;
                                attribute Ixx : Real = 0.5922631980969985;
                                attribute 'σ_Ixx' : Real = 0.37074144170588635;
                                attribute Iyy : Real = 0.5411192511834149;
                                attribute 'σ_Iyy' : Real = 0.3723953238821935;
                                attribute Izz : Real = 0.5990343141784179;
                                attribute 'σ_Izz' : Real = 0.37017423652493897;
                                attribute Ixy : Real = -0.020869722686725885;
                                attribute 'σ_Ixy' : Real = 0.02351283871158888;
                                attribute Ixz : Real = -0.01523174005210233;
                                attribute 'σ_Ixz' : Real = 0.022566176940390956;
                                attribute Iyz : Real = 0.023378957476498523;
                                attribute 'σ_Iyz' : Real = 0.02209918015384651;
                            }
                            part <'C.1.2.1.2.1.2.3'> 'Part 783' {
                                attribute POIconv : String = "-";
                                attribute Ipoint : Boolean = false;
                                attribute mass : Real = 0.3103963250808883;
                                attribute 'σ_mass' : Real = 0.28909372274994966;
                                attribute Cx : Real = -86.36587564833462;
                                attribute 'σ_Cx' : Real = 28.721044428837228;
                                attribute Cy : Real = 37.37825551070273;
                                attribute 'σ_Cy' : Real = 28.23690002309109;
                                attribute Cz : Real = -12.789325974881649;
                                attribute 'σ_Cz' : Real = 29.057750463592832;
                                attribute Ixx : Real = 0.4558636942131506;
                                attribute 'σ_Ixx' : Real = 0.37074144170588635;
                                attribute Iyy : Real = 0.4362299037507578;
                                attribute 'σ_Iyy' : Real = 0.3723953238821935;
                                attribute Izz : Real = 0.41569703789169093;
                                attribute 'σ_Izz' : Real = 0.37017423652493897;
                                attribute Ixy : Real = -0.01724698906522204;
                                attribute 'σ_Ixy' : Real = 0.02351283871158888;
                                attribute Ixz : Real = 0.02656037023855388;
                                attribute 'σ_Ixz' : Real = 0.022566176940390956;
                                attribute Iyz : Real = -0.01424340741913138;
                                attribute 'σ_Iyz' : Real = 0.02209918015384651;
                            }
                            part <'C.1.2.1.2.1.2.4'> 'Part 784' {
                                attribute POIconv : String = "-";
                                attribute Ipoint : Boolean = false;
                                attribute mass : Real = 0.6346428919578903;
                                attribute 'σ_mass' : Real = 0.28909372274994966;
                                attribute Cx : Real = 77.9730660840869;
                                attribute 'σ_Cx' : Real = 28.721044428837228;
                                attribute Cy : Real = -28.495900006964803;
                                attribute 'σ_Cy' : Real = 28.23690002309109;
                                attribute Cz : Real = -50.029381830245256;
                                attribute 'σ_Cz' : Real = 29.057750463592832;
                                attribute Ixx : Real = 0.7329935548123732;
                                attribute 'σ_Ixx' : Real = 0.37074144170588635;
                                attribute Iyy : Real = 0.7614634901049598;
                                attribute 'σ_Iyy' : Real = 0.3723953238821935;
                                attribute Izz : Real = 0.7121820272445466;
                                attribute 'σ_Izz' : Real = 0.37017423652493897;
                                attribute Ixy : Real = -0.005801728419172125;
                                attribute 'σ_Ixy' : Real = 0.02351283871158888;
                                attribute Ixz : Real = 0.03259256217629318;
                                attribute 'σ_Ixz' : Real = 0.022566176940390956;
                                attribute Iyz : Real = -0.0846216388887258;
                                attribute 'σ_Iyz' : Real = 0.02209918015384651;
                            }
                            part <'C.1.2.1.2.1.2.5'> 'Part 785' {
                                attribute POIconv : String = "+";
                                attribute Ipoint : Boolean = false;
                                attribute mass : Real = 0.08807765604951419;
                                attribute 'σ_mass' : Real = 0.28909372274994966;
                                attribute Cx : Real = 48.47814557142556;
                                attribute 'σ_Cx' : Real = 28.721044428837228;
                                attribute Cy : Real = -8.225739328190684;
                                attribute 'σ_Cy' : Real = 28.23690002309109;
                                attribute Cz : Real = -99.26294223405421;
                                attribute 'σ_Cz' : Real = 29.057750463592832;
                                attribute Ixx : Real = 0.11491125136854019;
                                attribute 'σ_Ixx' : Real = 0.37074144170588635;
                                attribute Iyy : Real = 0.11290689270670443;
                                attribute 'σ_Iyy' : Real = 0.3723953238821935;
                                attribute Izz : Real = 0.11238279128986862;
                                attribute 'σ_Izz' : Real = 0.37017423652493897;
                                attribute Ixy : Real = -0.0101107471521697;
                                attribute 'σ_Ixy' : Real = 0.02351283871158888;
                                attribute Ixz : Real = 0.0052061339342657645;
                                attribute 'σ_Ixz' : Real = 0.022566176940390956;
                                attribute Iyz : Real = 0.004563497151681397;
                                attribute 'σ_Iyz' : Real = 0.02209918015384651;
                            }
                        }
                    }
                    part <'C.1.2.1.2.2'> 'Assembly 64' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.2.2.1'> 'Subassembly 222' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.2.1.1'> 'Part 786' {
                                attribute POIconv : String = "+";
                                attribute Ipoint : Boolean = false;
                                attribute mass : Real = 0.7031996298830491;
                                attribute 'σ_mass' : Real = 0.28909372274994966;
                                attribute Cx : Real = 81.47697360254824;
                                attribute 'σ_Cx' : Real = 28.721044428837228;
                                attribute Cy : Real = -43.803377309814095;
                                attribute 'σ_Cy' : Real = 28.23690002309109;
                                attribute Cz : Real = 86.12206494435668;
                                attribute 'σ_Cz' : Real = 29.057750463592832;
                                attribute Ixx : Real = 0.8271366912517517;
                                attribute 'σ_Ixx' : Real = 0.37074144170588635;
                                attribute Iyy : Real = 0.8186292982732727;
                                attribute 'σ_Iyy' : Real = 0.3723953238821935;
                                attribute Izz : Real = 0.804797359763256;
                                attribute 'σ_Izz' : Real = 0.37017423652493897;
                                attribute Ixy : Real = 0.021796703704930157;
                                attribute 'σ_Ixy' : Real = 0.02351283871158888;
                                attribute Ixz : Real = -0.023162278768574483;
                                attribute 'σ_Ixz' : Real = 0.022566176940390956;
                                attribute Iyz : Real = 0.08761959001342756;
                                attribute 'σ_Iyz' : Real = 0.02209918015384651;
                            }
                            part <'C.1.2.1.2.2.1.2'> 'Part 787' {
                                attribute POIconv : String = "-";
                                attribute Ipoint : Boolean = false;
                                attribute mass : Real = 0.6107096083378419;
                                attribute 'σ_mass' : Real = 0.28909372274994966;
                                attribute Cx : Real = -10.976454429328442;
                                attribute 'σ_Cx' : Real = 28.721044428837228;
                                attribute Cy : Real = 61.08013056218624;
                                attribute 'σ_Cy' : Real = 28.23690002309109;
                                attribute Cz : Real = -23.59348777681589;
                                attribute 'σ_Cz' : Real = 29.057750463592832;
                                attribute Ixx : Real = 0.7580609423746537;
                                attribute 'σ_Ixx' : Real = 0.37074144170588635;
                                attribute Iyy : Real = 0.8641249607043112;
                                attribute 'σ_Iyy' : Real = 0.3723953238821935;
                                attribute Izz : Real = 0.8865991324989235;
                                attribute 'σ_Izz' : Real = 0.37017423652493897;
                                attribute Ixy : Real = -0.029844529749869755;
                                attribute 'σ_Ixy' : Real = 0.02351283871158888;
                                attribute Ixz : Real = 0.0134027210150167;
                                attribute 'σ_Ixz' : Real = 0.022566176940390956;
                                attribute Iyz : Real = 0.0010237878947334162;
                                attribute 'σ_Iyz' : Real = 0.02209918015384651;
                            }
                            part <'C.1.2.1.2.2.1.3'> 'Part 788' {
                                attribute POIconv : String = "+";
                                attribute Ipoint : Boolean = false;
                                attribute mass : Real = 0.7216352113587782;
                                attribute 'σ_mass' : Real = 0.28909372274994966;
                                attribute Cx : Real = -80.56707042269409;
                                attribute 'σ_Cx' : Real = 28.721044428837228;
                                attribute Cy : Real = 74.56366918049753;
                                attribute 'σ_Cy' : Real = 28.23690002309109;
                                attribute Cz : Real = 73.98471292108297;
                                attribute 'σ_Cz' : Real = 29.057750463592832;
                                attribute Ixx : Real = 0.9517261039315572;
                                attribute 'σ_Ixx' : Real = 0.37074144170588635;
                                attribute Iyy : Real = 0.9263140208916567;
                                attribute 'σ_Iyy' : Real = 0.3723953238821935;
                                attribute Izz : Real = 0.9808649857378658;
                                attribute 'σ_Izz' : Real = 0.37017423652493897;
                                attribute Ixy : Real = -0.0807944541635773;
                                attribute 'σ_Ixy' : Real = 0.02351283871158888;
                                attribute Ixz : Real = -0.030194919784497253;
                                attribute 'σ_Ixz' : Real = 0.022566176940390956;
                                attribute Iyz : Real = 0.04721151010382231;
                                attribute 'σ_Iyz' : Real = 0.02209918015384651;
                            }
                        }
                        part <'C.1.2.1.2.2.2'> 'Subassembly 223' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.2.2.1'> 'Part 789' {
                                attribute POIconv : String = "-";
                                attribute Ipoint : Boolean = false;
                                attribute mass : Real = 0.5963625535315369;
                                attribute 'σ_mass' : Real = 0.28909372274994966;
                                attribute Cx : Real = -35.33959714695811;
                                attribute 'σ_Cx' : Real = 28.721044428837228;
                                attribute Cy : Real = 5.758345918729901;
                                attribute 'σ_Cy' : Real = 28.23690002309109;
                                attribute Cz : Real = -10.905125783756375;
                                attribute 'σ_Cz' : Real = 29.057750463592832;
                                attribute Ixx : Real = 0.7097071432749391;
                                attribute 'σ_Ixx' : Real = 0.37074144170588635;
                                attribute Iyy : Real = 0.6050444493016389;
                                attribute 'σ_Iyy' : Real = 0.3723953238821935;
                                attribute Izz : Real = 0.7361689943627573;
                                attribute 'σ_Izz' : Real = 0.37017423652493897;
                                attribute Ixy : Real = -0.0514443556230926;
                                attribute 'σ_Ixy' : Real = 0.02351283871158888;
                                attribute Ixz : Real = 9.522132880161172e-4;
                                attribute 'σ_Ixz' : Real = 0.022566176940390956;
                                attribute Iyz : Real = 0.0027711750428329107;
                                attribute 'σ_Iyz' : Real = 0.02209918015384651;
                            }
                            part <'C.1.2.1.2.2.2.2'> 'Part 790' {
                                attribute POIconv : String = "+";
                                attribute Ipoint : Boolean = false;
                                attribute mass : Real = 0.3418703714166768;
                                attribute 'σ_mass' : Real = 0.28909372274994966;
                                attribute Cx : Real = 77.8700512368232;
                                attribute 'σ_Cx' : Real = 28.721044428837228;
                                attribute Cy : Real = 84.35743851587176;
                                attribute 'σ_Cy' : Real = 28.23690002309109;
                                attribute Cz : Real = 98.81083653308451;
                                attribute 'σ_Cz' : Real = 29.057750463592832;
                                attribute Ixx : Real = 0.3761324052244434;
                                attribute 'σ_Ixx' : Real = 0.37074144170588635;
                                attribute Iyy : Real = 0.4090230709603732;
                                attribute 'σ_Iyy' : Real = 0.3723953238821935;
                                attribute Izz : Real = 0.3315132307243925;
                                attribute 'σ_Izz' : Real = 0.37017423652493897;
                                attribute Ixy : Real = -0.009686537253991271;
                                attribute 'σ_Ixy' : Real = 0.02351283871158888;
                                attribute Ixz : Real = -0.0016634354892348304;
                                attribute 'σ_Ixz' : Real = 0.022566176940390956;
                                attribute Iyz : Real = -0.007568236412766384;
                                attribute 'σ_Iyz' : Real = 0.02209918015384651;
                            }
                        }
                    }
                    part <'C.1.2.1.2.3'> 'Assembly 65' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.2.3.1'> 'Subassembly 224' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.3.1.1'> 'Part 791' {
                                attribute POIconv : String = "-";
                                attribute Ipoint : Boolean = false;
                                attribute mass : Real = 0.012558446371462195;
                                attribute 'σ_mass' : Real = 0.28909372274994966;
                                attribute Cx : Real = -9.401254961267114;
                                attribute 'σ_Cx' : Real = 28.721044428837228;
                                attribute Cy : Real = 96.58035659231246;
                                attribute 'σ_Cy' : Real = 28.23690002309109;
                                attribute Cz : Real = -64.46152739226818;
                                attribute 'σ_Cz' : Real = 29.057750463592832;
                                attribute Ixx : Real = 0.015639866775647954;
                                attribute 'σ_Ixx' : Real = 0.37074144170588635;
                                attribute Iyy : Real = 0.015467731929471446;
                                attribute 'σ_Iyy' : Real = 0.3723953238821935;
                                attribute Izz : Real = 0.018537051960053934;
                                attribute 'σ_Izz' : Real = 0.37017423652493897;
                                attribute Ixy : Real = 1.8817300658688984e-4;
                                attribute 'σ_Ixy' : Real = 0.02351283871158888;
                                attribute Ixz : Real = 9.787084608281348e-4;
                                attribute 'σ_Ixz' : Real = 0.022566176940390956;
                                attribute Iyz : Real = 7.396656484681778e-4;
                                attribute 'σ_Iyz' : Real = 0.02209918015384651;
                            }
                            part <'C.1.2.1.2.3.1.2'> 'Part 792' {
                                attribute POIconv : String = "-";
                                attribute Ipoint : Boolean = false;
                                attribute mass : Real = 0.13000083908019588;
                                attribute 'σ_mass' : Real = 0.28909372274994966;
                                attribute Cx : Real = -72.66408405266702;
                                attribute 'σ_Cx' : Real = 28.721044428837228;
                                attribute Cy : Real = 74.18267871253192;
                                attribute 'σ_Cy' : Real = 28.23690002309109;
                                attribute Cz : Real = -38.575056521221995;
                                attribute 'σ_Cz' : Real = 29.057750463592832;
                                attribute Ixx : Real = 0.1786128631912603;
                                attribute 'σ_Ixx' : Real = 0.37074144170588635;
                                attribute Iyy : Real = 0.1621730835901498;
                                attribute 'σ_Iyy' : Real = 0.3723953238821935;
                                attribute Izz : Real = 0.16749981245858192;
                                attribute 'σ_Izz' : Real = 0.37017423652493897;
                                attribute Ixy : Real = 0.0027644068384633305;
                                attribute 'σ_Ixy' : Real = 0.02351283871158888;
                                attribute Ixz : Real = -5.334154205201602e-4;
                                attribute 'σ_Ixz' : Real = 0.022566176940390956;
                                attribute Iyz : Real = 0.0036116496686958302;
                                attribute 'σ_Iyz' : Real = 0.02209918015384651;
                            }
                            part <'C.1.2.1.2.3.1.3'> 'Part 793' {
                                attribute POIconv : String = "-";
                                attribute Ipoint : Boolean = false;
                                attribute mass : Real = 0.4713674660718534;
                                attribute 'σ_mass' : Real = 0.28909372274994966;
                                attribute Cx : Real = 22.665188275277615;
                                attribute 'σ_Cx' : Real = 28.721044428837228;
                                attribute Cy : Real = -14.303641393780708;
                                attribute 'σ_Cy' : Real = 28.23690002309109;
                                attribute Cz : Real = 30.133107444271445;
                                attribute 'σ_Cz' : Real = 29.057750463592832;
                                attribute Ixx : Real = 0.5397245576688406;
                                attribute 'σ_Ixx' : Real = 0.37074144170588635;
                                attribute Iyy : Real = 0.6836537021671852;
                                attribute 'σ_Iyy' : Real = 0.3723953238821935;
                                attribute Izz : Real = 0.6085699672212673;
                                attribute 'σ_Izz' : Real = 0.37017423652493897;
                                attribute Ixy : Real = -0.03318666805579211;
                                attribute 'σ_Ixy' : Real = 0.02351283871158888;
                                attribute Ixz : Real = 0.008271110673804191;
                                attribute 'σ_Ixz' : Real = 0.022566176940390956;
                                attribute Iyz : Real = -0.039573510499747326;
                                attribute 'σ_Iyz' : Real = 0.02209918015384651;
                            }
                            part <'C.1.2.1.2.3.1.4'> 'Part 794' {
                                attribute POIconv : String = "+";
                                attribute Ipoint : Boolean = false;
                                attribute mass : Real = 0.46327470292407086;
                                attribute 'σ_mass' : Real = 0.28909372274994966;
                                attribute Cx : Real = -71.8374929856509;
                                attribute 'σ_Cx' : Real = 28.721044428837228;
                                attribute Cy : Real = -79.42816913127899;
                                attribute 'σ_Cy' : Real = 28.23690002309109;
                                attribute Cz : Real = -60.00831709243357;
                                attribute 'σ_Cz' : Real = 29.057750463592832;
                                attribute Ixx : Real = 0.4667536653394323;
                                attribute 'σ_Ixx' : Real = 0.37074144170588635;
                                attribute Iyy : Real = 0.5582397311971575;
                                attribute 'σ_Iyy' : Real = 0.3723953238821935;
                                attribute Izz : Real = 0.5499085677142368;
                                attribute 'σ_Izz' : Real = 0.37017423652493897;
                                attribute Ixy : Real = -0.026660538558051554;
                                attribute 'σ_Ixy' : Real = 0.02351283871158888;
                                attribute Ixz : Real = 0.040320603938838503;
                                attribute 'σ_Ixz' : Real = 0.022566176940390956;
                                attribute Iyz : Real = -0.03456744239219553;
                                attribute 'σ_Iyz' : Real = 0.02209918015384651;
                            }
                        }
                        part <'C.1.2.1.2.3.2'> 'Subassembly 225' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.3.2.1'> 'Part 795' {
                                attribute POIconv : String = "-";
                                attribute Ipoint : Boolean = false;
                                attribute mass : Real = 0.39806503427005374;
                                attribute 'σ_mass' : Real = 0.28909372274994966;
                                attribute Cx : Real = 33.050579437986016;
                                attribute 'σ_Cx' : Real = 28.721044428837228;
                                attribute Cy : Real = -44.42807612940669;
                                attribute 'σ_Cy' : Real = 28.23690002309109;
                                attribute Cz : Real = 36.527072079479694;
                                attribute 'σ_Cz' : Real = 29.057750463592832;
                                attribute Ixx : Real = 0.5221425703793039;
                                attribute 'σ_Ixx' : Real = 0.37074144170588635;
                                attribute Iyy : Real = 0.5838256671670221;
                                attribute 'σ_Iyy' : Real = 0.3723953238821935;
                                attribute Izz : Real = 0.48283318939255543;
                                attribute 'σ_Izz' : Real = 0.37017423652493897;
                                attribute Ixy : Real = -0.052691696772483615;
                                attribute 'σ_Ixy' : Real = 0.02351283871158888;
                                attribute Ixz : Real = -0.01589208358967671;
                                attribute 'σ_Ixz' : Real = 0.022566176940390956;
                                attribute Iyz : Real = 0.03376923647044447;
                                attribute 'σ_Iyz' : Real = 0.02209918015384651;
                            }
                            part <'C.1.2.1.2.3.2.2'> 'Part 796' {
                                attribute POIconv : String = "+";
                                attribute Ipoint : Boolean = false;
                                attribute mass : Real = 0.12597863628156483;
                                attribute 'σ_mass' : Real = 0.28909372274994966;
                                attribute Cx : Real = 85.793522791937;
                                attribute 'σ_Cx' : Real = 28.721044428837228;
                                attribute Cy : Real = 19.847188564017415;
                                attribute 'σ_Cy' : Real = 28.23690002309109;
                                attribute Cz : Real = 39.365075808018446;
                                attribute 'σ_Cz' : Real = 29.057750463592832;
                                attribute Ixx : Real = 0.13465962923434727;
                                attribute 'σ_Ixx' : Real = 0.37074144170588635;
                                attribute Iyy : Real = 0.14294484600814117;
                                attribute 'σ_Iyy' : Real = 0.3723953238821935;
                                attribute Izz : Real = 0.13153587967221464;
                                attribute 'σ_Izz' : Real = 0.37017423652493897;
                                attribute Ixy : Real = -0.008150964249004536;
                                attribute 'σ_Ixy' : Real = 0.02351283871158888;
                                attribute Ixz : Real = -0.003214904828495585;
                                attribute 'σ_Ixz' : Real = 0.022566176940390956;
                                attribute Iyz : Real = -0.0035920655210944325;
                                attribute 'σ_Iyz' : Real = 0.02209918015384651;
                            }
                        }
                        part <'C.1.2.1.2.3.3'> 'Subassembly 226' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.3.3.1'> 'Part 797' {
                                attribute POIconv : String = "+";
                                attribute Ipoint : Boolean = false;
                                attribute mass : Real = 0.07205253432295285;
                                attribute 'σ_mass' : Real = 0.28909372274994966;
                                attribute Cx : Real = 68.93592262640595;
                                attribute 'σ_Cx' : Real = 28.721044428837228;
                                attribute Cy : Real = -2.637602109462023;
                                attribute 'σ_Cy' : Real = 28.23690002309109;
                                attribute Cz : Real = 99.48066803626716;
                                attribute 'σ_Cz' : Real = 29.057750463592832;
                                attribute Ixx : Real = 0.11211532557190812;
                                attribute 'σ_Ixx' : Real = 0.37074144170588635;
                                attribute Iyy : Real = 0.10582829990345527;
                                attribute 'σ_Iyy' : Real = 0.3723953238821935;
                                attribute Izz : Real = 0.10527760182278931;
                                attribute 'σ_Izz' : Real = 0.37017423652493897;
                                attribute Ixy : Real = 0.004385117292331931;
                                attribute 'σ_Ixy' : Real = 0.02351283871158888;
                                attribute Ixz : Real = -0.0037896988567930195;
                                attribute 'σ_Ixz' : Real = 0.022566176940390956;
                                attribute Iyz : Real = 0.0019253537541727747;
                                attribute 'σ_Iyz' : Real = 0.02209918015384651;
                            }
                            part <'C.1.2.1.2.3.3.2'> 'Part 798' {
                                attribute POIconv : String = "+";
                                attribute Ipoint : Boolean = false;
                                attribute mass : Real = 0.15758021018328144;
                                attribute 'σ_mass' : Real = 0.28909372274994966;
                                attribute Cx : Real = -68.36304180324078;
                                attribute 'σ_Cx' : Real = 28.721044428837228;
                                attribute Cy : Real = -25.796094117686152;
                                attribute 'σ_Cy' : Real = 28.23690002309109;
                                attribute Cz : Real = 6.208848906680942;
                                attribute 'σ_Cz' : Real = 29.057750463592832;
                                attribute Ixx : Real = 0.15362150771886662;
                                attribute 'σ_Ixx' : Real = 0.37074144170588635;
                                attribute Iyy : Real = 0.20440283854162733;
                                attribute 'σ_Iyy' : Real = 0.3723953238821935;
                                attribute Izz : Real = 0.18334220277604707;
                                attribute 'σ_Izz' : Real = 0.37017423652493897;
                                attribute Ixy : Real = -8.39053861175939e-4;
                                attribute 'σ_Ixy' : Real = 0.02351283871158888;
                                attribute Ixz : Real = -0.020888683997046145;
                                attribute 'σ_Ixz' : Real = 0.022566176940390956;
                                attribute Iyz : Real = -3.394102806807878e-4;
                                attribute 'σ_Iyz' : Real = 0.02209918015384651;
                            }
                            part <'C.1.2.1.2.3.3.3'> 'Part 799' {
                                attribute POIconv : String = "+";
                                attribute Ipoint : Boolean = false;
                                attribute mass : Real = 0.9852040670020505;
                                attribute 'σ_mass' : Real = 0.28909372274994966;
                                attribute Cx : Real = 8.059286838397384;
                                attribute 'σ_Cx' : Real = 28.721044428837228;
                                attribute Cy : Real = -39.23310409300029;
                                attribute 'σ_Cy' : Real = 28.23690002309109;
                                attribute Cz : Real = 86.49324448779225;
                                attribute 'σ_Cz' : Real = 29.057750463592832;
                                attribute Ixx : Real = 1.1073300174930836;
                                attribute 'σ_Ixx' : Real = 0.37074144170588635;
                                attribute Iyy : Real = 1.1611449787739927;
                                attribute 'σ_Iyy' : Real = 0.3723953238821935;
                                attribute Izz : Real = 1.019627518350172;
                                attribute 'σ_Izz' : Real = 0.37017423652493897;
                                attribute Ixy : Real = 0.0070599408844334;
                                attribute 'σ_Ixy' : Real = 0.02351283871158888;
                                attribute Ixz : Real = -0.04051163122632177;
                                attribute 'σ_Ixz' : Real = 0.022566176940390956;
                                attribute Iyz : Real = 0.024918638078416794;
                                attribute 'σ_Iyz' : Real = 0.02209918015384651;
                            }
                        }
                        part <'C.1.2.1.2.3.4'> 'Subassembly 227' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.3.4.1'> 'Part 800' {
                                attribute POIconv : String = "-";
                                attribute Ipoint : Boolean = false;
                                attribute mass : Real = 0.412517970159417;
                                attribute 'σ_mass' : Real = 0.28909372274994966;
                                attribute Cx : Real = 33.30162116326392;
                                attribute 'σ_Cx' : Real = 28.721044428837228;
                                attribute Cy : Real = -51.69420065358281;
                                attribute 'σ_Cy' : Real = 28.23690002309109;
                                attribute Cz : Real = 18.527037790045142;
                                attribute 'σ_Cz' : Real = 29.057750463592832;
                                attribute Ixx : Real = 0.39914024350096833;
                                attribute 'σ_Ixx' : Real = 0.37074144170588635;
                                attribute Iyy : Real = 0.4004222290436658;
                                attribute 'σ_Iyy' : Real = 0.3723953238821935;
                                attribute Izz : Real = 0.4117342307167128;
                                attribute 'σ_Izz' : Real = 0.37017423652493897;
                                attribute Ixy : Real = 0.016242073070566482;
                                attribute 'σ_Ixy' : Real = 0.02351283871158888;
                                attribute Ixz : Real = -0.00856392281014176;
                                attribute 'σ_Ixz' : Real = 0.022566176940390956;
                                attribute Iyz : Real = 0.008455876638044018;
                                attribute 'σ_Iyz' : Real = 0.02209918015384651;
                            }
                            part <'C.1.2.1.2.3.4.2'> 'Part 801' {
                                attribute POIconv : String = "-";
                                attribute Ipoint : Boolean = false;
                                attribute mass : Real = 0.8211163207006175;
                                attribute 'σ_mass' : Real = 0.28909372274994966;
                                attribute Cx : Real = -38.44122253358364;
                                attribute 'σ_Cx' : Real = 28.721044428837228;
                                attribute Cy : Real = 23.973912466317415;
                                attribute 'σ_Cy' : Real = 28.23690002309109;
                                attribute Cz : Real = -6.632704706862569;
                                attribute 'σ_Cz' : Real = 29.057750463592832;
                                attribute Ixx : Real = 1.0889735886199274;
                                attribute 'σ_Ixx' : Real = 0.37074144170588635;
                                attribute Iyy : Real = 1.075248296849076;
                                attribute 'σ_Iyy' : Real = 0.3723953238821935;
                                attribute Izz : Real = 1.0801764746287663;
                                attribute 'σ_Izz' : Real = 0.37017423652493897;
                                attribute Ixy : Real = -0.0027327348575962762;
                                attribute 'σ_Ixy' : Real = 0.02351283871158888;
                                attribute Ixz : Real = 0.00799863620921257;
                                attribute 'σ_Ixz' : Real = 0.022566176940390956;
                                attribute Iyz : Real = -0.0016216595719821237;
                                attribute 'σ_Iyz' : Real = 0.02209918015384651;
                            }
                            part <'C.1.2.1.2.3.4.3'> 'Part 802' {
                                attribute POIconv : String = "+";
                                attribute Ipoint : Boolean = false;
                                attribute mass : Real = 0.13423355266870932;
                                attribute 'σ_mass' : Real = 0.28909372274994966;
                                attribute Cx : Real = 88.8820132240653;
                                attribute 'σ_Cx' : Real = 28.721044428837228;
                                attribute Cy : Real = -57.840714836493134;
                                attribute 'σ_Cy' : Real = 28.23690002309109;
                                attribute Cz : Real = 54.37013851478696;
                                attribute 'σ_Cz' : Real = 29.057750463592832;
                                attribute Ixx : Real = 0.18268631099148483;
                                attribute 'σ_Ixx' : Real = 0.37074144170588635;
                                attribute Iyy : Real = 0.17522656286624175;
                                attribute 'σ_Iyy' : Real = 0.3723953238821935;
                                attribute Izz : Real = 0.18576274098727155;
                                attribute 'σ_Izz' : Real = 0.37017423652493897;
                                attribute Ixy : Real = 0.017604999117550334;
                                attribute 'σ_Ixy' : Real = 0.02351283871158888;
                                attribute Ixz : Real = -0.006578320417710843;
                                attribute 'σ_Ixz' : Real = 0.022566176940390956;
                                attribute Iyz : Real = -1.542702207145344e-4;
                                attribute 'σ_Iyz' : Real = 0.02209918015384651;
                            }
                            part <'C.1.2.1.2.3.4.4'> 'Part 803' {
                                attribute POIconv : String = "-";
                                attribute Ipoint : Boolean = false;
                                attribute mass : Real = 0.8582629183065146;
                                attribute 'σ_mass' : Real = 0.28909372274994966;
                                attribute Cx : Real = 85.00370723195374;
                                attribute 'σ_Cx' : Real = 28.721044428837228;
                                attribute Cy : Real = 58.3015123847872;
                                attribute 'σ_Cy' : Real = 28.23690002309109;
                                attribute Cz : Real = -96.42108110710979;
                                attribute 'σ_Cz' : Real = 29.057750463592832;
                                attribute Ixx : Real = 1.1485407594489083;
                                attribute 'σ_Ixx' : Real = 0.37074144170588635;
                                attribute Iyy : Real = 1.148576204634625;
                                attribute 'σ_Iyy' : Real = 0.3723953238821935;
                                attribute Izz : Real = 1.201531343942549;
                                attribute 'σ_Izz' : Real = 0.37017423652493897;
                                attribute Ixy : Real = -0.012600764820023994;
                                attribute 'σ_Ixy' : Real = 0.02351283871158888;
                                attribute Ixz : Real = -0.03880720970075034;
                                attribute 'σ_Ixz' : Real = 0.022566176940390956;
                                attribute Iyz : Real = 0.041898289418054985;
                                attribute 'σ_Iyz' : Real = 0.02209918015384651;
                            }
                        }
                    }
                    part <'C.1.2.1.2.4'> 'Assembly 66' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.2.4.1'> 'Subassembly 228' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.4.1.1'> 'Part 804' {
                                attribute POIconv : String = "-";
                                attribute Ipoint : Boolean = false;
                                attribute mass : Real = 0.8647730712809134;
                                attribute 'σ_mass' : Real = 0.28909372274994966;
                                attribute Cx : Real = -37.79769390821457;
                                attribute 'σ_Cx' : Real = 28.721044428837228;
                                attribute Cy : Real = 18.432783475145698;
                                attribute 'σ_Cy' : Real = 28.23690002309109;
                                attribute Cz : Real = 54.54795099794865;
                                attribute 'σ_Cz' : Real = 29.057750463592832;
                                attribute Ixx : Real = 1.0818066292808868;
                                attribute 'σ_Ixx' : Real = 0.37074144170588635;
                                attribute Iyy : Real = 1.2149066237522415;
                                attribute 'σ_Iyy' : Real = 0.3723953238821935;
                                attribute Izz : Real = 1.121349771579344;
                                attribute 'σ_Izz' : Real = 0.37017423652493897;
                                attribute Ixy : Real = -0.004667889009889363;
                                attribute 'σ_Ixy' : Real = 0.02351283871158888;
                                attribute Ixz : Real = 0.02446029180214645;
                                attribute 'σ_Ixz' : Real = 0.022566176940390956;
                                attribute Iyz : Real = -0.04858962275700097;
                                attribute 'σ_Iyz' : Real = 0.02209918015384651;
                            }
                            part <'C.1.2.1.2.4.1.2'> 'Part 805' {
                                attribute POIconv : String = "-";
                                attribute Ipoint : Boolean = false;
                                attribute mass : Real = 0.23963028427539393;
                                attribute 'σ_mass' : Real = 0.28909372274994966;
                                attribute Cx : Real = -75.16429228708148;
                                attribute 'σ_Cx' : Real = 28.721044428837228;
                                attribute Cy : Real = 16.32254645228386;
                                attribute 'σ_Cy' : Real = 28.23690002309109;
                                attribute Cz : Real = 20.508430479094386;
                                attribute 'σ_Cz' : Real = 29.057750463592832;
                                attribute Ixx : Real = 0.23867241040814213;
                                attribute 'σ_Ixx' : Real = 0.37074144170588635;
                                attribute Iyy : Real = 0.24458769615327913;
                                attribute 'σ_Iyy' : Real = 0.3723953238821935;
                                attribute Izz : Real = 0.256001055701629;
                                attribute 'σ_Izz' : Real = 0.37017423652493897;
                                attribute Ixy : Real = 0.006184236335142613;
                                attribute 'σ_Ixy' : Real = 0.02351283871158888;
                                attribute Ixz : Real = -0.0021676407206270626;
                                attribute 'σ_Ixz' : Real = 0.022566176940390956;
                                attribute Iyz : Real = 0.0012573111645372299;
                                attribute 'σ_Iyz' : Real = 0.02209918015384651;
                            }
                            part <'C.1.2.1.2.4.1.3'> 'Part 806' {
                                attribute POIconv : String = "+";
                                attribute Ipoint : Boolean = false;
                                attribute mass : Real = 0.3267420998723246;
                                attribute 'σ_mass' : Real = 0.28909372274994966;
                                attribute Cx : Real = -8.890654006972909;
                                attribute 'σ_Cx' : Real = 28.721044428837228;
                                attribute Cy : Real = -72.87516864016652;
                                attribute 'σ_Cy' : Real = 28.23690002309109;
                                attribute Cz : Real = -38.81826470606029;
                                attribute 'σ_Cz' : Real = 29.057750463592832;
                                attribute Ixx : Real = 0.49996237008511313;
                                attribute 'σ_Ixx' : Real = 0.37074144170588635;
                                attribute Iyy : Real = 0.5173728381077084;
                                attribute 'σ_Iyy' : Real = 0.3723953238821935;
                                attribute Izz : Real = 0.4843805826064876;
                                attribute 'σ_Izz' : Real = 0.37017423652493897;
                                attribute Ixy : Real = 0.012501945870505272;
                                attribute 'σ_Ixy' : Real = 0.02351283871158888;
                                attribute Ixz : Real = 8.661031078263801e-4;
                                attribute 'σ_Ixz' : Real = 0.022566176940390956;
                                attribute Iyz : Real = -0.0019662385902962194;
                                attribute 'σ_Iyz' : Real = 0.02209918015384651;
                            }
                            part <'C.1.2.1.2.4.1.4'> 'Part 807' {
                                attribute POIconv : String = "+";
                                attribute Ipoint : Boolean = false;
                                attribute mass : Real = 0.7272897051302716;
                                attribute 'σ_mass' : Real = 0.28909372274994966;
                                attribute Cx : Real = -68.14796905964613;
                                attribute 'σ_Cx' : Real = 28.721044428837228;
                                attribute Cy : Real = 76.05666127055883;
                                attribute 'σ_Cy' : Real = 28.23690002309109;
                                attribute Cz : Real = -6.900419574230909;
                                attribute 'σ_Cz' : Real = 29.057750463592832;
                                attribute Ixx : Real = 0.9791768215990834;
                                attribute 'σ_Ixx' : Real = 0.37074144170588635;
                                attribute Iyy : Real = 0.8860704797712587;
                                attribute 'σ_Iyy' : Real = 0.3723953238821935;
                                attribute Izz : Real = 0.9374630954174443;
                                attribute 'σ_Izz' : Real = 0.37017423652493897;
                                attribute Ixy : Real = -0.0013869810325858574;
                                attribute 'σ_Ixy' : Real = 0.02351283871158888;
                                attribute Ixz : Real = -0.09247330388404815;
                                attribute 'σ_Ixz' : Real = 0.022566176940390956;
                                attribute Iyz : Real = 0.03117674101409234;
                                attribute 'σ_Iyz' : Real = 0.02209918015384651;
                            }
                            part <'C.1.2.1.2.4.1.5'> 'Part 808' {
                                attribute POIconv : String = "-";
                                attribute Ipoint : Boolean = false;
                                attribute mass : Real = 0.5658271773017477;
                                attribute 'σ_mass' : Real = 0.28909372274994966;
                                attribute Cx : Real = -83.25843545608222;
                                attribute 'σ_Cx' : Real = 28.721044428837228;
                                attribute Cy : Real = 76.97888850234449;
                                attribute 'σ_Cy' : Real = 28.23690002309109;
                                attribute Cz : Real = -78.31415301188827;
                                attribute 'σ_Cz' : Real = 29.057750463592832;
                                attribute Ixx : Real = 0.662750235422354;
                                attribute 'σ_Ixx' : Real = 0.37074144170588635;
                                attribute Iyy : Real = 0.6280813471229602;
                                attribute 'σ_Iyy' : Real = 0.3723953238821935;
                                attribute Izz : Real = 0.5957829620488266;
                                attribute 'σ_Izz' : Real = 0.37017423652493897;
                                attribute Ixy : Real = 0.048334660757939886;
                                attribute 'σ_Ixy' : Real = 0.02351283871158888;
                                attribute Ixz : Real = 0.05409607205209871;
                                attribute 'σ_Ixz' : Real = 0.022566176940390956;
                                attribute Iyz : Real = -0.08089780142635626;
                                attribute 'σ_Iyz' : Real = 0.02209918015384651;
                            }
                        }
                        part <'C.1.2.1.2.4.2'> 'Subassembly 229' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.4.2.1'> 'Part 809' {
                                attribute POIconv : String = "+";
                                attribute Ipoint : Boolean = false;
                                attribute mass : Real = 0.7216553364193533;
                                attribute 'σ_mass' : Real = 0.28909372274994966;
                                attribute Cx : Real = 44.51233926229179;
                                attribute 'σ_Cx' : Real = 28.721044428837228;
                                attribute Cy : Real = -8.224520226940513;
                                attribute 'σ_Cy' : Real = 28.23690002309109;
                                attribute Cz : Real = -35.627303225919604;
                                attribute 'σ_Cz' : Real = 29.057750463592832;
                                attribute Ixx : Real = 0.666792743125651;
                                attribute 'σ_Ixx' : Real = 0.37074144170588635;
                                attribute Iyy : Real = 0.6557724275868243;
                                attribute 'σ_Iyy' : Real = 0.3723953238821935;
                                attribute Izz : Real = 0.6726569936945448;
                                attribute 'σ_Izz' : Real = 0.37017423652493897;
                                attribute Ixy : Real = -4.3038234080768e-4;
                                attribute 'σ_Ixy' : Real = 0.02351283871158888;
                                attribute Ixz : Real = 0.004284782359878392;
                                attribute 'σ_Ixz' : Real = 0.022566176940390956;
                                attribute Iyz : Real = 0.0020786959521412766;
                                attribute 'σ_Iyz' : Real = 0.02209918015384651;
                            }
                            part <'C.1.2.1.2.4.2.2'> 'Part 810' {
                                attribute POIconv : String = "+";
                                attribute Ipoint : Boolean = false;
                                attribute mass : Real = 0.01931958820275031;
                                attribute 'σ_mass' : Real = 0.28909372274994966;
                                attribute Cx : Real = 52.15042610652745;
                                attribute 'σ_Cx' : Real = 28.721044428837228;
                                attribute Cy : Real = 5.777149787172675;
                                attribute 'σ_Cy' : Real = 28.23690002309109;
                                attribute Cz : Real = -77.41399575024843;
                                attribute 'σ_Cz' : Real = 29.057750463592832;
                                attribute Ixx : Real = 0.017896556317728483;
                                attribute 'σ_Ixx' : Real = 0.37074144170588635;
                                attribute Iyy : Real = 0.01988321596731473;
                                attribute 'σ_Iyy' : Real = 0.3723953238821935;
                                attribute Izz : Real = 0.01947780938952731;
                                attribute 'σ_Izz' : Real = 0.37017423652493897;
                                attribute Ixy : Real = 7.51949920685642e-4;
                                attribute 'σ_Ixy' : Real = 0.02351283871158888;
                                attribute Ixz : Real = 4.743783020453926e-4;
                                attribute 'σ_Ixz' : Real = 0.022566176940390956;
                                attribute Iyz : Real = -2.603821331912986e-4;
                                attribute 'σ_Iyz' : Real = 0.02209918015384651;
                            }
                            part <'C.1.2.1.2.4.2.3'> 'Part 811' {
                                attribute POIconv : String = "-";
                                attribute Ipoint : Boolean = false;
                                attribute mass : Real = 0.2918663719270844;
                                attribute 'σ_mass' : Real = 0.28909372274994966;
                                attribute Cx : Real = -22.43285053409636;
                                attribute 'σ_Cx' : Real = 28.721044428837228;
                                attribute Cy : Real = -0.4365658853203058;
                                attribute 'σ_Cy' : Real = 28.23690002309109;
                                attribute Cz : Real = -49.58274313248694;
                                attribute 'σ_Cz' : Real = 29.057750463592832;
                                attribute Ixx : Real = 0.3453957261489187;
                                attribute 'σ_Ixx' : Real = 0.37074144170588635;
                                attribute Iyy : Real = 0.4168891183516289;
                                attribute 'σ_Iyy' : Real = 0.3723953238821935;
                                attribute Izz : Real = 0.35299767673283033;
                                attribute 'σ_Izz' : Real = 0.37017423652493897;
                                attribute Ixy : Real = 0.022476549351943383;
                                attribute 'σ_Ixy' : Real = 0.02351283871158888;
                                attribute Ixz : Real = 0.0017258267198888917;
                                attribute 'σ_Ixz' : Real = 0.022566176940390956;
                                attribute Iyz : Real = 0.02189942386670761;
                                attribute 'σ_Iyz' : Real = 0.02209918015384651;
                            }
                            part <'C.1.2.1.2.4.2.4'> 'Part 812' {
                                attribute POIconv : String = "-";
                                attribute Ipoint : Boolean = false;
                                attribute mass : Real = 0.19939040533732624;
                                attribute 'σ_mass' : Real = 0.28909372274994966;
                                attribute Cx : Real = -56.36100363917649;
                                attribute 'σ_Cx' : Real = 28.721044428837228;
                                attribute Cy : Real = -23.49372375756502;
                                attribute 'σ_Cy' : Real = 28.23690002309109;
                                attribute Cz : Real = -59.79600944556296;
                                attribute 'σ_Cz' : Real = 29.057750463592832;
                                attribute Ixx : Real = 0.19048126678535066;
                                attribute 'σ_Ixx' : Real = 0.37074144170588635;
                                attribute Iyy : Real = 0.21806339046888587;
                                attribute 'σ_Iyy' : Real = 0.3723953238821935;
                                attribute Izz : Real = 0.22083404888702535;
                                attribute 'σ_Izz' : Real = 0.37017423652493897;
                                attribute Ixy : Real = -0.007184577928820353;
                                attribute 'σ_Ixy' : Real = 0.02351283871158888;
                                attribute Ixz : Real = -0.011433031338499766;
                                attribute 'σ_Ixz' : Real = 0.022566176940390956;
                                attribute Iyz : Real = 3.2399330677648796e-4;
                                attribute 'σ_Iyz' : Real = 0.02209918015384651;
                            }
                        }
                        part <'C.1.2.1.2.4.3'> 'Subassembly 230' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.4.3.1'> 'Part 813' {
                                attribute POIconv : String = "+";
                                attribute Ipoint : Boolean = false;
                                attribute mass : Real = 0.8357904310591985;
                                attribute 'σ_mass' : Real = 0.28909372274994966;
                                attribute Cx : Real = 32.309469394385815;
                                attribute 'σ_Cx' : Real = 28.721044428837228;
                                attribute Cy : Real = -65.08840187452734;
                                attribute 'σ_Cy' : Real = 28.23690002309109;
                                attribute Cz : Real = 37.25717789493501;
                                attribute 'σ_Cz' : Real = 29.057750463592832;
                                attribute Ixx : Real = 0.9874327269102298;
                                attribute 'σ_Ixx' : Real = 0.37074144170588635;
                                attribute Iyy : Real = 1.0731532789619918;
                                attribute 'σ_Iyy' : Real = 0.3723953238821935;
                                attribute Izz : Real = 1.1380284466214423;
                                attribute 'σ_Izz' : Real = 0.37017423652493897;
                                attribute Ixy : Real = -0.046133088263470054;
                                attribute 'σ_Ixy' : Real = 0.02351283871158888;
                                attribute Ixz : Real = 0.07240316233168473;
                                attribute 'σ_Ixz' : Real = 0.022566176940390956;
                                attribute Iyz : Real = 0.09490695105118563;
                                attribute 'σ_Iyz' : Real = 0.02209918015384651;
                            }
                            part <'C.1.2.1.2.4.3.2'> 'Part 814' {
                                attribute POIconv : String = "+";
                                attribute Ipoint : Boolean = false;
                                attribute mass : Real = 0.5276788520901464;
                                attribute 'σ_mass' : Real = 0.28909372274994966;
                                attribute Cx : Real = 60.75677811168134;
                                attribute 'σ_Cx' : Real = 28.721044428837228;
                                attribute Cy : Real = -93.28174190595746;
                                attribute 'σ_Cy' : Real = 28.23690002309109;
                                attribute Cz : Real = -31.71930005773902;
                                attribute 'σ_Cz' : Real = 29.057750463592832;
                                attribute Ixx : Real = 0.6752545313641664;
                                attribute 'σ_Ixx' : Real = 0.37074144170588635;
                                attribute Iyy : Real = 0.6110967434861267;
                                attribute 'σ_Iyy' : Real = 0.3723953238821935;
                                attribute Izz : Real = 0.6282835263497757;
                                attribute 'σ_Izz' : Real = 0.37017423652493897;
                                attribute Ixy : Real = -0.06003160079778154;
                                attribute 'σ_Ixy' : Real = 0.02351283871158888;
                                attribute Ixz : Real = -0.005637790823054593;
                                attribute 'σ_Ixz' : Real = 0.022566176940390956;
                                attribute Iyz : Real = 0.05150892182210934;
                                attribute 'σ_Iyz' : Real = 0.02209918015384651;
                            }
                            part <'C.1.2.1.2.4.3.3'> 'Part 815' {
                                attribute POIconv : String = "-";
                                attribute Ipoint : Boolean = false;
                                attribute mass : Real = 0.2866579179561231;
                                attribute 'σ_mass' : Real = 0.28909372274994966;
                                attribute Cx : Real = 10.567488567903638;
                                attribute 'σ_Cx' : Real = 28.721044428837228;
                                attribute Cy : Real = -55.383821576833725;
                                attribute 'σ_Cy' : Real = 28.23690002309109;
                                attribute Cz : Real = -90.33429166302085;
                                attribute 'σ_Cz' : Real = 29.057750463592832;
                                attribute Ixx : Real = 0.2828717220816637;
                                attribute 'σ_Ixx' : Real = 0.37074144170588635;
                                attribute Iyy : Real = 0.2635401302214018;
                                attribute 'σ_Iyy' : Real = 0.3723953238821935;
                                attribute Izz : Real = 0.29447554542632004;
                                attribute 'σ_Izz' : Real = 0.37017423652493897;
                                attribute Ixy : Real = -0.005990270880614783;
                                attribute 'σ_Ixy' : Real = 0.02351283871158888;
                                attribute Ixz : Real = -0.007200619651265321;
                                attribute 'σ_Ixz' : Real = 0.022566176940390956;
                                attribute Iyz : Real = -0.006458395974597997;
                                attribute 'σ_Iyz' : Real = 0.02209918015384651;
                            }
                            part <'C.1.2.1.2.4.3.4'> 'Part 816' {
                                attribute POIconv : String = "+";
                                attribute Ipoint : Boolean = false;
                                attribute mass : Real = 0.8911068134093657;
                                attribute 'σ_mass' : Real = 0.28909372274994966;
                                attribute Cx : Real = -39.10878994502127;
                                attribute 'σ_Cx' : Real = 28.721044428837228;
                                attribute Cy : Real = -32.458433182910085;
                                attribute 'σ_Cy' : Real = 28.23690002309109;
                                attribute Cz : Real = 42.827041214331985;
                                attribute 'σ_Cz' : Real = 29.057750463592832;
                                attribute Ixx : Real = 1.100414917126418;
                                attribute 'σ_Ixx' : Real = 0.37074144170588635;
                                attribute Iyy : Real = 1.2747139134981942;
                                attribute 'σ_Iyy' : Real = 0.3723953238821935;
                                attribute Izz : Real = 1.0349239848879837;
                                attribute 'σ_Izz' : Real = 0.37017423652493897;
                                attribute Ixy : Real = -0.03431938115177424;
                                attribute 'σ_Ixy' : Real = 0.02351283871158888;
                                attribute Ixz : Real = -0.0012769543540904595;
                                attribute 'σ_Ixz' : Real = 0.022566176940390956;
                                attribute Iyz : Real = -0.03302775050662109;
                                attribute 'σ_Iyz' : Real = 0.02209918015384651;
                            }
                            part <'C.1.2.1.2.4.3.5'> 'Part 817' {
                                attribute POIconv : String = "-";
                                attribute Ipoint : Boolean = false;
                                attribute mass : Real = 0.5669845616898965;
                                attribute 'σ_mass' : Real = 0.28909372274994966;
                                attribute Cx : Real = -7.781800953671336;
                                attribute 'σ_Cx' : Real = 28.721044428837228;
                                attribute Cy : Real = -60.454552387818694;
                                attribute 'σ_Cy' : Real = 28.23690002309109;
                                attribute Cz : Real = -68.42243811115623;
                                attribute 'σ_Cz' : Real = 29.057750463592832;
                                attribute Ixx : Real = 0.7587028294971988;
                                attribute 'σ_Ixx' : Real = 0.37074144170588635;
                                attribute Iyy : Real = 0.7384174111092835;
                                attribute 'σ_Iyy' : Real = 0.3723953238821935;
                                attribute Izz : Real = 0.7963515283495621;
                                attribute 'σ_Izz' : Real = 0.37017423652493897;
                                attribute Ixy : Real = -0.016928491794814732;
                                attribute 'σ_Ixy' : Real = 0.02351283871158888;
                                attribute Ixz : Real = 0.014297663231862084;
                                attribute 'σ_Ixz' : Real = 0.022566176940390956;
                                attribute Iyz : Real = -0.03456291632365647;
                                attribute 'σ_Iyz' : Real = 0.02209918015384651;
                            }
                        }
                        part <'C.1.2.1.2.4.4'> 'Subassembly 231' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.4.4.1'> 'Part 818' {
                                attribute POIconv : String = "-";
                                attribute Ipoint : Boolean = false;
                                attribute mass : Real = 0.02775987434736453;
                                attribute 'σ_mass' : Real = 0.28909372274994966;
                                attribute Cx : Real = -19.107882492244244;
                                attribute 'σ_Cx' : Real = 28.721044428837228;
                                attribute Cy : Real = 81.39040870591998;
                                attribute 'σ_Cy' : Real = 28.23690002309109;
                                attribute Cz : Real = 59.768469678238034;
                                attribute 'σ_Cz' : Real = 29.057750463592832;
                                attribute Ixx : Real = 0.03352117541400993;
                                attribute 'σ_Ixx' : Real = 0.37074144170588635;
                                attribute Iyy : Real = 0.0300113556906247;
                                attribute 'σ_Iyy' : Real = 0.3723953238821935;
                                attribute Izz : Real = 0.03371325362756814;
                                attribute 'σ_Izz' : Real = 0.37017423652493897;
                                attribute Ixy : Real = 5.84289461273048e-4;
                                attribute 'σ_Ixy' : Real = 0.02351283871158888;
                                attribute Ixz : Real = 1.557363225420622e-5;
                                attribute 'σ_Ixz' : Real = 0.022566176940390956;
                                attribute Iyz : Real = 1.3984997185589767e-4;
                                attribute 'σ_Iyz' : Real = 0.02209918015384651;
                            }
                            part <'C.1.2.1.2.4.4.2'> 'Part 819' {
                                attribute POIconv : String = "-";
                                attribute Ipoint : Boolean = false;
                                attribute mass : Real = 0.9975247924628202;
                                attribute 'σ_mass' : Real = 0.28909372274994966;
                                attribute Cx : Real = -58.52100886404514;
                                attribute 'σ_Cx' : Real = 28.721044428837228;
                                attribute Cy : Real = -26.248004660010338;
                                attribute 'σ_Cy' : Real = 28.23690002309109;
                                attribute Cz : Real = -96.36492184363306;
                                attribute 'σ_Cz' : Real = 29.057750463592832;
                                attribute Ixx : Real = 1.050472921541383;
                                attribute 'σ_Ixx' : Real = 0.37074144170588635;
                                attribute Iyy : Real = 1.050829997993463;
                                attribute 'σ_Iyy' : Real = 0.3723953238821935;
                                attribute Izz : Real = 1.1079224008382247;
                                attribute 'σ_Izz' : Real = 0.37017423652493897;
                                attribute Ixy : Real = 0.08026193042551114;
                                attribute 'σ_Ixy' : Real = 0.02351283871158888;
                                attribute Ixz : Real = -0.006639878179441545;
                                attribute 'σ_Ixz' : Real = 0.022566176940390956;
                                attribute Iyz : Real = 0.009955918427628926;
                                attribute 'σ_Iyz' : Real = 0.02209918015384651;
                            }
                            part <'C.1.2.1.2.4.4.3'> 'Part 820' {
                                attribute POIconv : String = "-";
                                attribute Ipoint : Boolean = false;
                                attribute mass : Real = 0.7841411937372759;
                                attribute 'σ_mass' : Real = 0.28909372274994966;
                                attribute Cx : Real = -60.44355579651892;
                                attribute 'σ_Cx' : Real = 28.721044428837228;
                                attribute Cy : Real = 42.51666353084147;
                                attribute 'σ_Cy' : Real = 28.23690002309109;
                                attribute Cz : Real = 51.213312428444624;
                                attribute 'σ_Cz' : Real = 29.057750463592832;
                                attribute Ixx : Real = 0.8011600518152019;
                                attribute 'σ_Ixx' : Real = 0.37074144170588635;
                                attribute Iyy : Real = 0.7446147060284282;
                                attribute 'σ_Iyy' : Real = 0.3723953238821935;
                                attribute Izz : Real = 0.8025036987373738;
                                attribute 'σ_Izz' : Real = 0.37017423652493897;
                                attribute Ixy : Real = 0.024794181776634387;
                                attribute 'σ_Ixy' : Real = 0.02351283871158888;
                                attribute Ixz : Real = -0.007208786809275782;
                                attribute 'σ_Ixz' : Real = 0.022566176940390956;
                                attribute Iyz : Real = 0.01855066335371411;
                                attribute 'σ_Iyz' : Real = 0.02209918015384651;
                            }
                            part <'C.1.2.1.2.4.4.4'> 'Part 821' {
                                attribute POIconv : String = "+";
                                attribute Ipoint : Boolean = false;
                                attribute mass : Real = 0.0707622840164695;
                                attribute 'σ_mass' : Real = 0.28909372274994966;
                                attribute Cx : Real = 48.25788256712258;
                                attribute 'σ_Cx' : Real = 28.721044428837228;
                                attribute Cy : Real = -39.542839117348194;
                                attribute 'σ_Cy' : Real = 28.23690002309109;
                                attribute Cz : Real = 7.862336887046695;
                                attribute 'σ_Cz' : Real = 29.057750463592832;
                                attribute Ixx : Real = 0.08701404964993782;
                                attribute 'σ_Ixx' : Real = 0.37074144170588635;
                                attribute Iyy : Real = 0.0881479928677735;
                                attribute 'σ_Iyy' : Real = 0.3723953238821935;
                                attribute Izz : Real = 0.0938627547885274;
                                attribute 'σ_Izz' : Real = 0.37017423652493897;
                                attribute Ixy : Real = -0.00366943115564693;
                                attribute 'σ_Ixy' : Real = 0.02351283871158888;
                                attribute Ixz : Real = 0.004602252210396301;
                                attribute 'σ_Ixz' : Real = 0.022566176940390956;
                                attribute Iyz : Real = 0.010378993873078925;
                                attribute 'σ_Iyz' : Real = 0.02209918015384651;
                            }
                        }
                        part <'C.1.2.1.2.4.5'> 'Subassembly 232' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.4.5.1'> 'Part 822' {
                                attribute POIconv : String = "+";
                                attribute Ipoint : Boolean = false;
                                attribute mass : Real = 0.4072078144229017;
                                attribute 'σ_mass' : Real = 0.28909372274994966;
                                attribute Cx : Real = 92.35317665152252;
                                attribute 'σ_Cx' : Real = 28.721044428837228;
                                attribute Cy : Real = -64.68316460959613;
                                attribute 'σ_Cy' : Real = 28.23690002309109;
                                attribute Cz : Real = -19.350315490737557;
                                attribute 'σ_Cz' : Real = 29.057750463592832;
                                attribute Ixx : Real = 0.5885837720038378;
                                attribute 'σ_Ixx' : Real = 0.37074144170588635;
                                attribute Iyy : Real = 0.5697786219384158;
                                attribute 'σ_Iyy' : Real = 0.3723953238821935;
                                attribute Izz : Real = 0.5984418258242137;
                                attribute 'σ_Izz' : Real = 0.37017423652493897;
                                attribute Ixy : Real = -0.017945362807275135;
                                attribute 'σ_Ixy' : Real = 0.02351283871158888;
                                attribute Ixz : Real = -0.0010926556153732828;
                                attribute 'σ_Ixz' : Real = 0.022566176940390956;
                                attribute Iyz : Real = 0.0026388096326256747;
                                attribute 'σ_Iyz' : Real = 0.02209918015384651;
                            }
                            part <'C.1.2.1.2.4.5.2'> 'Part 823' {
                                attribute POIconv : String = "+";
                                attribute Ipoint : Boolean = false;
                                attribute mass : Real = 0.9981345199504867;
                                attribute 'σ_mass' : Real = 0.28909372274994966;
                                attribute Cx : Real = 45.81385510973632;
                                attribute 'σ_Cx' : Real = 28.721044428837228;
                                attribute Cy : Real = 80.57540208101273;
                                attribute 'σ_Cy' : Real = 28.23690002309109;
                                attribute Cz : Real = 13.06322286836803;
                                attribute 'σ_Cz' : Real = 29.057750463592832;
                                attribute Ixx : Real = 1.192093828866941;
                                attribute 'σ_Ixx' : Real = 0.37074144170588635;
                                attribute Iyy : Real = 1.3392310748014664;
                                attribute 'σ_Iyy' : Real = 0.3723953238821935;
                                attribute Izz : Real = 1.2369976623306118;
                                attribute 'σ_Izz' : Real = 0.37017423652493897;
                                attribute Ixy : Real = -0.07465667576540179;
                                attribute 'σ_Ixy' : Real = 0.02351283871158888;
                                attribute Ixz : Real = 0.10022896612910404;
                                attribute 'σ_Ixz' : Real = 0.022566176940390956;
                                attribute Iyz : Real = 0.08967724443355796;
                                attribute 'σ_Iyz' : Real = 0.02209918015384651;
                            }
                            part <'C.1.2.1.2.4.5.3'> 'Part 824' {
                                attribute POIconv : String = "-";
                                attribute Ipoint : Boolean = false;
                                attribute mass : Real = 0.10764958786056376;
                                attribute 'σ_mass' : Real = 0.28909372274994966;
                                attribute Cx : Real = -42.19682705588639;
                                attribute 'σ_Cx' : Real = 28.721044428837228;
                                attribute Cy : Real = -56.996966851875186;
                                attribute 'σ_Cy' : Real = 28.23690002309109;
                                attribute Cz : Real = -30.298014730215073;
                                attribute 'σ_Cz' : Real = 29.057750463592832;
                                attribute Ixx : Real = 0.1513570280368388;
                                attribute 'σ_Ixx' : Real = 0.37074144170588635;
                                attribute Iyy : Real = 0.15423437224017236;
                                attribute 'σ_Iyy' : Real = 0.3723953238821935;
                                attribute Izz : Real = 0.148468888734851;
                                attribute 'σ_Izz' : Real = 0.37017423652493897;
                                attribute Ixy : Real = 0.010718228458854992;
                                attribute 'σ_Ixy' : Real = 0.02351283871158888;
                                attribute Ixz : Real = -0.007946938892291297;
                                attribute 'σ_Ixz' : Real = 0.022566176940390956;
                                attribute Iyz : Real = -0.009001581295385176;
                                attribute 'σ_Iyz' : Real = 0.02209918015384651;
                            }
                            part <'C.1.2.1.2.4.5.4'> 'Part 825' {
                                attribute POIconv : String = "-";
                                attribute Ipoint : Boolean = false;
                                attribute mass : Real = 0.920315902720904;
                                attribute 'σ_mass' : Real = 0.28909372274994966;
                                attribute Cx : Real = -54.29401402361691;
                                attribute 'σ_Cx' : Real = 28.721044428837228;
                                attribute Cy : Real = -64.4571793731302;
                                attribute 'σ_Cy' : Real = 28.23690002309109;
                                attribute Cz : Real = -91.76239422522485;
                                attribute 'σ_Cz' : Real = 29.057750463592832;
                                attribute Ixx : Real = 1.2570674329021974;
                                attribute 'σ_Ixx' : Real = 0.37074144170588635;
                                attribute Iyy : Real = 1.3000220753039593;
                                attribute 'σ_Iyy' : Real = 0.3723953238821935;
                                attribute Izz : Real = 1.4227641175875914;
                                attribute 'σ_Izz' : Real = 0.37017423652493897;
                                attribute Ixy : Real = -0.01764992457399503;
                                attribute 'σ_Ixy' : Real = 0.02351283871158888;
                                attribute Ixz : Real = -0.06822718357408744;
                                attribute 'σ_Ixz' : Real = 0.022566176940390956;
                                attribute Iyz : Real = 0.0788622042842433;
                                attribute 'σ_Iyz' : Real = 0.02209918015384651;
                            }
                        }
                    }
                    part <'C.1.2.1.2.5'> 'Assembly 67' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.2.5.1'> 'Subassembly 233' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.5.1.1'> 'Part 826' {
                                attribute POIconv : String = "-";
                                attribute Ipoint : Boolean = false;
                                attribute mass : Real = 0.35472945754113605;
                                attribute 'σ_mass' : Real = 0.28909372274994966;
                                attribute Cx : Real = -32.57354265078902;
                                attribute 'σ_Cx' : Real = 28.721044428837228;
                                attribute Cy : Real = -54.359632916748524;
                                attribute 'σ_Cy' : Real = 28.23690002309109;
                                attribute Cz : Real = -60.033038118854165;
                                attribute 'σ_Cz' : Real = 29.057750463592832;
                                attribute Ixx : Real = 0.39465533938161407;
                                attribute 'σ_Ixx' : Real = 0.37074144170588635;
                                attribute Iyy : Real = 0.3708428361104746;
                                attribute 'σ_Iyy' : Real = 0.3723953238821935;
                                attribute Izz : Real = 0.4016438495341792;
                                attribute 'σ_Izz' : Real = 0.37017423652493897;
                                attribute Ixy : Real = -0.00901885303641029;
                                attribute 'σ_Ixy' : Real = 0.02351283871158888;
                                attribute Ixz : Real = -0.008405056752999634;
                                attribute 'σ_Ixz' : Real = 0.022566176940390956;
                                attribute Iyz : Real = -0.039442214739952464;
                                attribute 'σ_Iyz' : Real = 0.02209918015384651;
                            }
                            part <'C.1.2.1.2.5.1.2'> 'Part 827' {
                                attribute POIconv : String = "+";
                                attribute Ipoint : Boolean = false;
                                attribute mass : Real = 0.31314228507853115;
                                attribute 'σ_mass' : Real = 0.28909372274994966;
                                attribute Cx : Real = 73.49771121516824;
                                attribute 'σ_Cx' : Real = 28.721044428837228;
                                attribute Cy : Real = -14.560205908492208;
                                attribute 'σ_Cy' : Real = 28.23690002309109;
                                attribute Cz : Real = -57.27238794788718;
                                attribute 'σ_Cz' : Real = 29.057750463592832;
                                attribute Ixx : Real = 0.3536357841739443;
                                attribute 'σ_Ixx' : Real = 0.37074144170588635;
                                attribute Iyy : Real = 0.38870651252086724;
                                attribute 'σ_Iyy' : Real = 0.3723953238821935;
                                attribute Izz : Real = 0.3836471681829062;
                                attribute 'σ_Izz' : Real = 0.37017423652493897;
                                attribute Ixy : Real = -0.003130433380554972;
                                attribute 'σ_Ixy' : Real = 0.02351283871158888;
                                attribute Ixz : Real = 0.001020412698138922;
                                attribute 'σ_Ixz' : Real = 0.022566176940390956;
                                attribute Iyz : Real = 0.029871025344772557;
                                attribute 'σ_Iyz' : Real = 0.02209918015384651;
                            }
                            part <'C.1.2.1.2.5.1.3'> 'Part 828' {
                                attribute POIconv : String = "+";
                                attribute Ipoint : Boolean = false;
                                attribute mass : Real = 0.7795113956751302;
                                attribute 'σ_mass' : Real = 0.28909372274994966;
                                attribute Cx : Real = -88.55164228007197;
                                attribute 'σ_Cx' : Real = 28.721044428837228;
                                attribute Cy : Real = -95.1529074460268;
                                attribute 'σ_Cy' : Real = 28.23690002309109;
                                attribute Cz : Real = -29.581688018515706;
                                attribute 'σ_Cz' : Real = 29.057750463592832;
                                attribute Ixx : Real = 1.1342216883989427;
                                attribute 'σ_Ixx' : Real = 0.37074144170588635;
                                attribute Iyy : Real = 1.0789138109344536;
                                attribute 'σ_Iyy' : Real = 0.3723953238821935;
                                attribute Izz : Real = 1.1353333188813315;
                                attribute 'σ_Izz' : Real = 0.37017423652493897;
                                attribute Ixy : Real = -0.02123559450439876;
                                attribute 'σ_Ixy' : Real = 0.02351283871158888;
                                attribute Ixz : Real = -0.003284069208180234;
                                attribute 'σ_Ixz' : Real = 0.022566176940390956;
                                attribute Iyz : Real = -0.02408775241072387;
                                attribute 'σ_Iyz' : Real = 0.02209918015384651;
                            }
                            part <'C.1.2.1.2.5.1.4'> 'Part 829' {
                                attribute POIconv : String = "+";
                                attribute Ipoint : Boolean = false;
                                attribute mass : Real = 0.20580471056792884;
                                attribute 'σ_mass' : Real = 0.28909372274994966;
                                attribute Cx : Real = -68.28695512376726;
                                attribute 'σ_Cx' : Real = 28.721044428837228;
                                attribute Cy : Real = -73.13819658011198;
                                attribute 'σ_Cy' : Real = 28.23690002309109;
                                attribute Cz : Real = -43.99308650754392;
                                attribute 'σ_Cz' : Real = 29.057750463592832;
                                attribute Ixx : Real = 0.27761592021355075;
                                attribute 'σ_Ixx' : Real = 0.37074144170588635;
                                attribute Iyy : Real = 0.29510629942027644;
                                attribute 'σ_Iyy' : Real = 0.3723953238821935;
                                attribute Izz : Real = 0.24858597897777807;
                                attribute 'σ_Izz' : Real = 0.37017423652493897;
                                attribute Ixy : Real = -0.013734226100615247;
                                attribute 'σ_Ixy' : Real = 0.02351283871158888;
                                attribute Ixz : Real = -0.0029774467758205787;
                                attribute 'σ_Ixz' : Real = 0.022566176940390956;
                                attribute Iyz : Real = -0.004131084819970121;
                                attribute 'σ_Iyz' : Real = 0.02209918015384651;
                            }
                            part <'C.1.2.1.2.5.1.5'> 'Part 830' {
                                attribute POIconv : String = "-";
                                attribute Ipoint : Boolean = false;
                                attribute mass : Real = 0.6863058004488702;
                                attribute 'σ_mass' : Real = 0.28909372274994966;
                                attribute Cx : Real = -50.50122821703553;
                                attribute 'σ_Cx' : Real = 28.721044428837228;
                                attribute Cy : Real = -9.431499196216464;
                                attribute 'σ_Cy' : Real = 28.23690002309109;
                                attribute Cz : Real = 58.41679130680859;
                                attribute 'σ_Cz' : Real = 29.057750463592832;
                                attribute Ixx : Real = 0.8655261883665156;
                                attribute 'σ_Ixx' : Real = 0.37074144170588635;
                                attribute Iyy : Real = 0.8530180555528631;
                                attribute 'σ_Iyy' : Real = 0.3723953238821935;
                                attribute Izz : Real = 0.8814957000538955;
                                attribute 'σ_Izz' : Real = 0.37017423652493897;
                                attribute Ixy : Real = 0.026716929532031388;
                                attribute 'σ_Ixy' : Real = 0.02351283871158888;
                                attribute Ixz : Real = -0.009397924121129757;
                                attribute 'σ_Ixz' : Real = 0.022566176940390956;
                                attribute Iyz : Real = 0.010086649848528272;
                                attribute 'σ_Iyz' : Real = 0.02209918015384651;
                            }
                        }
                        part <'C.1.2.1.2.5.2'> 'Subassembly 234' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.2.5.2.1'> 'Part 831' {
                                attribute POIconv : String = "-";
                                attribute Ipoint : Boolean = false;
                                attribute mass : Real = 0.5344961925768293;
                                attribute 'σ_mass' : Real = 0.28909372274994966;
                                attribute Cx : Real = 31.313461251556873;
                                attribute 'σ_Cx' : Real = 28.721044428837228;
                                attribute Cy : Real = -69.91904112510383;
                                attribute 'σ_Cy' : Real = 28.23690002309109;
                                attribute Cz : Real = -96.5362448245287;
                                attribute 'σ_Cz' : Real = 29.057750463592832;
                                attribute Ixx : Real = 0.5897612726838234;
                                attribute 'σ_Ixx' : Real = 0.37074144170588635;
                                attribute Iyy : Real = 0.5753336902253086;
                                attribute 'σ_Iyy' : Real = 0.3723953238821935;
                                attribute Izz : Real = 0.5716296806534101;
                                attribute 'σ_Izz' : Real = 0.37017423652493897;
                                attribute Ixy : Real = -0.03224629452045791;
                                attribute 'σ_Ixy' : Real = 0.02351283871158888;
                                attribute Ixz : Real = -0.01831237160975026;
                                attribute 'σ_Ixz' : Real = 0.022566176940390956;
                                attribute Iyz : Real = -0.01580900411041409;
                                attribute 'σ_Iyz' : Real = 0.02209918015384651;
                            }
                            part <'C.1.2.1.2.5.2.2'> 'Part 832' {
                                attribute POIconv : String = "+";
                                attribute Ipoint : Boolean = false;
                                attribute mass : Real = 0.5820001744835172;
                                attribute 'σ_mass' : Real = 0.28909372274994966;
                                attribute Cx : Real = -2.857040846720338;
                                attribute 'σ_Cx' : Real = 28.721044428837228;
                                attribute Cy : Real = 38.35672647692263;
                                attribute 'σ_Cy' : Real = 28.23690002309109;
                                attribute Cz : Real = 79.24908045679331;
                                attribute 'σ_Cz' : Real = 29.057750463592832;
                                attribute Ixx : Real = 0.7097826186053038;
                                attribute 'σ_Ixx' : Real = 0.37074144170588635;
                                attribute Iyy : Real = 0.7219674236698198;
                                attribute 'σ_Iyy' : Real = 0.3723953238821935;
                                attribute Izz : Real = 0.7318502106340017;
                                attribute 'σ_Izz' : Real = 0.37017423652493897;
                                attribute Ixy : Real = 0.005117095709049087;
                                attribute 'σ_Ixy' : Real = 0.02351283871158888;
                                attribute Ixz : Real = 0.029877279594565147;
                                attribute 'σ_Ixz' : Real = 0.022566176940390956;
                                attribute Iyz : Real = 0.020985204599652585;
                                attribute 'σ_Iyz' : Real = 0.02209918015384651;
                            }
                            part <'C.1.2.1.2.5.2.3'> 'Part 833' {
                                attribute POIconv : String = "+";
                                attribute Ipoint : Boolean = false;
                                attribute mass : Real = 0.25039263765048236;
                                attribute 'σ_mass' : Real = 0.28909372274994966;
                                attribute Cx : Real = -71.0338328499347;
                                attribute 'σ_Cx' : Real = 28.721044428837228;
                                attribute Cy : Real = 76.33703076280653;
                                attribute 'σ_Cy' : Real = 28.23690002309109;
                                attribute Cz : Real = -25.62081404030323;
                                attribute 'σ_Cz' : Real = 29.057750463592832;
                                attribute Ixx : Real = 0.3791176394540979;
                                attribute 'σ_Ixx' : Real = 0.37074144170588635;
                                attribute Iyy : Real = 0.29990790383627103;
                                attribute 'σ_Iyy' : Real = 0.3723953238821935;
                                attribute Izz : Real = 0.3254716396937155;
                                attribute 'σ_Izz' : Real = 0.37017423652493897;
                                attribute Ixy : Real = -0.002602383852669089;
                                attribute 'σ_Ixy' : Real = 0.02351283871158888;
                                attribute Ixz : Real = 0.021845858598623;
                                attribute 'σ_Ixz' : Real = 0.022566176940390956;
                                attribute Iyz : Real = 0.0045430762067803394;
                                attribute 'σ_Iyz' : Real = 0.02209918015384651;
                            }
                        }
                    }
                }
                part <'C.1.2.1.3'> 'Subsystem 18' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.2.1.3.1'> 'Assembly 68' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.3.1.1'> 'Subassembly 235' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.3.1.1.1'> 'Part 834' {
                                attribute POIconv : String = "+";
                                attribute Ipoint : Boolean = false;
                                attribute mass : Real = 0.40099378614360465;
                                attribute 'σ_mass' : Real = 0.28909372274994966;
                                attribute Cx : Real = -63.31187314353883;
                                attribute 'σ_Cx' : Real = 28.721044428837228;
                                attribute Cy : Real = 24.416656279936433;
                                attribute 'σ_Cy' : Real = 28.23690002309109;
                                attribute Cz : Real = 20.430675148963928;
                                attribute 'σ_Cz' : Real = 29.057750463592832;
                                attribute Ixx : Real = 0.43389863714674715;
                                attribute 'σ_Ixx' : Real = 0.37074144170588635;
                                attribute Iyy : Real = 0.4136057863438934;
                                attribute 'σ_Iyy' : Real = 0.3723953238821935;
                                attribute Izz : Real = 0.4511421402189289;
                                attribute 'σ_Izz' : Real = 0.37017423652493897;
                                attribute Ixy : Real = -0.033465300315132056;
                                attribute 'σ_Ixy' : Real = 0.02351283871158888;
                                attribute Ixz : Real = -0.0071074181250441355;
                                attribute 'σ_Ixz' : Real = 0.022566176940390956;
                                attribute Iyz : Real = 0.003935043067827086;
                                attribute 'σ_Iyz' : Real = 0.02209918015384651;
                            }
                            part <'C.1.2.1.3.1.1.2'> 'Part 835' {
                                attribute POIconv : String = "+";
                                attribute Ipoint : Boolean = false;
                                attribute mass : Real = 0.3965485842186026;
                                attribute 'σ_mass' : Real = 0.28909372274994966;
                                attribute Cx : Real = -37.19825576990843;
                                attribute 'σ_Cx' : Real = 28.721044428837228;
                                attribute Cy : Real = 35.98375837318599;
                                attribute 'σ_Cy' : Real = 28.23690002309109;
                                attribute Cz : Real = 85.53113783709705;
                                attribute 'σ_Cz' : Real = 29.057750463592832;
                                attribute Ixx : Real = 0.4887816802310661;
                                attribute 'σ_Ixx' : Real = 0.37074144170588635;
                                attribute Iyy : Real = 0.4759077769836566;
                                attribute 'σ_Iyy' : Real = 0.3723953238821935;
                                attribute Izz : Real = 0.47835749363910546;
                                attribute 'σ_Izz' : Real = 0.37017423652493897;
                                attribute Ixy : Real = -0.02665996960369591;
                                attribute 'σ_Ixy' : Real = 0.02351283871158888;
                                attribute Ixz : Real = -0.034850689630659654;
                                attribute 'σ_Ixz' : Real = 0.022566176940390956;
                                attribute Iyz : Real = 0.026177675493291808;
                                attribute 'σ_Iyz' : Real = 0.02209918015384651;
                            }
                            part <'C.1.2.1.3.1.1.3'> 'Part 836' {
                                attribute POIconv : String = "-";
                                attribute Ipoint : Boolean = false;
                                attribute mass : Real = 0.8315259313513524;
                                attribute 'σ_mass' : Real = 0.28909372274994966;
                                attribute Cx : Real = 15.8177703153342;
                                attribute 'σ_Cx' : Real = 28.721044428837228;
                                attribute Cy : Real = 23.80897239781916;
                                attribute 'σ_Cy' : Real = 28.23690002309109;
                                attribute Cz : Real = 7.037206087261438;
                                attribute 'σ_Cz' : Real = 29.057750463592832;
                                attribute Ixx : Real = 0.9275314361620922;
                                attribute 'σ_Ixx' : Real = 0.37074144170588635;
                                attribute Iyy : Real = 1.0193814559402556;
                                attribute 'σ_Iyy' : Real = 0.3723953238821935;
                                attribute Izz : Real = 1.056605242268911;
                                attribute 'σ_Izz' : Real = 0.37017423652493897;
                                attribute Ixy : Real = 0.07547228895137376;
                                attribute 'σ_Ixy' : Real = 0.02351283871158888;
                                attribute Ixz : Real = -0.0022189472138;
                                attribute 'σ_Ixz' : Real = 0.022566176940390956;
                                attribute Iyz : Real = 0.04228784251264097;
                                attribute 'σ_Iyz' : Real = 0.02209918015384651;
                            }
                            part <'C.1.2.1.3.1.1.4'> 'Part 837' {
                                attribute POIconv : String = "+";
                                attribute Ipoint : Boolean = false;
                                attribute mass : Real = 0.723409161610296;
                                attribute 'σ_mass' : Real = 0.28909372274994966;
                                attribute Cx : Real = -98.86088455095887;
                                attribute 'σ_Cx' : Real = 28.721044428837228;
                                attribute Cy : Real = -64.86939382739365;
                                attribute 'σ_Cy' : Real = 28.23690002309109;
                                attribute Cz : Real = 35.91932603158057;
                                attribute 'σ_Cz' : Real = 29.057750463592832;
                                attribute Ixx : Real = 0.8889606265451537;
                                attribute 'σ_Ixx' : Real = 0.37074144170588635;
                                attribute Iyy : Real = 0.8428181531060767;
                                attribute 'σ_Iyy' : Real = 0.3723953238821935;
                                attribute Izz : Real = 0.8737200009732881;
                                attribute 'σ_Izz' : Real = 0.37017423652493897;
                                attribute Ixy : Real = 0.026297500605374745;
                                attribute 'σ_Ixy' : Real = 0.02351283871158888;
                                attribute Ixz : Real = -0.015683970796338036;
                                attribute 'σ_Ixz' : Real = 0.022566176940390956;
                                attribute Iyz : Real = 0.05770215468870961;
                                attribute 'σ_Iyz' : Real = 0.02209918015384651;
                            }
                        }
                        part <'C.1.2.1.3.1.2'> 'Subassembly 236' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.3.1.2.1'> 'Part 838' {
                                attribute POIconv : String = "-";
                                attribute Ipoint : Boolean = false;
                                attribute mass : Real = 0.18060214138007724;
                                attribute 'σ_mass' : Real = 0.28909372274994966;
                                attribute Cx : Real = 40.98220723681152;
                                attribute 'σ_Cx' : Real = 28.721044428837228;
                                attribute Cy : Real = -36.13418573513627;
                                attribute 'σ_Cy' : Real = 28.23690002309109;
                                attribute Cz : Real = 67.83918738365173;
                                attribute 'σ_Cz' : Real = 29.057750463592832;
                                attribute Ixx : Real = 0.17763309127981006;
                                attribute 'σ_Ixx' : Real = 0.37074144170588635;
                                attribute Iyy : Real = 0.1833857910489603;
                                attribute 'σ_Iyy' : Real = 0.3723953238821935;
                                attribute Izz : Real = 0.17439103717133309;
                                attribute 'σ_Izz' : Real = 0.37017423652493897;
                                attribute Ixy : Real = 0.007774736480611695;
                                attribute 'σ_Ixy' : Real = 0.02351283871158888;
                                attribute Ixz : Real = 0.0036302044481339012;
                                attribute 'σ_Ixz' : Real = 0.022566176940390956;
                                attribute Iyz : Real = 0.005082938168061955;
                                attribute 'σ_Iyz' : Real = 0.02209918015384651;
                            }
                            part <'C.1.2.1.3.1.2.2'> 'Part 839' {
                                attribute POIconv : String = "-";
                                attribute Ipoint : Boolean = false;
                                attribute mass : Real = 0.04448513200553134;
                                attribute 'σ_mass' : Real = 0.28909372274994966;
                                attribute Cx : Real = -94.68534686602652;
                                attribute 'σ_Cx' : Real = 28.721044428837228;
                                attribute Cy : Real = 50.96291727386415;
                                attribute 'σ_Cy' : Real = 28.23690002309109;
                                attribute Cz : Real = 45.531967328861356;
                                attribute 'σ_Cz' : Real = 29.057750463592832;
                                attribute Ixx : Real = 0.048070007514982596;
                                attribute 'σ_Ixx' : Real = 0.37074144170588635;
                                attribute Iyy : Real = 0.05155913239151727;
                                attribute 'σ_Iyy' : Real = 0.3723953238821935;
                                attribute Izz : Real = 0.04919815742735186;
                                attribute 'σ_Izz' : Real = 0.37017423652493897;
                                attribute Ixy : Real = -3.405101173115414e-4;
                                attribute 'σ_Ixy' : Real = 0.02351283871158888;
                                attribute Ixz : Real = 2.667001804250943e-4;
                                attribute 'σ_Ixz' : Real = 0.022566176940390956;
                                attribute Iyz : Real = -0.0011680604355123628;
                                attribute 'σ_Iyz' : Real = 0.02209918015384651;
                            }
                            part <'C.1.2.1.3.1.2.3'> 'Part 840' {
                                attribute POIconv : String = "+";
                                attribute Ipoint : Boolean = false;
                                attribute mass : Real = 0.8832804494213778;
                                attribute 'σ_mass' : Real = 0.28909372274994966;
                                attribute Cx : Real = 99.69018320553005;
                                attribute 'σ_Cx' : Real = 28.721044428837228;
                                attribute Cy : Real = -21.789415599778295;
                                attribute 'σ_Cy' : Real = 28.23690002309109;
                                attribute Cz : Real = 47.132286708801985;
                                attribute 'σ_Cz' : Real = 29.057750463592832;
                                attribute Ixx : Real = 1.037771344959049;
                                attribute 'σ_Ixx' : Real = 0.37074144170588635;
                                attribute Iyy : Real = 1.227757984799689;
                                attribute 'σ_Iyy' : Real = 0.3723953238821935;
                                attribute Izz : Real = 1.1584179282114149;
                                attribute 'σ_Izz' : Real = 0.37017423652493897;
                                attribute Ixy : Real = 2.0116007688728452e-4;
                                attribute 'σ_Ixy' : Real = 0.02351283871158888;
                                attribute Ixz : Real = 0.023356926861564535;
                                attribute 'σ_Ixz' : Real = 0.022566176940390956;
                                attribute Iyz : Real = 0.01975443995295485;
                                attribute 'σ_Iyz' : Real = 0.02209918015384651;
                            }
                        }
                        part <'C.1.2.1.3.1.3'> 'Subassembly 237' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.3.1.3.1'> 'Part 841' {
                                attribute POIconv : String = "-";
                                attribute Ipoint : Boolean = false;
                                attribute mass : Real = 0.6974133238613139;
                                attribute 'σ_mass' : Real = 0.28909372274994966;
                                attribute Cx : Real = 58.90536648221314;
                                attribute 'σ_Cx' : Real = 28.721044428837228;
                                attribute Cy : Real = 11.541157588362694;
                                attribute 'σ_Cy' : Real = 28.23690002309109;
                                attribute Cz : Real = 42.282070592045784;
                                attribute 'σ_Cz' : Real = 29.057750463592832;
                                attribute Ixx : Real = 0.7733964985157729;
                                attribute 'σ_Ixx' : Real = 0.37074144170588635;
                                attribute Iyy : Real = 0.9014774039244129;
                                attribute 'σ_Iyy' : Real = 0.3723953238821935;
                                attribute Izz : Real = 0.8169174212999276;
                                attribute 'σ_Izz' : Real = 0.37017423652493897;
                                attribute Ixy : Real = 0.0870349451067998;
                                attribute 'σ_Ixy' : Real = 0.02351283871158888;
                                attribute Ixz : Real = 0.02392171970335654;
                                attribute 'σ_Ixz' : Real = 0.022566176940390956;
                                attribute Iyz : Real = 0.02333493268479006;
                                attribute 'σ_Iyz' : Real = 0.02209918015384651;
                            }
                            part <'C.1.2.1.3.1.3.2'> 'Part 842' {
                                attribute POIconv : String = "-";
                                attribute Ipoint : Boolean = false;
                                attribute mass : Real = 0.4710435666393023;
                                attribute 'σ_mass' : Real = 0.28909372274994966;
                                attribute Cx : Real = -61.673590913414955;
                                attribute 'σ_Cx' : Real = 28.721044428837228;
                                attribute Cy : Real = -27.983535081148148;
                                attribute 'σ_Cy' : Real = 28.23690002309109;
                                attribute Cz : Real = -97.16738099232316;
                                attribute 'σ_Cz' : Real = 29.057750463592832;
                                attribute Ixx : Real = 0.5614294522864547;
                                attribute 'σ_Ixx' : Real = 0.37074144170588635;
                                attribute Iyy : Real = 0.5569097222664281;
                                attribute 'σ_Iyy' : Real = 0.3723953238821935;
                                attribute Izz : Real = 0.6337890002713044;
                                attribute 'σ_Izz' : Real = 0.37017423652493897;
                                attribute Ixy : Real = 0.0037484803960846948;
                                attribute 'σ_Ixy' : Real = 0.02351283871158888;
                                attribute Ixz : Real = 0.0024649904939099583;
                                attribute 'σ_Ixz' : Real = 0.022566176940390956;
                                attribute Iyz : Real = -0.0064300217386122575;
                                attribute 'σ_Iyz' : Real = 0.02209918015384651;
                            }
                            part <'C.1.2.1.3.1.3.3'> 'Part 843' {
                                attribute POIconv : String = "-";
                                attribute Ipoint : Boolean = false;
                                attribute mass : Real = 0.5676760180015117;
                                attribute 'σ_mass' : Real = 0.28909372274994966;
                                attribute Cx : Real = 70.62185569666326;
                                attribute 'σ_Cx' : Real = 28.721044428837228;
                                attribute Cy : Real = -5.148091074079275;
                                attribute 'σ_Cy' : Real = 28.23690002309109;
                                attribute Cz : Real = -45.27322403155267;
                                attribute 'σ_Cz' : Real = 29.057750463592832;
                                attribute Ixx : Real = 0.6506581121627749;
                                attribute 'σ_Ixx' : Real = 0.37074144170588635;
                                attribute Iyy : Real = 0.6773699207006573;
                                attribute 'σ_Iyy' : Real = 0.3723953238821935;
                                attribute Izz : Real = 0.8307662490023936;
                                attribute 'σ_Izz' : Real = 0.37017423652493897;
                                attribute Ixy : Real = -0.03918493957988709;
                                attribute 'σ_Ixy' : Real = 0.02351283871158888;
                                attribute Ixz : Real = 0.01553861912446197;
                                attribute 'σ_Ixz' : Real = 0.022566176940390956;
                                attribute Iyz : Real = -0.02922590426635077;
                                attribute 'σ_Iyz' : Real = 0.02209918015384651;
                            }
                            part <'C.1.2.1.3.1.3.4'> 'Part 844' {
                                attribute POIconv : String = "-";
                                attribute Ipoint : Boolean = false;
                                attribute mass : Real = 0.36819439607369714;
                                attribute 'σ_mass' : Real = 0.28909372274994966;
                                attribute Cx : Real = -19.362441822886467;
                                attribute 'σ_Cx' : Real = 28.721044428837228;
                                attribute Cy : Real = 76.76816508173943;
                                attribute 'σ_Cy' : Real = 28.23690002309109;
                                attribute Cz : Real = -20.25180640630424;
                                attribute 'σ_Cz' : Real = 29.057750463592832;
                                attribute Ixx : Real = 0.40684972322174673;
                                attribute 'σ_Ixx' : Real = 0.37074144170588635;
                                attribute Iyy : Real = 0.3816103408811263;
                                attribute 'σ_Iyy' : Real = 0.3723953238821935;
                                attribute Izz : Real = 0.40004719993120336;
                                attribute 'σ_Izz' : Real = 0.37017423652493897;
                                attribute Ixy : Real = -0.00459355852336243;
                                attribute 'σ_Ixy' : Real = 0.02351283871158888;
                                attribute Ixz : Real = 0.01398166946070881;
                                attribute 'σ_Ixz' : Real = 0.022566176940390956;
                                attribute Iyz : Real = 0.005299486149481961;
                                attribute 'σ_Iyz' : Real = 0.02209918015384651;
                            }
                        }
                        part <'C.1.2.1.3.1.4'> 'Subassembly 238' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.3.1.4.1'> 'Part 845' {
                                attribute POIconv : String = "-";
                                attribute Ipoint : Boolean = false;
                                attribute mass : Real = 0.17836986341816374;
                                attribute 'σ_mass' : Real = 0.28909372274994966;
                                attribute Cx : Real = -84.28431488573551;
                                attribute 'σ_Cx' : Real = 28.721044428837228;
                                attribute Cy : Real = 11.25832605175674;
                                attribute 'σ_Cy' : Real = 28.23690002309109;
                                attribute Cz : Real = 36.66739072650671;
                                attribute 'σ_Cz' : Real = 29.057750463592832;
                                attribute Ixx : Real = 0.20491633877743987;
                                attribute 'σ_Ixx' : Real = 0.37074144170588635;
                                attribute Iyy : Real = 0.21112120229710843;
                                attribute 'σ_Iyy' : Real = 0.3723953238821935;
                                attribute Izz : Real = 0.20690681109857711;
                                attribute 'σ_Izz' : Real = 0.37017423652493897;
                                attribute Ixy : Real = 0.006710751585280946;
                                attribute 'σ_Ixy' : Real = 0.02351283871158888;
                                attribute Ixz : Real = -0.015210111434240042;
                                attribute 'σ_Ixz' : Real = 0.022566176940390956;
                                attribute Iyz : Real = -0.002353009527986966;
                                attribute 'σ_Iyz' : Real = 0.02209918015384651;
                            }
                            part <'C.1.2.1.3.1.4.2'> 'Part 846' {
                                attribute POIconv : String = "-";
                                attribute Ipoint : Boolean = false;
                                attribute mass : Real = 0.025595546347554773;
                                attribute 'σ_mass' : Real = 0.28909372274994966;
                                attribute Cx : Real = 6.225353619083762;
                                attribute 'σ_Cx' : Real = 28.721044428837228;
                                attribute Cy : Real = 45.47065733931959;
                                attribute 'σ_Cy' : Real = 28.23690002309109;
                                attribute Cz : Real = -46.5387755073607;
                                attribute 'σ_Cz' : Real = 29.057750463592832;
                                attribute Ixx : Real = 0.036601651673853056;
                                attribute 'σ_Ixx' : Real = 0.37074144170588635;
                                attribute Iyy : Real = 0.03465495501650911;
                                attribute 'σ_Iyy' : Real = 0.3723953238821935;
                                attribute Izz : Real = 0.036434757713451886;
                                attribute 'σ_Izz' : Real = 0.37017423652493897;
                                attribute Ixy : Real = 6.698178929613933e-4;
                                attribute 'σ_Ixy' : Real = 0.02351283871158888;
                                attribute Ixz : Real = 6.956095830493443e-5;
                                attribute 'σ_Ixz' : Real = 0.022566176940390956;
                                attribute Iyz : Real = -9.337699946537705e-5;
                                attribute 'σ_Iyz' : Real = 0.02209918015384651;
                            }
                            part <'C.1.2.1.3.1.4.3'> 'Part 847' {
                                attribute POIconv : String = "-";
                                attribute Ipoint : Boolean = false;
                                attribute mass : Real = 0.7577999298607465;
                                attribute 'σ_mass' : Real = 0.28909372274994966;
                                attribute Cx : Real = 57.1947630494833;
                                attribute 'σ_Cx' : Real = 28.721044428837228;
                                attribute Cy : Real = -29.537076270207763;
                                attribute 'σ_Cy' : Real = 28.23690002309109;
                                attribute Cz : Real = 62.86085303872824;
                                attribute 'σ_Cz' : Real = 29.057750463592832;
                                attribute Ixx : Real = 0.8989543317891859;
                                attribute 'σ_Ixx' : Real = 0.37074144170588635;
                                attribute Iyy : Real = 0.93669153846115;
                                attribute 'σ_Iyy' : Real = 0.3723953238821935;
                                attribute Izz : Real = 0.9273691313152126;
                                attribute 'σ_Izz' : Real = 0.37017423652493897;
                                attribute Ixy : Real = 0.006974220493670368;
                                attribute 'σ_Ixy' : Real = 0.02351283871158888;
                                attribute Ixz : Real = -0.0015070331325996455;
                                attribute 'σ_Ixz' : Real = 0.022566176940390956;
                                attribute Iyz : Real = -0.004893940154830681;
                                attribute 'σ_Iyz' : Real = 0.02209918015384651;
                            }
                            part <'C.1.2.1.3.1.4.4'> 'Part 848' {
                                attribute POIconv : String = "+";
                                attribute Ipoint : Boolean = false;
                                attribute mass : Real = 0.4715934967182111;
                                attribute 'σ_mass' : Real = 0.28909372274994966;
                                attribute Cx : Real = -51.51402843184769;
                                attribute 'σ_Cx' : Real = 28.721044428837228;
                                attribute Cy : Real = 81.42598224803805;
                                attribute 'σ_Cy' : Real = 28.23690002309109;
                                attribute Cz : Real = 16.80910838767886;
                                attribute 'σ_Cz' : Real = 29.057750463592832;
                                attribute Ixx : Real = 0.5489609593213219;
                                attribute 'σ_Ixx' : Real = 0.37074144170588635;
                                attribute Iyy : Real = 0.5693346421181444;
                                attribute 'σ_Iyy' : Real = 0.3723953238821935;
                                attribute Izz : Real = 0.6659487347226564;
                                attribute 'σ_Izz' : Real = 0.37017423652493897;
                                attribute Ixy : Real = 0.03993464009478294;
                                attribute 'σ_Ixy' : Real = 0.02351283871158888;
                                attribute Ixz : Real = -0.023106712773182526;
                                attribute 'σ_Ixz' : Real = 0.022566176940390956;
                                attribute Iyz : Real = -0.006797290756618564;
                                attribute 'σ_Iyz' : Real = 0.02209918015384651;
                            }
                        }
                        part <'C.1.2.1.3.1.5'> 'Subassembly 239' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.3.1.5.1'> 'Part 849' {
                                attribute POIconv : String = "-";
                                attribute Ipoint : Boolean = false;
                                attribute mass : Real = 0.7584273910708725;
                                attribute 'σ_mass' : Real = 0.28909372274994966;
                                attribute Cx : Real = 98.75570465810597;
                                attribute 'σ_Cx' : Real = 28.721044428837228;
                                attribute Cy : Real = 38.16164047457278;
                                attribute 'σ_Cy' : Real = 28.23690002309109;
                                attribute Cz : Real = 42.628013947978616;
                                attribute 'σ_Cz' : Real = 29.057750463592832;
                                attribute Ixx : Real = 0.9456711438455622;
                                attribute 'σ_Ixx' : Real = 0.37074144170588635;
                                attribute Iyy : Real = 0.8135015464339254;
                                attribute 'σ_Iyy' : Real = 0.3723953238821935;
                                attribute Izz : Real = 0.9009828819031636;
                                attribute 'σ_Izz' : Real = 0.37017423652493897;
                                attribute Ixy : Real = 0.025686869040586;
                                attribute 'σ_Ixy' : Real = 0.02351283871158888;
                                attribute Ixz : Real = -0.0025239344307033413;
                                attribute 'σ_Ixz' : Real = 0.022566176940390956;
                                attribute Iyz : Real = -0.06813605856113383;
                                attribute 'σ_Iyz' : Real = 0.02209918015384651;
                            }
                            part <'C.1.2.1.3.1.5.2'> 'Part 850' {
                                attribute POIconv : String = "-";
                                attribute Ipoint : Boolean = false;
                                attribute mass : Real = 0.07093144333455711;
                                attribute 'σ_mass' : Real = 0.28909372274994966;
                                attribute Cx : Real = -90.91553427278996;
                                attribute 'σ_Cx' : Real = 28.721044428837228;
                                attribute Cy : Real = 71.49170157499611;
                                attribute 'σ_Cy' : Real = 28.23690002309109;
                                attribute Cz : Real = -94.74786752834916;
                                attribute 'σ_Cz' : Real = 29.057750463592832;
                                attribute Ixx : Real = 0.08694027832231106;
                                attribute 'σ_Ixx' : Real = 0.37074144170588635;
                                attribute Iyy : Real = 0.07925489046836325;
                                attribute 'σ_Iyy' : Real = 0.3723953238821935;
                                attribute Izz : Real = 0.07676549023377613;
                                attribute 'σ_Izz' : Real = 0.37017423652493897;
                                attribute Ixy : Real = -7.213143040008382e-4;
                                attribute 'σ_Ixy' : Real = 0.02351283871158888;
                                attribute Ixz : Real = -0.008296425753552775;
                                attribute 'σ_Ixz' : Real = 0.022566176940390956;
                                attribute Iyz : Real = -0.0014388781583278211;
                                attribute 'σ_Iyz' : Real = 0.02209918015384651;
                            }
                        }
                    }
                    part <'C.1.2.1.3.2'> 'Assembly 69' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.3.2.1'> 'Subassembly 240' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.3.2.1.1'> 'Part 851' {
                                attribute POIconv : String = "-";
                                attribute Ipoint : Boolean = false;
                                attribute mass : Real = 0.16698747498332522;
                                attribute 'σ_mass' : Real = 0.28909372274994966;
                                attribute Cx : Real = 79.75233374163508;
                                attribute 'σ_Cx' : Real = 28.721044428837228;
                                attribute Cy : Real = -42.011516727507114;
                                attribute 'σ_Cy' : Real = 28.23690002309109;
                                attribute Cz : Real = -50.059696519747376;
                                attribute 'σ_Cz' : Real = 29.057750463592832;
                                attribute Ixx : Real = 0.2446022948140927;
                                attribute 'σ_Ixx' : Real = 0.37074144170588635;
                                attribute Iyy : Real = 0.24626061312165018;
                                attribute 'σ_Iyy' : Real = 0.3723953238821935;
                                attribute Izz : Real = 0.23472495987538344;
                                attribute 'σ_Izz' : Real = 0.37017423652493897;
                                attribute Ixy : Real = -0.002972235633421123;
                                attribute 'σ_Ixy' : Real = 0.02351283871158888;
                                attribute Ixz : Real = 0.0029887339776154863;
                                attribute 'σ_Ixz' : Real = 0.022566176940390956;
                                attribute Iyz : Real = 0.013387998794383862;
                                attribute 'σ_Iyz' : Real = 0.02209918015384651;
                            }
                            part <'C.1.2.1.3.2.1.2'> 'Part 852' {
                                attribute POIconv : String = "-";
                                attribute Ipoint : Boolean = false;
                                attribute mass : Real = 0.8872344696600921;
                                attribute 'σ_mass' : Real = 0.28909372274994966;
                                attribute Cx : Real = 33.247135719284415;
                                attribute 'σ_Cx' : Real = 28.721044428837228;
                                attribute Cy : Real = -13.975840294733644;
                                attribute 'σ_Cy' : Real = 28.23690002309109;
                                attribute Cz : Real = -74.10353431478143;
                                attribute 'σ_Cz' : Real = 29.057750463592832;
                                attribute Ixx : Real = 1.0351687186330198;
                                attribute 'σ_Ixx' : Real = 0.37074144170588635;
                                attribute Iyy : Real = 1.0173308018021852;
                                attribute 'σ_Iyy' : Real = 0.3723953238821935;
                                attribute Izz : Real = 1.1655502162221663;
                                attribute 'σ_Izz' : Real = 0.37017423652493897;
                                attribute Ixy : Real = -1.5872870575983403e-4;
                                attribute 'σ_Ixy' : Real = 0.02351283871158888;
                                attribute Ixz : Real = -0.10618243061171033;
                                attribute 'σ_Ixz' : Real = 0.022566176940390956;
                                attribute Iyz : Real = -0.02182010108579728;
                                attribute 'σ_Iyz' : Real = 0.02209918015384651;
                            }
                            part <'C.1.2.1.3.2.1.3'> 'Part 853' {
                                attribute POIconv : String = "-";
                                attribute Ipoint : Boolean = false;
                                attribute mass : Real = 0.7200871382390615;
                                attribute 'σ_mass' : Real = 0.28909372274994966;
                                attribute Cx : Real = 84.28843710571527;
                                attribute 'σ_Cx' : Real = 28.721044428837228;
                                attribute Cy : Real = -76.57057633623481;
                                attribute 'σ_Cy' : Real = 28.23690002309109;
                                attribute Cz : Real = -24.23769822344184;
                                attribute 'σ_Cz' : Real = 29.057750463592832;
                                attribute Ixx : Real = 0.7041585712206068;
                                attribute 'σ_Ixx' : Real = 0.37074144170588635;
                                attribute Iyy : Real = 0.7016647586513276;
                                attribute 'σ_Iyy' : Real = 0.3723953238821935;
                                attribute Izz : Real = 0.7074755072409198;
                                attribute 'σ_Izz' : Real = 0.37017423652493897;
                                attribute Ixy : Real = 0.0027835058640887454;
                                attribute 'σ_Ixy' : Real = 0.02351283871158888;
                                attribute Ixz : Real = -0.011163511440675228;
                                attribute 'σ_Ixz' : Real = 0.022566176940390956;
                                attribute Iyz : Real = -0.034477368700925395;
                                attribute 'σ_Iyz' : Real = 0.02209918015384651;
                            }
                        }
                        part <'C.1.2.1.3.2.2'> 'Subassembly 241' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.3.2.2.1'> 'Part 854' {
                                attribute POIconv : String = "+";
                                attribute Ipoint : Boolean = false;
                                attribute mass : Real = 0.06637552624614909;
                                attribute 'σ_mass' : Real = 0.28909372274994966;
                                attribute Cx : Real = -65.73344920761883;
                                attribute 'σ_Cx' : Real = 28.721044428837228;
                                attribute Cy : Real = 42.837348533794284;
                                attribute 'σ_Cy' : Real = 28.23690002309109;
                                attribute Cz : Real = -47.21266976557672;
                                attribute 'σ_Cz' : Real = 29.057750463592832;
                                attribute Ixx : Real = 0.07601141126649608;
                                attribute 'σ_Ixx' : Real = 0.37074144170588635;
                                attribute Iyy : Real = 0.07311074736691542;
                                attribute 'σ_Iyy' : Real = 0.3723953238821935;
                                attribute Izz : Real = 0.07816037962959646;
                                attribute 'σ_Izz' : Real = 0.37017423652493897;
                                attribute Ixy : Real = -0.003240559665272272;
                                attribute 'σ_Ixy' : Real = 0.02351283871158888;
                                attribute Ixz : Real = 5.301398026383039e-4;
                                attribute 'σ_Ixz' : Real = 0.022566176940390956;
                                attribute Iyz : Real = 2.3359646076289906e-4;
                                attribute 'σ_Iyz' : Real = 0.02209918015384651;
                            }
                            part <'C.1.2.1.3.2.2.2'> 'Part 855' {
                                attribute POIconv : String = "-";
                                attribute Ipoint : Boolean = false;
                                attribute mass : Real = 0.651910930801183;
                                attribute 'σ_mass' : Real = 0.28909372274994966;
                                attribute Cx : Real = 30.22468676790595;
                                attribute 'σ_Cx' : Real = 28.721044428837228;
                                attribute Cy : Real = -98.74559822492301;
                                attribute 'σ_Cy' : Real = 28.23690002309109;
                                attribute Cz : Real = -17.42980726994574;
                                attribute 'σ_Cz' : Real = 29.057750463592832;
                                attribute Ixx : Real = 0.8577564852089625;
                                attribute 'σ_Ixx' : Real = 0.37074144170588635;
                                attribute Iyy : Real = 0.7401335690513332;
                                attribute 'σ_Iyy' : Real = 0.3723953238821935;
                                attribute Izz : Real = 0.8739325202977855;
                                attribute 'σ_Izz' : Real = 0.37017423652493897;
                                attribute Ixy : Real = -0.05112854812300843;
                                attribute 'σ_Ixy' : Real = 0.02351283871158888;
                                attribute Ixz : Real = 0.005699994729036106;
                                attribute 'σ_Ixz' : Real = 0.022566176940390956;
                                attribute Iyz : Real = 0.016233382108483515;
                                attribute 'σ_Iyz' : Real = 0.02209918015384651;
                            }
                            part <'C.1.2.1.3.2.2.3'> 'Part 856' {
                                attribute POIconv : String = "-";
                                attribute Ipoint : Boolean = false;
                                attribute mass : Real = 0.7030004933588206;
                                attribute 'σ_mass' : Real = 0.28909372274994966;
                                attribute Cx : Real = -19.05247075483203;
                                attribute 'σ_Cx' : Real = 28.721044428837228;
                                attribute Cy : Real = -20.96820971928537;
                                attribute 'σ_Cy' : Real = 28.23690002309109;
                                attribute Cz : Real = 30.952070746570826;
                                attribute 'σ_Cz' : Real = 29.057750463592832;
                                attribute Ixx : Real = 0.7477947201232356;
                                attribute 'σ_Ixx' : Real = 0.37074144170588635;
                                attribute Iyy : Real = 0.7509087750921246;
                                attribute 'σ_Iyy' : Real = 0.3723953238821935;
                                attribute Izz : Real = 0.6083553538837135;
                                attribute 'σ_Izz' : Real = 0.37017423652493897;
                                attribute Ixy : Real = 0.004966556991600009;
                                attribute 'σ_Ixy' : Real = 0.02351283871158888;
                                attribute Ixz : Real = -0.024876684771466758;
                                attribute 'σ_Ixz' : Real = 0.022566176940390956;
                                attribute Iyz : Real = 0.02692203311809019;
                                attribute 'σ_Iyz' : Real = 0.02209918015384651;
                            }
                            part <'C.1.2.1.3.2.2.4'> 'Part 857' {
                                attribute POIconv : String = "-";
                                attribute Ipoint : Boolean = false;
                                attribute mass : Real = 0.3131305677311029;
                                attribute 'σ_mass' : Real = 0.28909372274994966;
                                attribute Cx : Real = -78.30029143951833;
                                attribute 'σ_Cx' : Real = 28.721044428837228;
                                attribute Cy : Real = -86.1513308249414;
                                attribute 'σ_Cy' : Real = 28.23690002309109;
                                attribute Cz : Real = 19.880848145112395;
                                attribute 'σ_Cz' : Real = 29.057750463592832;
                                attribute Ixx : Real = 0.47021226519225606;
                                attribute 'σ_Ixx' : Real = 0.37074144170588635;
                                attribute Iyy : Real = 0.47282941316419513;
                                attribute 'σ_Iyy' : Real = 0.3723953238821935;
                                attribute Izz : Real = 0.49582818660291456;
                                attribute 'σ_Izz' : Real = 0.37017423652493897;
                                attribute Ixy : Real = -0.004039362404676732;
                                attribute 'σ_Ixy' : Real = 0.02351283871158888;
                                attribute Ixz : Real = -0.0029216016162537327;
                                attribute 'σ_Ixz' : Real = 0.022566176940390956;
                                attribute Iyz : Real = 0.008060700605007121;
                                attribute 'σ_Iyz' : Real = 0.02209918015384651;
                            }
                        }
                        part <'C.1.2.1.3.2.3'> 'Subassembly 242' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.3.2.3.1'> 'Part 858' {
                                attribute POIconv : String = "-";
                                attribute Ipoint : Boolean = false;
                                attribute mass : Real = 0.00933534731529653;
                                attribute 'σ_mass' : Real = 0.28909372274994966;
                                attribute Cx : Real = -47.66736491583288;
                                attribute 'σ_Cx' : Real = 28.721044428837228;
                                attribute Cy : Real = -14.171905443072319;
                                attribute 'σ_Cy' : Real = 28.23690002309109;
                                attribute Cz : Real = 61.94947957992554;
                                attribute 'σ_Cz' : Real = 29.057750463592832;
                                attribute Ixx : Real = 0.012872223157351688;
                                attribute 'σ_Ixx' : Real = 0.37074144170588635;
                                attribute Iyy : Real = 0.011692039029950179;
                                attribute 'σ_Iyy' : Real = 0.3723953238821935;
                                attribute Izz : Real = 0.012112301882123434;
                                attribute 'σ_Izz' : Real = 0.37017423652493897;
                                attribute Ixy : Real = -8.5968288171009e-4;
                                attribute 'σ_Ixy' : Real = 0.02351283871158888;
                                attribute Ixz : Real = -0.0013162378460921578;
                                attribute 'σ_Ixz' : Real = 0.022566176940390956;
                                attribute Iyz : Real = 2.3031250823094397e-4;
                                attribute 'σ_Iyz' : Real = 0.02209918015384651;
                            }
                            part <'C.1.2.1.3.2.3.2'> 'Part 859' {
                                attribute POIconv : String = "-";
                                attribute Ipoint : Boolean = false;
                                attribute mass : Real = 0.4648861519698985;
                                attribute 'σ_mass' : Real = 0.28909372274994966;
                                attribute Cx : Real = 69.58614005707204;
                                attribute 'σ_Cx' : Real = 28.721044428837228;
                                attribute Cy : Real = 56.126068299636245;
                                attribute 'σ_Cy' : Real = 28.23690002309109;
                                attribute Cz : Real = 48.7769422121346;
                                attribute 'σ_Cz' : Real = 29.057750463592832;
                                attribute Ixx : Real = 0.5964410415207153;
                                attribute 'σ_Ixx' : Real = 0.37074144170588635;
                                attribute Iyy : Real = 0.4803773995355326;
                                attribute 'σ_Iyy' : Real = 0.3723953238821935;
                                attribute Izz : Real = 0.6377796703367564;
                                attribute 'σ_Izz' : Real = 0.37017423652493897;
                                attribute Ixy : Real = 0.003160270056478289;
                                attribute 'σ_Ixy' : Real = 0.02351283871158888;
                                attribute Ixz : Real = 0.019801128400824486;
                                attribute 'σ_Ixz' : Real = 0.022566176940390956;
                                attribute Iyz : Real = 0.005662558371979268;
                                attribute 'σ_Iyz' : Real = 0.02209918015384651;
                            }
                            part <'C.1.2.1.3.2.3.3'> 'Part 860' {
                                attribute POIconv : String = "-";
                                attribute Ipoint : Boolean = false;
                                attribute mass : Real = 0.5012732081627473;
                                attribute 'σ_mass' : Real = 0.28909372274994966;
                                attribute Cx : Real = 76.55848963186145;
                                attribute 'σ_Cx' : Real = 28.721044428837228;
                                attribute Cy : Real = 44.267522636801004;
                                attribute 'σ_Cy' : Real = 28.23690002309109;
                                attribute Cz : Real = 16.963543090969324;
                                attribute 'σ_Cz' : Real = 29.057750463592832;
                                attribute Ixx : Real = 0.6205684414365252;
                                attribute 'σ_Ixx' : Real = 0.37074144170588635;
                                attribute Iyy : Real = 0.6257512516446063;
                                attribute 'σ_Iyy' : Real = 0.3723953238821935;
                                attribute Izz : Real = 0.6233369809397908;
                                attribute 'σ_Izz' : Real = 0.37017423652493897;
                                attribute Ixy : Real = 0.0028794879059003088;
                                attribute 'σ_Ixy' : Real = 0.02351283871158888;
                                attribute Ixz : Real = -0.003101390170643961;
                                attribute 'σ_Ixz' : Real = 0.022566176940390956;
                                attribute Iyz : Real = 4.958489557705843e-4;
                                attribute 'σ_Iyz' : Real = 0.02209918015384651;
                            }
                            part <'C.1.2.1.3.2.3.4'> 'Part 861' {
                                attribute POIconv : String = "-";
                                attribute Ipoint : Boolean = false;
                                attribute mass : Real = 0.6474192474596202;
                                attribute 'σ_mass' : Real = 0.28909372274994966;
                                attribute Cx : Real = -65.2507589198649;
                                attribute 'σ_Cx' : Real = 28.721044428837228;
                                attribute Cy : Real = 65.32276957295835;
                                attribute 'σ_Cy' : Real = 28.23690002309109;
                                attribute Cz : Real = -29.151621041819453;
                                attribute 'σ_Cz' : Real = 29.057750463592832;
                                attribute Ixx : Real = 0.7558995706929647;
                                attribute 'σ_Ixx' : Real = 0.37074144170588635;
                                attribute Iyy : Real = 0.7928488191668013;
                                attribute 'σ_Iyy' : Real = 0.3723953238821935;
                                attribute Izz : Real = 0.7165132914075537;
                                attribute 'σ_Izz' : Real = 0.37017423652493897;
                                attribute Ixy : Real = -0.024177475921984385;
                                attribute 'σ_Ixy' : Real = 0.02351283871158888;
                                attribute Ixz : Real = 0.020254634278347613;
                                attribute 'σ_Ixz' : Real = 0.022566176940390956;
                                attribute Iyz : Real = 0.01851132812549184;
                                attribute 'σ_Iyz' : Real = 0.02209918015384651;
                            }
                        }
                        part <'C.1.2.1.3.2.4'> 'Subassembly 243' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.3.2.4.1'> 'Part 862' {
                                attribute POIconv : String = "+";
                                attribute Ipoint : Boolean = false;
                                attribute mass : Real = 0.4121293020050507;
                                attribute 'σ_mass' : Real = 0.28909372274994966;
                                attribute Cx : Real = -14.421700173988938;
                                attribute 'σ_Cx' : Real = 28.721044428837228;
                                attribute Cy : Real = 74.04830218292773;
                                attribute 'σ_Cy' : Real = 28.23690002309109;
                                attribute Cz : Real = -25.63537247478962;
                                attribute 'σ_Cz' : Real = 29.057750463592832;
                                attribute Ixx : Real = 0.538959382654313;
                                attribute 'σ_Ixx' : Real = 0.37074144170588635;
                                attribute Iyy : Real = 0.5400639859835994;
                                attribute 'σ_Iyy' : Real = 0.3723953238821935;
                                attribute Izz : Real = 0.4226073905186561;
                                attribute 'σ_Izz' : Real = 0.37017423652493897;
                                attribute Ixy : Real = 0.0015989473031791206;
                                attribute 'σ_Ixy' : Real = 0.02351283871158888;
                                attribute Ixz : Real = 0.0019416072073452939;
                                attribute 'σ_Ixz' : Real = 0.022566176940390956;
                                attribute Iyz : Real = 0.0017356833858610727;
                                attribute 'σ_Iyz' : Real = 0.02209918015384651;
                            }
                            part <'C.1.2.1.3.2.4.2'> 'Part 863' {
                                attribute POIconv : String = "+";
                                attribute Ipoint : Boolean = false;
                                attribute mass : Real = 0.9977999405567535;
                                attribute 'σ_mass' : Real = 0.28909372274994966;
                                attribute Cx : Real = 25.604777736589313;
                                attribute 'σ_Cx' : Real = 28.721044428837228;
                                attribute Cy : Real = 1.6419955994933844;
                                attribute 'σ_Cy' : Real = 28.23690002309109;
                                attribute Cz : Real = -52.63201417401433;
                                attribute 'σ_Cz' : Real = 29.057750463592832;
                                attribute Ixx : Real = 1.3773431124218019;
                                attribute 'σ_Ixx' : Real = 0.37074144170588635;
                                attribute Iyy : Real = 1.3055362404790645;
                                attribute 'σ_Iyy' : Real = 0.3723953238821935;
                                attribute Izz : Real = 1.2207548115469578;
                                attribute 'σ_Izz' : Real = 0.37017423652493897;
                                attribute Ixy : Real = -0.10230191196398598;
                                attribute 'σ_Ixy' : Real = 0.02351283871158888;
                                attribute Ixz : Real = -0.07650615223409113;
                                attribute 'σ_Ixz' : Real = 0.022566176940390956;
                                attribute Iyz : Real = -0.03266701715737544;
                                attribute 'σ_Iyz' : Real = 0.02209918015384651;
                            }
                        }
                        part <'C.1.2.1.3.2.5'> 'Subassembly 244' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.3.2.5.1'> 'Part 864' {
                                attribute POIconv : String = "-";
                                attribute Ipoint : Boolean = false;
                                attribute mass : Real = 0.5356775743139442;
                                attribute 'σ_mass' : Real = 0.28909372274994966;
                                attribute Cx : Real = 95.3914912417531;
                                attribute 'σ_Cx' : Real = 28.721044428837228;
                                attribute Cy : Real = -94.64962691999972;
                                attribute 'σ_Cy' : Real = 28.23690002309109;
                                attribute Cz : Real = 70.65375722013414;
                                attribute 'σ_Cz' : Real = 29.057750463592832;
                                attribute Ixx : Real = 0.5065910577528606;
                                attribute 'σ_Ixx' : Real = 0.37074144170588635;
                                attribute Iyy : Real = 0.6666737058866342;
                                attribute 'σ_Iyy' : Real = 0.3723953238821935;
                                attribute Izz : Real = 0.6209295219931377;
                                attribute 'σ_Izz' : Real = 0.37017423652493897;
                                attribute Ixy : Real = 0.013106678148177375;
                                attribute 'σ_Ixy' : Real = 0.02351283871158888;
                                attribute Ixz : Real = -0.06445713535372527;
                                attribute 'σ_Ixz' : Real = 0.022566176940390956;
                                attribute Iyz : Real = 0.009277910904441102;
                                attribute 'σ_Iyz' : Real = 0.02209918015384651;
                            }
                            part <'C.1.2.1.3.2.5.2'> 'Part 865' {
                                attribute POIconv : String = "-";
                                attribute Ipoint : Boolean = false;
                                attribute mass : Real = 0.9789306758067104;
                                attribute 'σ_mass' : Real = 0.28909372274994966;
                                attribute Cx : Real = 94.38720103353262;
                                attribute 'σ_Cx' : Real = 28.721044428837228;
                                attribute Cy : Real = -67.743732733652;
                                attribute 'σ_Cy' : Real = 28.23690002309109;
                                attribute Cz : Real = 49.35169564560056;
                                attribute 'σ_Cz' : Real = 29.057750463592832;
                                attribute Ixx : Real = 1.1316552003076614;
                                attribute 'σ_Ixx' : Real = 0.37074144170588635;
                                attribute Iyy : Real = 1.2492147928009492;
                                attribute 'σ_Iyy' : Real = 0.3723953238821935;
                                attribute Izz : Real = 1.0228918812757202;
                                attribute 'σ_Izz' : Real = 0.37017423652493897;
                                attribute Ixy : Real = -0.028851869426001063;
                                attribute 'σ_Ixy' : Real = 0.02351283871158888;
                                attribute Ixz : Real = 0.07290580738775347;
                                attribute 'σ_Ixz' : Real = 0.022566176940390956;
                                attribute Iyz : Real = -0.07001034554191826;
                                attribute 'σ_Iyz' : Real = 0.02209918015384651;
                            }
                            part <'C.1.2.1.3.2.5.3'> 'Part 866' {
                                attribute POIconv : String = "+";
                                attribute Ipoint : Boolean = false;
                                attribute mass : Real = 0.2665159461244475;
                                attribute 'σ_mass' : Real = 0.28909372274994966;
                                attribute Cx : Real = 20.90835776180029;
                                attribute 'σ_Cx' : Real = 28.721044428837228;
                                attribute Cy : Real = -10.535001801326871;
                                attribute 'σ_Cy' : Real = 28.23690002309109;
                                attribute Cz : Real = 12.772182933986187;
                                attribute 'σ_Cz' : Real = 29.057750463592832;
                                attribute Ixx : Real = 0.34417945419279855;
                                attribute 'σ_Ixx' : Real = 0.37074144170588635;
                                attribute Iyy : Real = 0.35010805416529395;
                                attribute 'σ_Iyy' : Real = 0.3723953238821935;
                                attribute Izz : Real = 0.3961672255533621;
                                attribute 'σ_Izz' : Real = 0.37017423652493897;
                                attribute Ixy : Real = 1.1508781543481677e-4;
                                attribute 'σ_Ixy' : Real = 0.02351283871158888;
                                attribute Ixz : Real = 4.253799259685243e-4;
                                attribute 'σ_Ixz' : Real = 0.022566176940390956;
                                attribute Iyz : Real = -0.0029131415057917854;
                                attribute 'σ_Iyz' : Real = 0.02209918015384651;
                            }
                            part <'C.1.2.1.3.2.5.4'> 'Part 867' {
                                attribute POIconv : String = "+";
                                attribute Ipoint : Boolean = false;
                                attribute mass : Real = 0.0030841485098935663;
                                attribute 'σ_mass' : Real = 0.28909372274994966;
                                attribute Cx : Real = 81.85773957520723;
                                attribute 'σ_Cx' : Real = 28.721044428837228;
                                attribute Cy : Real = 83.96136229857802;
                                attribute 'σ_Cy' : Real = 28.23690002309109;
                                attribute Cz : Real = 88.07933288626373;
                                attribute 'σ_Cz' : Real = 29.057750463592832;
                                attribute Ixx : Real = 0.003597133464721806;
                                attribute 'σ_Ixx' : Real = 0.37074144170588635;
                                attribute Iyy : Real = 0.003748139705033749;
                                attribute 'σ_Iyy' : Real = 0.3723953238821935;
                                attribute Izz : Real = 0.0040511232916386;
                                attribute 'σ_Izz' : Real = 0.37017423652493897;
                                attribute Ixy : Real = 4.35008819557647e-5;
                                attribute 'σ_Ixy' : Real = 0.02351283871158888;
                                attribute Ixz : Real = 4.662714983698157e-5;
                                attribute 'σ_Ixz' : Real = 0.022566176940390956;
                                attribute Iyz : Real = -3.2771128475900236e-4;
                                attribute 'σ_Iyz' : Real = 0.02209918015384651;
                            }
                            part <'C.1.2.1.3.2.5.5'> 'Part 868' {
                                attribute POIconv : String = "+";
                                attribute Ipoint : Boolean = false;
                                attribute mass : Real = 0.035796168793691324;
                                attribute 'σ_mass' : Real = 0.28909372274994966;
                                attribute Cx : Real = 92.03539369627833;
                                attribute 'σ_Cx' : Real = 28.721044428837228;
                                attribute Cy : Real = 59.25218351185322;
                                attribute 'σ_Cy' : Real = 28.23690002309109;
                                attribute Cz : Real = 6.988506857305765;
                                attribute 'σ_Cz' : Real = 29.057750463592832;
                                attribute Ixx : Real = 0.044401768379264066;
                                attribute 'σ_Ixx' : Real = 0.37074144170588635;
                                attribute Iyy : Real = 0.04714700625441354;
                                attribute 'σ_Iyy' : Real = 0.3723953238821935;
                                attribute Izz : Real = 0.04463445237186242;
                                attribute 'σ_Izz' : Real = 0.37017423652493897;
                                attribute Ixy : Real = -0.00249347545891977;
                                attribute 'σ_Ixy' : Real = 0.02351283871158888;
                                attribute Ixz : Real = -0.001406768059127789;
                                attribute 'σ_Ixz' : Real = 0.022566176940390956;
                                attribute Iyz : Real = -0.002809141600363138;
                                attribute 'σ_Iyz' : Real = 0.02209918015384651;
                            }
                        }
                    }
                }
                part <'C.1.2.1.4'> 'Subsystem 19' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.2.1.4.1'> 'Assembly 70' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.4.1.1'> 'Subassembly 245' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.1.1.1'> 'Part 869' {
                                attribute POIconv : String = "+";
                                attribute Ipoint : Boolean = false;
                                attribute mass : Real = 0.27223217856604603;
                                attribute 'σ_mass' : Real = 0.28909372274994966;
                                attribute Cx : Real = 80.46283801086247;
                                attribute 'σ_Cx' : Real = 28.721044428837228;
                                attribute Cy : Real = 57.47569045051932;
                                attribute 'σ_Cy' : Real = 28.23690002309109;
                                attribute Cz : Real = -86.99930654838681;
                                attribute 'σ_Cz' : Real = 29.057750463592832;
                                attribute Ixx : Real = 0.3961942194821377;
                                attribute 'σ_Ixx' : Real = 0.37074144170588635;
                                attribute Iyy : Real = 0.34880401745538203;
                                attribute 'σ_Iyy' : Real = 0.3723953238821935;
                                attribute Izz : Real = 0.3581649715034036;
                                attribute 'σ_Izz' : Real = 0.37017423652493897;
                                attribute Ixy : Real = -0.01663236375212988;
                                attribute 'σ_Ixy' : Real = 0.02351283871158888;
                                attribute Ixz : Real = 0.027185724562474915;
                                attribute 'σ_Ixz' : Real = 0.022566176940390956;
                                attribute Iyz : Real = 0.0040272209932980165;
                                attribute 'σ_Iyz' : Real = 0.02209918015384651;
                            }
                            part <'C.1.2.1.4.1.1.2'> 'Part 870' {
                                attribute POIconv : String = "-";
                                attribute Ipoint : Boolean = false;
                                attribute mass : Real = 0.8327855869045016;
                                attribute 'σ_mass' : Real = 0.28909372274994966;
                                attribute Cx : Real = 51.206410210579634;
                                attribute 'σ_Cx' : Real = 28.721044428837228;
                                attribute Cy : Real = 87.50078310258687;
                                attribute 'σ_Cy' : Real = 28.23690002309109;
                                attribute Cz : Real = 62.32571257278323;
                                attribute 'σ_Cz' : Real = 29.057750463592832;
                                attribute Ixx : Real = 1.0072639413371467;
                                attribute 'σ_Ixx' : Real = 0.37074144170588635;
                                attribute Iyy : Real = 0.9020600361509343;
                                attribute 'σ_Iyy' : Real = 0.3723953238821935;
                                attribute Izz : Real = 0.993808398604382;
                                attribute 'σ_Izz' : Real = 0.37017423652493897;
                                attribute Ixy : Real = 0.07621546486115519;
                                attribute 'σ_Ixy' : Real = 0.02351283871158888;
                                attribute Ixz : Real = -0.046705179633531935;
                                attribute 'σ_Ixz' : Real = 0.022566176940390956;
                                attribute Iyz : Real = 0.08847384438793632;
                                attribute 'σ_Iyz' : Real = 0.02209918015384651;
                            }
                        }
                        part <'C.1.2.1.4.1.2'> 'Subassembly 246' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.1.2.1'> 'Part 871' {
                                attribute POIconv : String = "-";
                                attribute Ipoint : Boolean = false;
                                attribute mass : Real = 0.2949817116728518;
                                attribute 'σ_mass' : Real = 0.28909372274994966;
                                attribute Cx : Real = 86.81539348326623;
                                attribute 'σ_Cx' : Real = 28.721044428837228;
                                attribute Cy : Real = 76.32933091372252;
                                attribute 'σ_Cy' : Real = 28.23690002309109;
                                attribute Cz : Real = 99.27633125334978;
                                attribute 'σ_Cz' : Real = 29.057750463592832;
                                attribute Ixx : Real = 0.34408543131221214;
                                attribute 'σ_Ixx' : Real = 0.37074144170588635;
                                attribute Iyy : Real = 0.4071461575395191;
                                attribute 'σ_Iyy' : Real = 0.3723953238821935;
                                attribute Izz : Real = 0.35501415697126604;
                                attribute 'σ_Izz' : Real = 0.37017423652493897;
                                attribute Ixy : Real = 0.0134424292994893;
                                attribute 'σ_Ixy' : Real = 0.02351283871158888;
                                attribute Ixz : Real = -0.0034219645196100993;
                                attribute 'σ_Ixz' : Real = 0.022566176940390956;
                                attribute Iyz : Real = -0.01589020465438252;
                                attribute 'σ_Iyz' : Real = 0.02209918015384651;
                            }
                            part <'C.1.2.1.4.1.2.2'> 'Part 872' {
                                attribute POIconv : String = "+";
                                attribute Ipoint : Boolean = false;
                                attribute mass : Real = 0.7826816371108871;
                                attribute 'σ_mass' : Real = 0.28909372274994966;
                                attribute Cx : Real = -56.27164328470826;
                                attribute 'σ_Cx' : Real = 28.721044428837228;
                                attribute Cy : Real = 91.53945492580533;
                                attribute 'σ_Cy' : Real = 28.23690002309109;
                                attribute Cz : Real = 24.067642632871866;
                                attribute 'σ_Cz' : Real = 29.057750463592832;
                                attribute Ixx : Real = 0.9778478964809706;
                                attribute 'σ_Ixx' : Real = 0.37074144170588635;
                                attribute Iyy : Real = 0.9496995845322196;
                                attribute 'σ_Iyy' : Real = 0.3723953238821935;
                                attribute Izz : Real = 0.6957101008845437;
                                attribute 'σ_Izz' : Real = 0.37017423652493897;
                                attribute Ixy : Real = 0.0023040540404262056;
                                attribute 'σ_Ixy' : Real = 0.02351283871158888;
                                attribute Ixz : Real = 0.039310745442766484;
                                attribute 'σ_Ixz' : Real = 0.022566176940390956;
                                attribute Iyz : Real = 0.01361643285858351;
                                attribute 'σ_Iyz' : Real = 0.02209918015384651;
                            }
                            part <'C.1.2.1.4.1.2.3'> 'Part 873' {
                                attribute POIconv : String = "+";
                                attribute Ipoint : Boolean = false;
                                attribute mass : Real = 0.6386355466933455;
                                attribute 'σ_mass' : Real = 0.28909372274994966;
                                attribute Cx : Real = 12.498214095830917;
                                attribute 'σ_Cx' : Real = 28.721044428837228;
                                attribute Cy : Real = -5.787724442780018;
                                attribute 'σ_Cy' : Real = 28.23690002309109;
                                attribute Cz : Real = -5.697828670963645;
                                attribute 'σ_Cz' : Real = 29.057750463592832;
                                attribute Ixx : Real = 0.8671067831517091;
                                attribute 'σ_Ixx' : Real = 0.37074144170588635;
                                attribute Iyy : Real = 0.9959601496049392;
                                attribute 'σ_Iyy' : Real = 0.3723953238821935;
                                attribute Izz : Real = 0.8581832902650786;
                                attribute 'σ_Izz' : Real = 0.37017423652493897;
                                attribute Ixy : Real = -0.02616752523860597;
                                attribute 'σ_Ixy' : Real = 0.02351283871158888;
                                attribute Ixz : Real = 4.076729359052414e-4;
                                attribute 'σ_Ixz' : Real = 0.022566176940390956;
                                attribute Iyz : Real = 0.0019840933129517506;
                                attribute 'σ_Iyz' : Real = 0.02209918015384651;
                            }
                        }
                        part <'C.1.2.1.4.1.3'> 'Subassembly 247' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.1.3.1'> 'Part 874' {
                                attribute POIconv : String = "+";
                                attribute Ipoint : Boolean = false;
                                attribute mass : Real = 0.9408222606582567;
                                attribute 'σ_mass' : Real = 0.28909372274994966;
                                attribute Cx : Real = -82.05497930757701;
                                attribute 'σ_Cx' : Real = 28.721044428837228;
                                attribute Cy : Real = 21.43986476585269;
                                attribute 'σ_Cy' : Real = 28.23690002309109;
                                attribute Cz : Real = 23.9314301405102;
                                attribute 'σ_Cz' : Real = 29.057750463592832;
                                attribute Ixx : Real = 1.3638283437191279;
                                attribute 'σ_Ixx' : Real = 0.37074144170588635;
                                attribute Iyy : Real = 1.2896698188481333;
                                attribute 'σ_Iyy' : Real = 0.3723953238821935;
                                attribute Izz : Real = 1.1927794239794551;
                                attribute 'σ_Izz' : Real = 0.37017423652493897;
                                attribute Ixy : Real = -0.08440370084619134;
                                attribute 'σ_Ixy' : Real = 0.02351283871158888;
                                attribute Ixz : Real = -0.0765637423114574;
                                attribute 'σ_Ixz' : Real = 0.022566176940390956;
                                attribute Iyz : Real = -0.03919185966259717;
                                attribute 'σ_Iyz' : Real = 0.02209918015384651;
                            }
                            part <'C.1.2.1.4.1.3.2'> 'Part 875' {
                                attribute POIconv : String = "-";
                                attribute Ipoint : Boolean = false;
                                attribute mass : Real = 0.6573671267961617;
                                attribute 'σ_mass' : Real = 0.28909372274994966;
                                attribute Cx : Real = -43.227718537673354;
                                attribute 'σ_Cx' : Real = 28.721044428837228;
                                attribute Cy : Real = -6.98245270177722;
                                attribute 'σ_Cy' : Real = 28.23690002309109;
                                attribute Cz : Real = 50.39826179854572;
                                attribute 'σ_Cz' : Real = 29.057750463592832;
                                attribute Ixx : Real = 0.844242415430575;
                                attribute 'σ_Ixx' : Real = 0.37074144170588635;
                                attribute Iyy : Real = 0.8904826876670747;
                                attribute 'σ_Iyy' : Real = 0.3723953238821935;
                                attribute Izz : Real = 0.8357265737891564;
                                attribute 'σ_Izz' : Real = 0.37017423652493897;
                                attribute Ixy : Real = -0.056719963109132895;
                                attribute 'σ_Ixy' : Real = 0.02351283871158888;
                                attribute Ixz : Real = 0.004520140436816887;
                                attribute 'σ_Ixz' : Real = 0.022566176940390956;
                                attribute Iyz : Real = 0.07768755813589966;
                                attribute 'σ_Iyz' : Real = 0.02209918015384651;
                            }
                        }
                    }
                    part <'C.1.2.1.4.2'> 'Assembly 71' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.4.2.1'> 'Subassembly 248' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.2.1.1'> 'Part 876' {
                                attribute POIconv : String = "-";
                                attribute Ipoint : Boolean = false;
                                attribute mass : Real = 0.3450348290752154;
                                attribute 'σ_mass' : Real = 0.28909372274994966;
                                attribute Cx : Real = 26.07601834461093;
                                attribute 'σ_Cx' : Real = 28.721044428837228;
                                attribute Cy : Real = -48.367415415123105;
                                attribute 'σ_Cy' : Real = 28.23690002309109;
                                attribute Cz : Real = -55.055674351751804;
                                attribute 'σ_Cz' : Real = 29.057750463592832;
                                attribute Ixx : Real = 0.40830853274365597;
                                attribute 'σ_Ixx' : Real = 0.37074144170588635;
                                attribute Iyy : Real = 0.40658366946626634;
                                attribute 'σ_Iyy' : Real = 0.3723953238821935;
                                attribute Izz : Real = 0.5182531799146531;
                                attribute 'σ_Izz' : Real = 0.37017423652493897;
                                attribute Ixy : Real = -4.167074262375955e-4;
                                attribute 'σ_Ixy' : Real = 0.02351283871158888;
                                attribute Ixz : Real = -0.013953812759018238;
                                attribute 'σ_Ixz' : Real = 0.022566176940390956;
                                attribute Iyz : Real = 0.003962769157415912;
                                attribute 'σ_Iyz' : Real = 0.02209918015384651;
                            }
                            part <'C.1.2.1.4.2.1.2'> 'Part 877' {
                                attribute POIconv : String = "+";
                                attribute Ipoint : Boolean = false;
                                attribute mass : Real = 0.9683599509310443;
                                attribute 'σ_mass' : Real = 0.28909372274994966;
                                attribute Cx : Real = -48.36346236988902;
                                attribute 'σ_Cx' : Real = 28.721044428837228;
                                attribute Cy : Real = -5.667475052177906;
                                attribute 'σ_Cy' : Real = 28.23690002309109;
                                attribute Cz : Real = 33.29205485060811;
                                attribute 'σ_Cz' : Real = 29.057750463592832;
                                attribute Ixx : Real = 1.3096615421195466;
                                attribute 'σ_Ixx' : Real = 0.37074144170588635;
                                attribute Iyy : Real = 1.3522068302386205;
                                attribute 'σ_Iyy' : Real = 0.3723953238821935;
                                attribute Izz : Real = 1.3870068925175236;
                                attribute 'σ_Izz' : Real = 0.37017423652493897;
                                attribute Ixy : Real = 0.007844667177271513;
                                attribute 'σ_Ixy' : Real = 0.02351283871158888;
                                attribute Ixz : Real = -0.04817599092855786;
                                attribute 'σ_Ixz' : Real = 0.022566176940390956;
                                attribute Iyz : Real = -0.023319006418379376;
                                attribute 'σ_Iyz' : Real = 0.02209918015384651;
                            }
                        }
                        part <'C.1.2.1.4.2.2'> 'Subassembly 249' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.2.2.1'> 'Part 878' {
                                attribute POIconv : String = "+";
                                attribute Ipoint : Boolean = false;
                                attribute mass : Real = 0.32665915898117237;
                                attribute 'σ_mass' : Real = 0.28909372274994966;
                                attribute Cx : Real = 59.33857928030193;
                                attribute 'σ_Cx' : Real = 28.721044428837228;
                                attribute Cy : Real = 75.91856541112065;
                                attribute 'σ_Cy' : Real = 28.23690002309109;
                                attribute Cz : Real = 58.514846256002784;
                                attribute 'σ_Cz' : Real = 29.057750463592832;
                                attribute Ixx : Real = 0.32790540412752905;
                                attribute 'σ_Ixx' : Real = 0.37074144170588635;
                                attribute Iyy : Real = 0.3886392247945744;
                                attribute 'σ_Iyy' : Real = 0.3723953238821935;
                                attribute Izz : Real = 0.39209893694157205;
                                attribute 'σ_Izz' : Real = 0.37017423652493897;
                                attribute Ixy : Real = 0.02817494455285071;
                                attribute 'σ_Ixy' : Real = 0.02351283871158888;
                                attribute Ixz : Real = 0.032126219191795966;
                                attribute 'σ_Ixz' : Real = 0.022566176940390956;
                                attribute Iyz : Real = 0.0047057567483918625;
                                attribute 'σ_Iyz' : Real = 0.02209918015384651;
                            }
                            part <'C.1.2.1.4.2.2.2'> 'Part 879' {
                                attribute POIconv : String = "+";
                                attribute Ipoint : Boolean = false;
                                attribute mass : Real = 0.1723956700002309;
                                attribute 'σ_mass' : Real = 0.28909372274994966;
                                attribute Cx : Real = 34.508997248485684;
                                attribute 'σ_Cx' : Real = 28.721044428837228;
                                attribute Cy : Real = -12.193138571456075;
                                attribute 'σ_Cy' : Real = 28.23690002309109;
                                attribute Cz : Real = 21.78624365478754;
                                attribute 'σ_Cz' : Real = 29.057750463592832;
                                attribute Ixx : Real = 0.2364483067339139;
                                attribute 'σ_Ixx' : Real = 0.37074144170588635;
                                attribute Iyy : Real = 0.2300038769012629;
                                attribute 'σ_Iyy' : Real = 0.3723953238821935;
                                attribute Izz : Real = 0.19061696205901213;
                                attribute 'σ_Izz' : Real = 0.37017423652493897;
                                attribute Ixy : Real = -0.01936783134201921;
                                attribute 'σ_Ixy' : Real = 0.02351283871158888;
                                attribute Ixz : Real = 0.0015651232361137085;
                                attribute 'σ_Ixz' : Real = 0.022566176940390956;
                                attribute Iyz : Real = -0.00505840643941757;
                                attribute 'σ_Iyz' : Real = 0.02209918015384651;
                            }
                            part <'C.1.2.1.4.2.2.3'> 'Part 880' {
                                attribute POIconv : String = "-";
                                attribute Ipoint : Boolean = false;
                                attribute mass : Real = 0.49579794705542735;
                                attribute 'σ_mass' : Real = 0.28909372274994966;
                                attribute Cx : Real = -96.14929696545005;
                                attribute 'σ_Cx' : Real = 28.721044428837228;
                                attribute Cy : Real = -62.139587150886655;
                                attribute 'σ_Cy' : Real = 28.23690002309109;
                                attribute Cz : Real = -77.74973716586828;
                                attribute 'σ_Cz' : Real = 29.057750463592832;
                                attribute Ixx : Real = 0.5187867401552515;
                                attribute 'σ_Ixx' : Real = 0.37074144170588635;
                                attribute Iyy : Real = 0.6038550697233149;
                                attribute 'σ_Iyy' : Real = 0.3723953238821935;
                                attribute Izz : Real = 0.517129027971741;
                                attribute 'σ_Izz' : Real = 0.37017423652493897;
                                attribute Ixy : Real = -0.023769010484124015;
                                attribute 'σ_Ixy' : Real = 0.02351283871158888;
                                attribute Ixz : Real = 0.0021216731298101497;
                                attribute 'σ_Ixz' : Real = 0.022566176940390956;
                                attribute Iyz : Real = -3.7679636179241253e-4;
                                attribute 'σ_Iyz' : Real = 0.02209918015384651;
                            }
                            part <'C.1.2.1.4.2.2.4'> 'Part 881' {
                                attribute POIconv : String = "-";
                                attribute Ipoint : Boolean = false;
                                attribute mass : Real = 0.5065603755596094;
                                attribute 'σ_mass' : Real = 0.28909372274994966;
                                attribute Cx : Real = -38.02535077556968;
                                attribute 'σ_Cx' : Real = 28.721044428837228;
                                attribute Cy : Real = -1.133557641878724;
                                attribute 'σ_Cy' : Real = 28.23690002309109;
                                attribute Cz : Real = -88.88060031458735;
                                attribute 'σ_Cz' : Real = 29.057750463592832;
                                attribute Ixx : Real = 0.5506132929822533;
                                attribute 'σ_Ixx' : Real = 0.37074144170588635;
                                attribute Iyy : Real = 0.49463721108655295;
                                attribute 'σ_Iyy' : Real = 0.3723953238821935;
                                attribute Izz : Real = 0.5082754194049325;
                                attribute 'σ_Izz' : Real = 0.37017423652493897;
                                attribute Ixy : Real = -0.022121695050827107;
                                attribute 'σ_Ixy' : Real = 0.02351283871158888;
                                attribute Ixz : Real = -0.008213365103601874;
                                attribute 'σ_Ixz' : Real = 0.022566176940390956;
                                attribute Iyz : Real = -0.009709987028756221;
                                attribute 'σ_Iyz' : Real = 0.02209918015384651;
                            }
                        }
                        part <'C.1.2.1.4.2.3'> 'Subassembly 250' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.2.3.1'> 'Part 882' {
                                attribute POIconv : String = "-";
                                attribute Ipoint : Boolean = false;
                                attribute mass : Real = 0.050590304508339616;
                                attribute 'σ_mass' : Real = 0.28909372274994966;
                                attribute Cx : Real = 62.426201067864895;
                                attribute 'σ_Cx' : Real = 28.721044428837228;
                                attribute Cy : Real = -50.291696889325976;
                                attribute 'σ_Cy' : Real = 28.23690002309109;
                                attribute Cz : Real = 50.19796080887318;
                                attribute 'σ_Cz' : Real = 29.057750463592832;
                                attribute Ixx : Real = 0.06874078058828009;
                                attribute 'σ_Ixx' : Real = 0.37074144170588635;
                                attribute Iyy : Real = 0.06490268322578027;
                                attribute 'σ_Iyy' : Real = 0.3723953238821935;
                                attribute Izz : Real = 0.07600627149522667;
                                attribute 'σ_Izz' : Real = 0.37017423652493897;
                                attribute Ixy : Real = -8.540706664279351e-4;
                                attribute 'σ_Ixy' : Real = 0.02351283871158888;
                                attribute Ixz : Real = -0.0023882023017479316;
                                attribute 'σ_Ixz' : Real = 0.022566176940390956;
                                attribute Iyz : Real = 4.652158540353906e-4;
                                attribute 'σ_Iyz' : Real = 0.02209918015384651;
                            }
                            part <'C.1.2.1.4.2.3.2'> 'Part 883' {
                                attribute POIconv : String = "+";
                                attribute Ipoint : Boolean = false;
                                attribute mass : Real = 0.5100211774855852;
                                attribute 'σ_mass' : Real = 0.28909372274994966;
                                attribute Cx : Real = 80.02120340242982;
                                attribute 'σ_Cx' : Real = 28.721044428837228;
                                attribute Cy : Real = 5.123272677883506;
                                attribute 'σ_Cy' : Real = 28.23690002309109;
                                attribute Cz : Real = 25.464348448440433;
                                attribute 'σ_Cz' : Real = 29.057750463592832;
                                attribute Ixx : Real = 0.8123473071364197;
                                attribute 'σ_Ixx' : Real = 0.37074144170588635;
                                attribute Iyy : Real = 0.7761243942042328;
                                attribute 'σ_Iyy' : Real = 0.3723953238821935;
                                attribute Izz : Real = 0.8058108417780543;
                                attribute 'σ_Izz' : Real = 0.37017423652493897;
                                attribute Ixy : Real = -0.011232746683602125;
                                attribute 'σ_Ixy' : Real = 0.02351283871158888;
                                attribute Ixz : Real = 0.030361710838555822;
                                attribute 'σ_Ixz' : Real = 0.022566176940390956;
                                attribute Iyz : Real = 0.006308870912483725;
                                attribute 'σ_Iyz' : Real = 0.02209918015384651;
                            }
                            part <'C.1.2.1.4.2.3.3'> 'Part 884' {
                                attribute POIconv : String = "+";
                                attribute Ipoint : Boolean = false;
                                attribute mass : Real = 0.2998657077439129;
                                attribute 'σ_mass' : Real = 0.28909372274994966;
                                attribute Cx : Real = 64.65895618312061;
                                attribute 'σ_Cx' : Real = 28.721044428837228;
                                attribute Cy : Real = -77.45726886205375;
                                attribute 'σ_Cy' : Real = 28.23690002309109;
                                attribute Cz : Real = -25.359030766412616;
                                attribute 'σ_Cz' : Real = 29.057750463592832;
                                attribute Ixx : Real = 0.4455265326663298;
                                attribute 'σ_Ixx' : Real = 0.37074144170588635;
                                attribute Iyy : Real = 0.39840045803022395;
                                attribute 'σ_Iyy' : Real = 0.3723953238821935;
                                attribute Izz : Real = 0.4477280357967806;
                                attribute 'σ_Izz' : Real = 0.37017423652493897;
                                attribute Ixy : Real = -0.0018984741520829875;
                                attribute 'σ_Ixy' : Real = 0.02351283871158888;
                                attribute Ixz : Real = -0.0054391085791179695;
                                attribute 'σ_Ixz' : Real = 0.022566176940390956;
                                attribute Iyz : Real = -0.009097553900918872;
                                attribute 'σ_Iyz' : Real = 0.02209918015384651;
                            }
                        }
                    }
                    part <'C.1.2.1.4.3'> 'Assembly 72' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.4.3.1'> 'Subassembly 251' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.3.1.1'> 'Part 885' {
                                attribute POIconv : String = "+";
                                attribute Ipoint : Boolean = false;
                                attribute mass : Real = 0.7491437257248909;
                                attribute 'σ_mass' : Real = 0.28909372274994966;
                                attribute Cx : Real = -82.03398082405329;
                                attribute 'σ_Cx' : Real = 28.721044428837228;
                                attribute Cy : Real = 66.7016813531518;
                                attribute 'σ_Cy' : Real = 28.23690002309109;
                                attribute Cz : Real = -32.23336827941239;
                                attribute 'σ_Cz' : Real = 29.057750463592832;
                                attribute Ixx : Real = 0.9855565016923363;
                                attribute 'σ_Ixx' : Real = 0.37074144170588635;
                                attribute Iyy : Real = 0.9921624877944623;
                                attribute 'σ_Iyy' : Real = 0.3723953238821935;
                                attribute Izz : Real = 0.9669671789260723;
                                attribute 'σ_Izz' : Real = 0.37017423652493897;
                                attribute Ixy : Real = -0.003268591755477613;
                                attribute 'σ_Ixy' : Real = 0.02351283871158888;
                                attribute Ixz : Real = 0.0013095174335343777;
                                attribute 'σ_Ixz' : Real = 0.022566176940390956;
                                attribute Iyz : Real = 8.691981100164805e-4;
                                attribute 'σ_Iyz' : Real = 0.02209918015384651;
                            }
                            part <'C.1.2.1.4.3.1.2'> 'Part 886' {
                                attribute POIconv : String = "+";
                                attribute Ipoint : Boolean = false;
                                attribute mass : Real = 0.6998283636940178;
                                attribute 'σ_mass' : Real = 0.28909372274994966;
                                attribute Cx : Real = -36.004902655258775;
                                attribute 'σ_Cx' : Real = 28.721044428837228;
                                attribute Cy : Real = 18.71897391974926;
                                attribute 'σ_Cy' : Real = 28.23690002309109;
                                attribute Cz : Real = 57.644529454410076;
                                attribute 'σ_Cz' : Real = 29.057750463592832;
                                attribute Ixx : Real = 0.9282714449993907;
                                attribute 'σ_Ixx' : Real = 0.37074144170588635;
                                attribute Iyy : Real = 1.021879984634578;
                                attribute 'σ_Iyy' : Real = 0.3723953238821935;
                                attribute Izz : Real = 1.0571767025242786;
                                attribute 'σ_Izz' : Real = 0.37017423652493897;
                                attribute Ixy : Real = 0.007263574339031811;
                                attribute 'σ_Ixy' : Real = 0.02351283871158888;
                                attribute Ixz : Real = 0.009131728147379236;
                                attribute 'σ_Ixz' : Real = 0.022566176940390956;
                                attribute Iyz : Real = 0.001446424153335739;
                                attribute 'σ_Iyz' : Real = 0.02209918015384651;
                            }
                        }
                        part <'C.1.2.1.4.3.2'> 'Subassembly 252' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.3.2.1'> 'Part 887' {
                                attribute POIconv : String = "-";
                                attribute Ipoint : Boolean = false;
                                attribute mass : Real = 0.10775876299384982;
                                attribute 'σ_mass' : Real = 0.28909372274994966;
                                attribute Cx : Real = -58.45392211340368;
                                attribute 'σ_Cx' : Real = 28.721044428837228;
                                attribute Cy : Real = 45.44548690319061;
                                attribute 'σ_Cy' : Real = 28.23690002309109;
                                attribute Cz : Real = 15.222681732848287;
                                attribute 'σ_Cz' : Real = 29.057750463592832;
                                attribute Ixx : Real = 0.14406637367684322;
                                attribute 'σ_Ixx' : Real = 0.37074144170588635;
                                attribute Iyy : Real = 0.14100496678242813;
                                attribute 'σ_Iyy' : Real = 0.3723953238821935;
                                attribute Izz : Real = 0.15616785894719315;
                                attribute 'σ_Izz' : Real = 0.37017423652493897;
                                attribute Ixy : Real = 0.00547566011066585;
                                attribute 'σ_Ixy' : Real = 0.02351283871158888;
                                attribute Ixz : Real = 0.00559854859800277;
                                attribute 'σ_Ixz' : Real = 0.022566176940390956;
                                attribute Iyz : Real = -0.0069062261422062066;
                                attribute 'σ_Iyz' : Real = 0.02209918015384651;
                            }
                            part <'C.1.2.1.4.3.2.2'> 'Part 888' {
                                attribute POIconv : String = "+";
                                attribute Ipoint : Boolean = false;
                                attribute mass : Real = 0.865055982094258;
                                attribute 'σ_mass' : Real = 0.28909372274994966;
                                attribute Cx : Real = -44.30886339396238;
                                attribute 'σ_Cx' : Real = 28.721044428837228;
                                attribute Cy : Real = -53.615461522713304;
                                attribute 'σ_Cy' : Real = 28.23690002309109;
                                attribute Cz : Real = 42.18867253512144;
                                attribute 'σ_Cz' : Real = 29.057750463592832;
                                attribute Ixx : Real = 0.9418215373310636;
                                attribute 'σ_Ixx' : Real = 0.37074144170588635;
                                attribute Iyy : Real = 0.7608142694735102;
                                attribute 'σ_Iyy' : Real = 0.3723953238821935;
                                attribute Izz : Real = 0.922507610945533;
                                attribute 'σ_Izz' : Real = 0.37017423652493897;
                                attribute Ixy : Real = 0.003954190996576758;
                                attribute 'σ_Ixy' : Real = 0.02351283871158888;
                                attribute Ixz : Real = -0.0070787821950095;
                                attribute 'σ_Ixz' : Real = 0.022566176940390956;
                                attribute Iyz : Real = 0.04187183472708235;
                                attribute 'σ_Iyz' : Real = 0.02209918015384651;
                            }
                            part <'C.1.2.1.4.3.2.3'> 'Part 889' {
                                attribute POIconv : String = "+";
                                attribute Ipoint : Boolean = false;
                                attribute mass : Real = 0.3976534101071302;
                                attribute 'σ_mass' : Real = 0.28909372274994966;
                                attribute Cx : Real = -51.677533937618136;
                                attribute 'σ_Cx' : Real = 28.721044428837228;
                                attribute Cy : Real = -73.42608482576907;
                                attribute 'σ_Cy' : Real = 28.23690002309109;
                                attribute Cz : Real = 67.81320073641837;
                                attribute 'σ_Cz' : Real = 29.057750463592832;
                                attribute Ixx : Real = 0.5600971354308069;
                                attribute 'σ_Ixx' : Real = 0.37074144170588635;
                                attribute Iyy : Real = 0.5396715266257596;
                                attribute 'σ_Iyy' : Real = 0.3723953238821935;
                                attribute Izz : Real = 0.4744866499202376;
                                attribute 'σ_Izz' : Real = 0.37017423652493897;
                                attribute Ixy : Real = 0.007534120957154927;
                                attribute 'σ_Ixy' : Real = 0.02351283871158888;
                                attribute Ixz : Real = -0.017460491659828672;
                                attribute 'σ_Ixz' : Real = 0.022566176940390956;
                                attribute Iyz : Real = 0.033087381637155536;
                                attribute 'σ_Iyz' : Real = 0.02209918015384651;
                            }
                            part <'C.1.2.1.4.3.2.4'> 'Part 890' {
                                attribute POIconv : String = "-";
                                attribute Ipoint : Boolean = false;
                                attribute mass : Real = 0.555115302071441;
                                attribute 'σ_mass' : Real = 0.28909372274994966;
                                attribute Cx : Real = 61.39585142955184;
                                attribute 'σ_Cx' : Real = 28.721044428837228;
                                attribute Cy : Real = 64.13843552581966;
                                attribute 'σ_Cy' : Real = 28.23690002309109;
                                attribute Cz : Real = -77.88812830112875;
                                attribute 'σ_Cz' : Real = 29.057750463592832;
                                attribute Ixx : Real = 0.6611942778411626;
                                attribute 'σ_Ixx' : Real = 0.37074144170588635;
                                attribute Iyy : Real = 0.6738151119641261;
                                attribute 'σ_Iyy' : Real = 0.3723953238821935;
                                attribute Izz : Real = 0.7929114094951272;
                                attribute 'σ_Izz' : Real = 0.37017423652493897;
                                attribute Ixy : Real = -5.09362731094902e-4;
                                attribute 'σ_Ixy' : Real = 0.02351283871158888;
                                attribute Ixz : Real = 0.0057383556083115995;
                                attribute 'σ_Ixz' : Real = 0.022566176940390956;
                                attribute Iyz : Real = -0.04000901188237635;
                                attribute 'σ_Iyz' : Real = 0.02209918015384651;
                            }
                            part <'C.1.2.1.4.3.2.5'> 'Part 891' {
                                attribute POIconv : String = "-";
                                attribute Ipoint : Boolean = false;
                                attribute mass : Real = 0.6058797412668355;
                                attribute 'σ_mass' : Real = 0.28909372274994966;
                                attribute Cx : Real = 85.72617047466338;
                                attribute 'σ_Cx' : Real = 28.721044428837228;
                                attribute Cy : Real = 22.597145475447178;
                                attribute 'σ_Cy' : Real = 28.23690002309109;
                                attribute Cz : Real = -39.75072959437966;
                                attribute 'σ_Cz' : Real = 29.057750463592832;
                                attribute Ixx : Real = 0.7779372659849757;
                                attribute 'σ_Ixx' : Real = 0.37074144170588635;
                                attribute Iyy : Real = 0.842547680294552;
                                attribute 'σ_Iyy' : Real = 0.3723953238821935;
                                attribute Izz : Real = 0.7815172456056424;
                                attribute 'σ_Izz' : Real = 0.37017423652493897;
                                attribute Ixy : Real = 0.06006724028695434;
                                attribute 'σ_Ixy' : Real = 0.02351283871158888;
                                attribute Ixz : Real = 0.03884631353718987;
                                attribute 'σ_Ixz' : Real = 0.022566176940390956;
                                attribute Iyz : Real = 0.06444937135160092;
                                attribute 'σ_Iyz' : Real = 0.02209918015384651;
                            }
                        }
                    }
                    part <'C.1.2.1.4.4'> 'Assembly 73' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.4.4.1'> 'Subassembly 253' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.4.1.1'> 'Part 892' {
                                attribute POIconv : String = "+";
                                attribute Ipoint : Boolean = false;
                                attribute mass : Real = 0.9839543643093203;
                                attribute 'σ_mass' : Real = 0.28909372274994966;
                                attribute Cx : Real = -8.969714026898146;
                                attribute 'σ_Cx' : Real = 28.721044428837228;
                                attribute Cy : Real = 3.772946447134018;
                                attribute 'σ_Cy' : Real = 28.23690002309109;
                                attribute Cz : Real = -95.32698071561754;
                                attribute 'σ_Cz' : Real = 29.057750463592832;
                                attribute Ixx : Real = 1.0476112449192303;
                                attribute 'σ_Ixx' : Real = 0.37074144170588635;
                                attribute Iyy : Real = 1.0957999013834414;
                                attribute 'σ_Iyy' : Real = 0.3723953238821935;
                                attribute Izz : Real = 1.1519422399144252;
                                attribute 'σ_Izz' : Real = 0.37017423652493897;
                                attribute Ixy : Real = 0.004691518554134694;
                                attribute 'σ_Ixy' : Real = 0.02351283871158888;
                                attribute Ixz : Real = -0.009787090024304276;
                                attribute 'σ_Ixz' : Real = 0.022566176940390956;
                                attribute Iyz : Real = -0.03499389460194705;
                                attribute 'σ_Iyz' : Real = 0.02209918015384651;
                            }
                            part <'C.1.2.1.4.4.1.2'> 'Part 893' {
                                attribute POIconv : String = "-";
                                attribute Ipoint : Boolean = false;
                                attribute mass : Real = 0.9674728149638977;
                                attribute 'σ_mass' : Real = 0.28909372274994966;
                                attribute Cx : Real = -34.53551633283496;
                                attribute 'σ_Cx' : Real = 28.721044428837228;
                                attribute Cy : Real = 48.11259317211807;
                                attribute 'σ_Cy' : Real = 28.23690002309109;
                                attribute Cz : Real = 20.308606885373592;
                                attribute 'σ_Cz' : Real = 29.057750463592832;
                                attribute Ixx : Real = 1.298959936817941;
                                attribute 'σ_Ixx' : Real = 0.37074144170588635;
                                attribute Iyy : Real = 1.1970174149185824;
                                attribute 'σ_Iyy' : Real = 0.3723953238821935;
                                attribute Izz : Real = 1.2442993808244205;
                                attribute 'σ_Izz' : Real = 0.37017423652493897;
                                attribute Ixy : Real = 0.0010835452257832892;
                                attribute 'σ_Ixy' : Real = 0.02351283871158888;
                                attribute Ixz : Real = 0.01743985679662994;
                                attribute 'σ_Ixz' : Real = 0.022566176940390956;
                                attribute Iyz : Real = -0.049229822046473096;
                                attribute 'σ_Iyz' : Real = 0.02209918015384651;
                            }
                            part <'C.1.2.1.4.4.1.3'> 'Part 894' {
                                attribute POIconv : String = "-";
                                attribute Ipoint : Boolean = false;
                                attribute mass : Real = 0.4150230034815613;
                                attribute 'σ_mass' : Real = 0.28909372274994966;
                                attribute Cx : Real = -87.33480595983565;
                                attribute 'σ_Cx' : Real = 28.721044428837228;
                                attribute Cy : Real = 65.438820887357;
                                attribute 'σ_Cy' : Real = 28.23690002309109;
                                attribute Cz : Real = 55.272462125867605;
                                attribute 'σ_Cz' : Real = 29.057750463592832;
                                attribute Ixx : Real = 0.4833654988359504;
                                attribute 'σ_Ixx' : Real = 0.37074144170588635;
                                attribute Iyy : Real = 0.4284578636487586;
                                attribute 'σ_Iyy' : Real = 0.3723953238821935;
                                attribute Izz : Real = 0.5189108504499969;
                                attribute 'σ_Izz' : Real = 0.37017423652493897;
                                attribute Ixy : Real = 0.04067450610915517;
                                attribute 'σ_Ixy' : Real = 0.02351283871158888;
                                attribute Ixz : Real = -0.0034760958638650474;
                                attribute 'σ_Ixz' : Real = 0.022566176940390956;
                                attribute Iyz : Real = 0.014641128303072837;
                                attribute 'σ_Iyz' : Real = 0.02209918015384651;
                            }
                        }
                        part <'C.1.2.1.4.4.2'> 'Subassembly 254' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.4.2.1'> 'Part 895' {
                                attribute POIconv : String = "+";
                                attribute Ipoint : Boolean = false;
                                attribute mass : Real = 0.21539932430023329;
                                attribute 'σ_mass' : Real = 0.28909372274994966;
                                attribute Cx : Real = -60.005019744858146;
                                attribute 'σ_Cx' : Real = 28.721044428837228;
                                attribute Cy : Real = -73.90226856805384;
                                attribute 'σ_Cy' : Real = 28.23690002309109;
                                attribute Cz : Real = -22.535437997430563;
                                attribute 'σ_Cz' : Real = 29.057750463592832;
                                attribute Ixx : Real = 0.28205077494830033;
                                attribute 'σ_Ixx' : Real = 0.37074144170588635;
                                attribute Iyy : Real = 0.2805262765242215;
                                attribute 'σ_Iyy' : Real = 0.3723953238821935;
                                attribute Izz : Real = 0.2682207295553417;
                                attribute 'σ_Izz' : Real = 0.37017423652493897;
                                attribute Ixy : Real = 0.0012811378256245706;
                                attribute 'σ_Ixy' : Real = 0.02351283871158888;
                                attribute Ixz : Real = 0.002118327299968095;
                                attribute 'σ_Ixz' : Real = 0.022566176940390956;
                                attribute Iyz : Real = 0.006586046086165365;
                                attribute 'σ_Iyz' : Real = 0.02209918015384651;
                            }
                            part <'C.1.2.1.4.4.2.2'> 'Part 896' {
                                attribute POIconv : String = "+";
                                attribute Ipoint : Boolean = false;
                                attribute mass : Real = 0.07367561930697411;
                                attribute 'σ_mass' : Real = 0.28909372274994966;
                                attribute Cx : Real = -5.640270933508873;
                                attribute 'σ_Cx' : Real = 28.721044428837228;
                                attribute Cy : Real = -55.06888208910823;
                                attribute 'σ_Cy' : Real = 28.23690002309109;
                                attribute Cz : Real = -69.62717603892088;
                                attribute 'σ_Cz' : Real = 29.057750463592832;
                                attribute Ixx : Real = 0.10319062508449083;
                                attribute 'σ_Ixx' : Real = 0.37074144170588635;
                                attribute Iyy : Real = 0.08460161430152588;
                                attribute 'σ_Iyy' : Real = 0.3723953238821935;
                                attribute Izz : Real = 0.08290583454514729;
                                attribute 'σ_Izz' : Real = 0.37017423652493897;
                                attribute Ixy : Real = -0.00247429462184856;
                                attribute 'σ_Ixy' : Real = 0.02351283871158888;
                                attribute Ixz : Real = -4.6761340291356647e-4;
                                attribute 'σ_Ixz' : Real = 0.022566176940390956;
                                attribute Iyz : Real = 0.0020673827736758647;
                                attribute 'σ_Iyz' : Real = 0.02209918015384651;
                            }
                        }
                        part <'C.1.2.1.4.4.3'> 'Subassembly 255' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.4.3.1'> 'Part 897' {
                                attribute POIconv : String = "-";
                                attribute Ipoint : Boolean = false;
                                attribute mass : Real = 0.18614264408056624;
                                attribute 'σ_mass' : Real = 0.28909372274994966;
                                attribute Cx : Real = 72.10570042952895;
                                attribute 'σ_Cx' : Real = 28.721044428837228;
                                attribute Cy : Real = 97.81113904900849;
                                attribute 'σ_Cy' : Real = 28.23690002309109;
                                attribute Cz : Real = -63.903958862647414;
                                attribute 'σ_Cz' : Real = 29.057750463592832;
                                attribute Ixx : Real = 0.22739184197252096;
                                attribute 'σ_Ixx' : Real = 0.37074144170588635;
                                attribute Iyy : Real = 0.22077749649485345;
                                attribute 'σ_Iyy' : Real = 0.3723953238821935;
                                attribute Izz : Real = 0.17139875844780797;
                                attribute 'σ_Izz' : Real = 0.37017423652493897;
                                attribute Ixy : Real = 1.8407312316736938e-4;
                                attribute 'σ_Ixy' : Real = 0.02351283871158888;
                                attribute Ixz : Real = 0.005989788758016578;
                                attribute 'σ_Ixz' : Real = 0.022566176940390956;
                                attribute Iyz : Real = 0.01380473445709085;
                                attribute 'σ_Iyz' : Real = 0.02209918015384651;
                            }
                            part <'C.1.2.1.4.4.3.2'> 'Part 898' {
                                attribute POIconv : String = "+";
                                attribute Ipoint : Boolean = false;
                                attribute mass : Real = 0.659777350923745;
                                attribute 'σ_mass' : Real = 0.28909372274994966;
                                attribute Cx : Real = 31.922034500166774;
                                attribute 'σ_Cx' : Real = 28.721044428837228;
                                attribute Cy : Real = 69.23373588360846;
                                attribute 'σ_Cy' : Real = 28.23690002309109;
                                attribute Cz : Real = 39.722401136532426;
                                attribute 'σ_Cz' : Real = 29.057750463592832;
                                attribute Ixx : Real = 0.8985933368900464;
                                attribute 'σ_Ixx' : Real = 0.37074144170588635;
                                attribute Iyy : Real = 0.7896529321151579;
                                attribute 'σ_Iyy' : Real = 0.3723953238821935;
                                attribute Izz : Real = 0.746699741519373;
                                attribute 'σ_Izz' : Real = 0.37017423652493897;
                                attribute Ixy : Real = 0.016804329216767125;
                                attribute 'σ_Ixy' : Real = 0.02351283871158888;
                                attribute Ixz : Real = 0.016468893058255885;
                                attribute 'σ_Ixz' : Real = 0.022566176940390956;
                                attribute Iyz : Real = -0.011405131987001174;
                                attribute 'σ_Iyz' : Real = 0.02209918015384651;
                            }
                            part <'C.1.2.1.4.4.3.3'> 'Part 899' {
                                attribute POIconv : String = "+";
                                attribute Ipoint : Boolean = false;
                                attribute mass : Real = 0.8913685550305527;
                                attribute 'σ_mass' : Real = 0.28909372274994966;
                                attribute Cx : Real = -17.91359605267644;
                                attribute 'σ_Cx' : Real = 28.721044428837228;
                                attribute Cy : Real = -19.816756481304765;
                                attribute 'σ_Cy' : Real = 28.23690002309109;
                                attribute Cz : Real = 50.54476298391819;
                                attribute 'σ_Cz' : Real = 29.057750463592832;
                                attribute Ixx : Real = 1.1596795829030486;
                                attribute 'σ_Ixx' : Real = 0.37074144170588635;
                                attribute Iyy : Real = 1.1055662569799072;
                                attribute 'σ_Iyy' : Real = 0.3723953238821935;
                                attribute Izz : Real = 1.1761322989736598;
                                attribute 'σ_Izz' : Real = 0.37017423652493897;
                                attribute Ixy : Real = 0.050428461875966245;
                                attribute 'σ_Ixy' : Real = 0.02351283871158888;
                                attribute Ixz : Real = 0.10270566284548288;
                                attribute 'σ_Ixz' : Real = 0.022566176940390956;
                                attribute Iyz : Real = -0.07918629919857945;
                                attribute 'σ_Iyz' : Real = 0.02209918015384651;
                            }
                            part <'C.1.2.1.4.4.3.4'> 'Part 900' {
                                attribute POIconv : String = "+";
                                attribute Ipoint : Boolean = false;
                                attribute mass : Real = 0.7228929672855884;
                                attribute 'σ_mass' : Real = 0.28909372274994966;
                                attribute Cx : Real = -15.475675417110324;
                                attribute 'σ_Cx' : Real = 28.721044428837228;
                                attribute Cy : Real = 6.788926990702748;
                                attribute 'σ_Cy' : Real = 28.23690002309109;
                                attribute Cz : Real = 44.040646962821484;
                                attribute 'σ_Cz' : Real = 29.057750463592832;
                                attribute Ixx : Real = 1.1257810632924674;
                                attribute 'σ_Ixx' : Real = 0.37074144170588635;
                                attribute Iyy : Real = 1.0887673715194335;
                                attribute 'σ_Iyy' : Real = 0.3723953238821935;
                                attribute Izz : Real = 1.10291969637122;
                                attribute 'σ_Izz' : Real = 0.37017423652493897;
                                attribute Ixy : Real = -0.009399960292215643;
                                attribute 'σ_Ixy' : Real = 0.02351283871158888;
                                attribute Ixz : Real = 0.004075911691954967;
                                attribute 'σ_Ixz' : Real = 0.022566176940390956;
                                attribute Iyz : Real = -0.01451089432710169;
                                attribute 'σ_Iyz' : Real = 0.02209918015384651;
                            }
                            part <'C.1.2.1.4.4.3.5'> 'Part 901' {
                                attribute POIconv : String = "+";
                                attribute Ipoint : Boolean = false;
                                attribute mass : Real = 0.8402870817596558;
                                attribute 'σ_mass' : Real = 0.28909372274994966;
                                attribute Cx : Real = 99.09817320294678;
                                attribute 'σ_Cx' : Real = 28.721044428837228;
                                attribute Cy : Real = -37.684794375672936;
                                attribute 'σ_Cy' : Real = 28.23690002309109;
                                attribute Cz : Real = 91.3101399783045;
                                attribute 'σ_Cz' : Real = 29.057750463592832;
                                attribute Ixx : Real = 1.0499494222789698;
                                attribute 'σ_Ixx' : Real = 0.37074144170588635;
                                attribute Iyy : Real = 1.0311288766198201;
                                attribute 'σ_Iyy' : Real = 0.3723953238821935;
                                attribute Izz : Real = 0.9452527494790259;
                                attribute 'σ_Izz' : Real = 0.37017423652493897;
                                attribute Ixy : Real = 0.01649123168632765;
                                attribute 'σ_Ixy' : Real = 0.02351283871158888;
                                attribute Ixz : Real = 0.0875617034375826;
                                attribute 'σ_Ixz' : Real = 0.022566176940390956;
                                attribute Iyz : Real = 0.060795154040447816;
                                attribute 'σ_Iyz' : Real = 0.02209918015384651;
                            }
                        }
                    }
                    part <'C.1.2.1.4.5'> 'Assembly 74' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.1.4.5.1'> 'Subassembly 256' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.5.1.1'> 'Part 902' {
                                attribute POIconv : String = "-";
                                attribute Ipoint : Boolean = false;
                                attribute mass : Real = 0.16321988468291238;
                                attribute 'σ_mass' : Real = 0.28909372274994966;
                                attribute Cx : Real = 35.74164588935673;
                                attribute 'σ_Cx' : Real = 28.721044428837228;
                                attribute Cy : Real = -44.9633308686316;
                                attribute 'σ_Cy' : Real = 28.23690002309109;
                                attribute Cz : Real = 36.01789614185691;
                                attribute 'σ_Cz' : Real = 29.057750463592832;
                                attribute Ixx : Real = 0.22734708184046687;
                                attribute 'σ_Ixx' : Real = 0.37074144170588635;
                                attribute Iyy : Real = 0.2076190436766494;
                                attribute 'σ_Iyy' : Real = 0.3723953238821935;
                                attribute Izz : Real = 0.23427637492602166;
                                attribute 'σ_Izz' : Real = 0.37017423652493897;
                                attribute Ixy : Real = -0.009973224396861505;
                                attribute 'σ_Ixy' : Real = 0.02351283871158888;
                                attribute Ixz : Real = 0.003016754044513954;
                                attribute 'σ_Ixz' : Real = 0.022566176940390956;
                                attribute Iyz : Real = -0.006980194161737406;
                                attribute 'σ_Iyz' : Real = 0.02209918015384651;
                            }
                            part <'C.1.2.1.4.5.1.2'> 'Part 903' {
                                attribute POIconv : String = "-";
                                attribute Ipoint : Boolean = false;
                                attribute mass : Real = 0.03630846361606382;
                                attribute 'σ_mass' : Real = 0.28909372274994966;
                                attribute Cx : Real = 18.450580164790154;
                                attribute 'σ_Cx' : Real = 28.721044428837228;
                                attribute Cy : Real = 49.28942285478115;
                                attribute 'σ_Cy' : Real = 28.23690002309109;
                                attribute Cz : Real = -47.71031131967902;
                                attribute 'σ_Cz' : Real = 29.057750463592832;
                                attribute Ixx : Real = 0.04831391835655754;
                                attribute 'σ_Ixx' : Real = 0.37074144170588635;
                                attribute Iyy : Real = 0.051327151170760706;
                                attribute 'σ_Iyy' : Real = 0.3723953238821935;
                                attribute Izz : Real = 0.05101950202499285;
                                attribute 'σ_Izz' : Real = 0.37017423652493897;
                                attribute Ixy : Real = -0.0025796904542062463;
                                attribute 'σ_Ixy' : Real = 0.02351283871158888;
                                attribute Ixz : Real = 0.0015706718858319703;
                                attribute 'σ_Ixz' : Real = 0.022566176940390956;
                                attribute Iyz : Real = -1.3149686612232364e-4;
                                attribute 'σ_Iyz' : Real = 0.02209918015384651;
                            }
                        }
                        part <'C.1.2.1.4.5.2'> 'Subassembly 257' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.5.2.1'> 'Part 904' {
                                attribute POIconv : String = "-";
                                attribute Ipoint : Boolean = false;
                                attribute mass : Real = 0.4556970932257827;
                                attribute 'σ_mass' : Real = 0.28909372274994966;
                                attribute Cx : Real = -82.85814980044961;
                                attribute 'σ_Cx' : Real = 28.721044428837228;
                                attribute Cy : Real = 54.810406314209104;
                                attribute 'σ_Cy' : Real = 28.23690002309109;
                                attribute Cz : Real = 74.36641436070204;
                                attribute 'σ_Cz' : Real = 29.057750463592832;
                                attribute Ixx : Real = 0.5373910816917773;
                                attribute 'σ_Ixx' : Real = 0.37074144170588635;
                                attribute Iyy : Real = 0.5466813953993623;
                                attribute 'σ_Iyy' : Real = 0.3723953238821935;
                                attribute Izz : Real = 0.5760682400459038;
                                attribute 'σ_Izz' : Real = 0.37017423652493897;
                                attribute Ixy : Real = 0.012471985862480921;
                                attribute 'σ_Ixy' : Real = 0.02351283871158888;
                                attribute Ixz : Real = 0.008315407157988192;
                                attribute 'σ_Ixz' : Real = 0.022566176940390956;
                                attribute Iyz : Real = 0.007519354798033175;
                                attribute 'σ_Iyz' : Real = 0.02209918015384651;
                            }
                            part <'C.1.2.1.4.5.2.2'> 'Part 905' {
                                attribute POIconv : String = "+";
                                attribute Ipoint : Boolean = false;
                                attribute mass : Real = 0.3292598923475016;
                                attribute 'σ_mass' : Real = 0.28909372274994966;
                                attribute Cx : Real = 29.94237500242889;
                                attribute 'σ_Cx' : Real = 28.721044428837228;
                                attribute Cy : Real = -84.90685326978564;
                                attribute 'σ_Cy' : Real = 28.23690002309109;
                                attribute Cz : Real = 68.43279334716499;
                                attribute 'σ_Cz' : Real = 29.057750463592832;
                                attribute Ixx : Real = 0.3287548232186033;
                                attribute 'σ_Ixx' : Real = 0.37074144170588635;
                                attribute Iyy : Real = 0.4091890112585607;
                                attribute 'σ_Iyy' : Real = 0.3723953238821935;
                                attribute Izz : Real = 0.3717316520153332;
                                attribute 'σ_Izz' : Real = 0.37017423652493897;
                                attribute Ixy : Real = 0.011893074160816895;
                                attribute 'σ_Ixy' : Real = 0.02351283871158888;
                                attribute Ixz : Real = -0.00777580297754038;
                                attribute 'σ_Ixz' : Real = 0.022566176940390956;
                                attribute Iyz : Real = -0.0033934025539105067;
                                attribute 'σ_Iyz' : Real = 0.02209918015384651;
                            }
                        }
                        part <'C.1.2.1.4.5.3'> 'Subassembly 258' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.5.3.1'> 'Part 906' {
                                attribute POIconv : String = "-";
                                attribute Ipoint : Boolean = false;
                                attribute mass : Real = 0.08604126638337038;
                                attribute 'σ_mass' : Real = 0.28909372274994966;
                                attribute Cx : Real = 0.16682944260537624;
                                attribute 'σ_Cx' : Real = 28.721044428837228;
                                attribute Cy : Real = 72.42533755488694;
                                attribute 'σ_Cy' : Real = 28.23690002309109;
                                attribute Cz : Real = -49.94699549861252;
                                attribute 'σ_Cz' : Real = 29.057750463592832;
                                attribute Ixx : Real = 0.12348995040614347;
                                attribute 'σ_Ixx' : Real = 0.37074144170588635;
                                attribute Iyy : Real = 0.0969606623349993;
                                attribute 'σ_Iyy' : Real = 0.3723953238821935;
                                attribute Izz : Real = 0.10742809834243293;
                                attribute 'σ_Izz' : Real = 0.37017423652493897;
                                attribute Ixy : Real = 1.746850971018804e-4;
                                attribute 'σ_Ixy' : Real = 0.02351283871158888;
                                attribute Ixz : Real = -0.005498840870320367;
                                attribute 'σ_Ixz' : Real = 0.022566176940390956;
                                attribute Iyz : Real = -0.0022803598221760703;
                                attribute 'σ_Iyz' : Real = 0.02209918015384651;
                            }
                            part <'C.1.2.1.4.5.3.2'> 'Part 907' {
                                attribute POIconv : String = "+";
                                attribute Ipoint : Boolean = false;
                                attribute mass : Real = 0.2610773052168079;
                                attribute 'σ_mass' : Real = 0.28909372274994966;
                                attribute Cx : Real = -20.107315946370363;
                                attribute 'σ_Cx' : Real = 28.721044428837228;
                                attribute Cy : Real = 71.14589419215918;
                                attribute 'σ_Cy' : Real = 28.23690002309109;
                                attribute Cz : Real = -14.439121447503567;
                                attribute 'σ_Cz' : Real = 29.057750463592832;
                                attribute Ixx : Real = 0.34884878494131816;
                                attribute 'σ_Ixx' : Real = 0.37074144170588635;
                                attribute Iyy : Real = 0.36178838477476194;
                                attribute 'σ_Iyy' : Real = 0.3723953238821935;
                                attribute Izz : Real = 0.34669864073993517;
                                attribute 'σ_Izz' : Real = 0.37017423652493897;
                                attribute Ixy : Real = 9.399749468557673e-4;
                                attribute 'σ_Ixy' : Real = 0.02351283871158888;
                                attribute Ixz : Real = -0.007932919262221935;
                                attribute 'σ_Ixz' : Real = 0.022566176940390956;
                                attribute Iyz : Real = 0.009078917828234521;
                                attribute 'σ_Iyz' : Real = 0.02209918015384651;
                            }
                        }
                        part <'C.1.2.1.4.5.4'> 'Subassembly 259' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.5.4.1'> 'Part 908' {
                                attribute POIconv : String = "+";
                                attribute Ipoint : Boolean = false;
                                attribute mass : Real = 0.8068403077791445;
                                attribute 'σ_mass' : Real = 0.28909372274994966;
                                attribute Cx : Real = -1.0880951303988695;
                                attribute 'σ_Cx' : Real = 28.721044428837228;
                                attribute Cy : Real = 0.8990242145955563;
                                attribute 'σ_Cy' : Real = 28.23690002309109;
                                attribute Cz : Real = -39.590950217098;
                                attribute 'σ_Cz' : Real = 29.057750463592832;
                                attribute Ixx : Real = 0.7986237294814765;
                                attribute 'σ_Ixx' : Real = 0.37074144170588635;
                                attribute Iyy : Real = 0.8436211985908275;
                                attribute 'σ_Iyy' : Real = 0.3723953238821935;
                                attribute Izz : Real = 0.8312427565921664;
                                attribute 'σ_Izz' : Real = 0.37017423652493897;
                                attribute Ixy : Real = -0.030949503629324464;
                                attribute 'σ_Ixy' : Real = 0.02351283871158888;
                                attribute Ixz : Real = 0.05107112979500075;
                                attribute 'σ_Ixz' : Real = 0.022566176940390956;
                                attribute Iyz : Real = -0.019157663661828396;
                                attribute 'σ_Iyz' : Real = 0.02209918015384651;
                            }
                            part <'C.1.2.1.4.5.4.2'> 'Part 909' {
                                attribute POIconv : String = "-";
                                attribute Ipoint : Boolean = false;
                                attribute mass : Real = 0.4692512869823258;
                                attribute 'σ_mass' : Real = 0.28909372274994966;
                                attribute Cx : Real = 6.088963942602277;
                                attribute 'σ_Cx' : Real = 28.721044428837228;
                                attribute Cy : Real = -21.3752927724272;
                                attribute 'σ_Cy' : Real = 28.23690002309109;
                                attribute Cz : Real = 64.60574492812157;
                                attribute 'σ_Cz' : Real = 29.057750463592832;
                                attribute Ixx : Real = 0.57655092121534;
                                attribute 'σ_Ixx' : Real = 0.37074144170588635;
                                attribute Iyy : Real = 0.49832157986254155;
                                attribute 'σ_Iyy' : Real = 0.3723953238821935;
                                attribute Izz : Real = 0.5350523602865666;
                                attribute 'σ_Izz' : Real = 0.37017423652493897;
                                attribute Ixy : Real = 0.028700772204402966;
                                attribute 'σ_Ixy' : Real = 0.02351283871158888;
                                attribute Ixz : Real = 0.02210745199556042;
                                attribute 'σ_Ixz' : Real = 0.022566176940390956;
                                attribute Iyz : Real = -0.06741317046096157;
                                attribute 'σ_Iyz' : Real = 0.02209918015384651;
                            }
                        }
                        part <'C.1.2.1.4.5.5'> 'Subassembly 260' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.1.4.5.5.1'> 'Part 910' {
                                attribute POIconv : String = "+";
                                attribute Ipoint : Boolean = false;
                                attribute mass : Real = 0.05411040050140582;
                                attribute 'σ_mass' : Real = 0.28909372274994966;
                                attribute Cx : Real = -31.49070292711258;
                                attribute 'σ_Cx' : Real = 28.721044428837228;
                                attribute Cy : Real = -95.90522358193994;
                                attribute 'σ_Cy' : Real = 28.23690002309109;
                                attribute Cz : Real = 35.6134373228997;
                                attribute 'σ_Cz' : Real = 29.057750463592832;
                                attribute Ixx : Real = 0.06452898808547211;
                                attribute 'σ_Ixx' : Real = 0.37074144170588635;
                                attribute Iyy : Real = 0.07071973036627267;
                                attribute 'σ_Iyy' : Real = 0.3723953238821935;
                                attribute Izz : Real = 0.05949398525096096;
                                attribute 'σ_Izz' : Real = 0.37017423652493897;
                                attribute Ixy : Real = 0.004295690846381135;
                                attribute 'σ_Ixy' : Real = 0.02351283871158888;
                                attribute Ixz : Real = 3.341978864272371e-4;
                                attribute 'σ_Ixz' : Real = 0.022566176940390956;
                                attribute Iyz : Real = -6.686160451230072e-4;
                                attribute 'σ_Iyz' : Real = 0.02209918015384651;
                            }
                            part <'C.1.2.1.4.5.5.2'> 'Part 911' {
                                attribute POIconv : String = "+";
                                attribute Ipoint : Boolean = false;
                                attribute mass : Real = 0.9242297377332579;
                                attribute 'σ_mass' : Real = 0.28909372274994966;
                                attribute Cx : Real = 28.850201843306422;
                                attribute 'σ_Cx' : Real = 28.721044428837228;
                                attribute Cy : Real = 59.65702119283378;
                                attribute 'σ_Cy' : Real = 28.23690002309109;
                                attribute Cz : Real = -10.29543704353273;
                                attribute 'σ_Cz' : Real = 29.057750463592832;
                                attribute Ixx : Real = 1.3496659670435212;
                                attribute 'σ_Ixx' : Real = 0.37074144170588635;
                                attribute Iyy : Real = 1.1661099603608587;
                                attribute 'σ_Iyy' : Real = 0.3723953238821935;
                                attribute Izz : Real = 1.2270295291901012;
                                attribute 'σ_Izz' : Real = 0.37017423652493897;
                                attribute Ixy : Real = 0.1226870384290793;
                                attribute 'σ_Ixy' : Real = 0.02351283871158888;
                                attribute Ixz : Real = 0.002985209822428875;
                                attribute 'σ_Ixz' : Real = 0.022566176940390956;
                                attribute Iyz : Real = -0.0014710157500724868;
                                attribute 'σ_Iyz' : Real = 0.02209918015384651;
                            }
                            part <'C.1.2.1.4.5.5.3'> 'Part 912' {
                                attribute POIconv : String = "+";
                                attribute Ipoint : Boolean = false;
                                attribute mass : Real = 0.7754282531798817;
                                attribute 'σ_mass' : Real = 0.28909372274994966;
                                attribute Cx : Real = 92.87134446203709;
                                attribute 'σ_Cx' : Real = 28.721044428837228;
                                attribute Cy : Real = -68.52519162930548;
                                attribute 'σ_Cy' : Real = 28.23690002309109;
                                attribute Cz : Real = -59.747326048091054;
                                attribute 'σ_Cz' : Real = 29.057750463592832;
                                attribute Ixx : Real = 1.0911166716455396;
                                attribute 'σ_Ixx' : Real = 0.37074144170588635;
                                attribute Iyy : Real = 1.1007192810350237;
                                attribute 'σ_Iyy' : Real = 0.3723953238821935;
                                attribute Izz : Real = 1.0795607138371808;
                                attribute 'σ_Izz' : Real = 0.37017423652493897;
                                attribute Ixy : Real = -0.014754331565705572;
                                attribute 'σ_Ixy' : Real = 0.02351283871158888;
                                attribute Ixz : Real = 0.0149293794165677;
                                attribute 'σ_Ixz' : Real = 0.022566176940390956;
                                attribute Iyz : Real = 0.011358750116650218;
                                attribute 'σ_Iyz' : Real = 0.02209918015384651;
                            }
                            part <'C.1.2.1.4.5.5.4'> 'Part 913' {
                                attribute POIconv : String = "+";
                                attribute Ipoint : Boolean = false;
                                attribute mass : Real = 0.5277832171006593;
                                attribute 'σ_mass' : Real = 0.28909372274994966;
                                attribute Cx : Real = -16.497942758724093;
                                attribute 'σ_Cx' : Real = 28.721044428837228;
                                attribute Cy : Real = -87.71315040066838;
                                attribute 'σ_Cy' : Real = 28.23690002309109;
                                attribute Cz : Real = -81.69335275888443;
                                attribute 'σ_Cz' : Real = 29.057750463592832;
                                attribute Ixx : Real = 0.6284057323342536;
                                attribute 'σ_Ixx' : Real = 0.37074144170588635;
                                attribute Iyy : Real = 0.5303161842795756;
                                attribute 'σ_Iyy' : Real = 0.3723953238821935;
                                attribute Izz : Real = 0.6409211170850135;
                                attribute 'σ_Izz' : Real = 0.37017423652493897;
                                attribute Ixy : Real = -0.06409805373840372;
                                attribute 'σ_Ixy' : Real = 0.02351283871158888;
                                attribute Ixz : Real = -0.00298168478519825;
                                attribute 'σ_Ixz' : Real = 0.022566176940390956;
                                attribute Iyz : Real = 0.04669028045524837;
                                attribute 'σ_Iyz' : Real = 0.02209918015384651;
                            }
                            part <'C.1.2.1.4.5.5.5'> 'Part 914' {
                                attribute POIconv : String = "+";
                                attribute Ipoint : Boolean = false;
                                attribute mass : Real = 0.910513954089256;
                                attribute 'σ_mass' : Real = 0.28909372274994966;
                                attribute Cx : Real = 95.22037766873837;
                                attribute 'σ_Cx' : Real = 28.721044428837228;
                                attribute Cy : Real = 94.02346019633114;
                                attribute 'σ_Cy' : Real = 28.23690002309109;
                                attribute Cz : Real = -88.30452910624444;
                                attribute 'σ_Cz' : Real = 29.057750463592832;
                                attribute Ixx : Real = 0.9713111976167066;
                                attribute 'σ_Ixx' : Real = 0.37074144170588635;
                                attribute Iyy : Real = 0.9559105266824719;
                                attribute 'σ_Iyy' : Real = 0.3723953238821935;
                                attribute Izz : Real = 1.008727936764042;
                                attribute 'σ_Izz' : Real = 0.37017423652493897;
                                attribute Ixy : Real = 0.11407276798272098;
                                attribute 'σ_Ixy' : Real = 0.02351283871158888;
                                attribute Ixz : Real = 0.011828437228512768;
                                attribute 'σ_Ixz' : Real = 0.022566176940390956;
                                attribute Iyz : Real = 0.030549192355939177;
                                attribute 'σ_Iyz' : Real = 0.02209918015384651;
                            }
                        }
                    }
                }
            }
            part <'C.1.2.2'> 'Element 6' {
                attribute POIconv : String = "-";
                attribute Ipoint : Boolean;
                attribute mass : Real;
                attribute 'σ_mass' : Real;
                attribute Cx : Real;
                attribute 'σ_Cx' : Real;
                attribute Cy : Real;
                attribute 'σ_Cy' : Real;
                attribute Cz : Real;
                attribute 'σ_Cz' : Real;
                attribute Ixx : Real;
                attribute 'σ_Ixx' : Real;
                attribute Iyy : Real;
                attribute 'σ_Iyy' : Real;
                attribute Izz : Real;
                attribute 'σ_Izz' : Real;
                attribute Ixy : Real;
                attribute 'σ_Ixy' : Real;
                attribute Ixz : Real;
                attribute 'σ_Ixz' : Real;
                attribute Iyz : Real;
                attribute 'σ_Iyz' : Real;
                part <'C.1.2.2.1'> 'Subsystem 20' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.2.2.1.1'> 'Assembly 75' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.2.1.1.1'> 'Subassembly 261' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.1.1.1.1'> 'Part 915' {
                                attribute POIconv : String = "-";
                                attribute Ipoint : Boolean = false;
                                attribute mass : Real = 0.36086366243776863;
                                attribute 'σ_mass' : Real = 0.28909372274994966;
                                attribute Cx : Real = -96.05082822963595;
                                attribute 'σ_Cx' : Real = 28.721044428837228;
                                attribute Cy : Real = -54.78245229460299;
                                attribute 'σ_Cy' : Real = 28.23690002309109;
                                attribute Cz : Real = 55.986605025827885;
                                attribute 'σ_Cz' : Real = 29.057750463592832;
                                attribute Ixx : Real = 0.3860246912287275;
                                attribute 'σ_Ixx' : Real = 0.37074144170588635;
                                attribute Iyy : Real = 0.39453440759335656;
                                attribute 'σ_Iyy' : Real = 0.3723953238821935;
                                attribute Izz : Real = 0.3866428853829205;
                                attribute 'σ_Izz' : Real = 0.37017423652493897;
                                attribute Ixy : Real = 0.017560447715276668;
                                attribute 'σ_Ixy' : Real = 0.02351283871158888;
                                attribute Ixz : Real = -0.01578187406659621;
                                attribute 'σ_Ixz' : Real = 0.022566176940390956;
                                attribute Iyz : Real = -0.014754927220251481;
                                attribute 'σ_Iyz' : Real = 0.02209918015384651;
                            }
                            part <'C.1.2.2.1.1.1.2'> 'Part 916' {
                                attribute POIconv : String = "+";
                                attribute Ipoint : Boolean = false;
                                attribute mass : Real = 0.6230471224761568;
                                attribute 'σ_mass' : Real = 0.28909372274994966;
                                attribute Cx : Real = 79.72097382880747;
                                attribute 'σ_Cx' : Real = 28.721044428837228;
                                attribute Cy : Real = 31.737680453807116;
                                attribute 'σ_Cy' : Real = 28.23690002309109;
                                attribute Cz : Real = 59.28669576533139;
                                attribute 'σ_Cz' : Real = 29.057750463592832;
                                attribute Ixx : Real = 0.7365694227711755;
                                attribute 'σ_Ixx' : Real = 0.37074144170588635;
                                attribute Iyy : Real = 0.7295201248252913;
                                attribute 'σ_Iyy' : Real = 0.3723953238821935;
                                attribute Izz : Real = 0.618345636521789;
                                attribute 'σ_Izz' : Real = 0.37017423652493897;
                                attribute Ixy : Real = -0.004303659115087235;
                                attribute 'σ_Ixy' : Real = 0.02351283871158888;
                                attribute Ixz : Real = -0.029245930707172872;
                                attribute 'σ_Ixz' : Real = 0.022566176940390956;
                                attribute Iyz : Real = 0.013223996752649222;
                                attribute 'σ_Iyz' : Real = 0.02209918015384651;
                            }
                            part <'C.1.2.2.1.1.1.3'> 'Part 917' {
                                attribute POIconv : String = "+";
                                attribute Ipoint : Boolean = false;
                                attribute mass : Real = 0.06109494648454711;
                                attribute 'σ_mass' : Real = 0.28909372274994966;
                                attribute Cx : Real = -60.14827489852905;
                                attribute 'σ_Cx' : Real = 28.721044428837228;
                                attribute Cy : Real = -8.96461522206664;
                                attribute 'σ_Cy' : Real = 28.23690002309109;
                                attribute Cz : Real = -96.33653969503939;
                                attribute 'σ_Cz' : Real = 29.057750463592832;
                                attribute Ixx : Real = 0.07257276811325816;
                                attribute 'σ_Ixx' : Real = 0.37074144170588635;
                                attribute Iyy : Real = 0.07149315115337382;
                                attribute 'σ_Iyy' : Real = 0.3723953238821935;
                                attribute Izz : Real = 0.0718609471865199;
                                attribute 'σ_Izz' : Real = 0.37017423652493897;
                                attribute Ixy : Real = -0.002870623075422591;
                                attribute 'σ_Ixy' : Real = 0.02351283871158888;
                                attribute Ixz : Real = -0.006649221059225049;
                                attribute 'σ_Ixz' : Real = 0.022566176940390956;
                                attribute Iyz : Real = 0.006603619038093246;
                                attribute 'σ_Iyz' : Real = 0.02209918015384651;
                            }
                            part <'C.1.2.2.1.1.1.4'> 'Part 918' {
                                attribute POIconv : String = "-";
                                attribute Ipoint : Boolean = false;
                                attribute mass : Real = 0.713394578338135;
                                attribute 'σ_mass' : Real = 0.28909372274994966;
                                attribute Cx : Real = -94.92362956516445;
                                attribute 'σ_Cx' : Real = 28.721044428837228;
                                attribute Cy : Real = -73.7762161064893;
                                attribute 'σ_Cy' : Real = 28.23690002309109;
                                attribute Cz : Real = -9.6294354647398;
                                attribute 'σ_Cz' : Real = 29.057750463592832;
                                attribute Ixx : Real = 0.7032529255843124;
                                attribute 'σ_Ixx' : Real = 0.37074144170588635;
                                attribute Iyy : Real = 0.7552442876030476;
                                attribute 'σ_Iyy' : Real = 0.3723953238821935;
                                attribute Izz : Real = 0.8113232026448255;
                                attribute 'σ_Izz' : Real = 0.37017423652493897;
                                attribute Ixy : Real = 0.09836509643646447;
                                attribute 'σ_Ixy' : Real = 0.02351283871158888;
                                attribute Ixz : Real = -0.04925069913912512;
                                attribute 'σ_Ixz' : Real = 0.022566176940390956;
                                attribute Iyz : Real = 0.03789759159950372;
                                attribute 'σ_Iyz' : Real = 0.02209918015384651;
                            }
                        }
                        part <'C.1.2.2.1.1.2'> 'Subassembly 262' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.1.1.2.1'> 'Part 919' {
                                attribute POIconv : String = "+";
                                attribute Ipoint : Boolean = false;
                                attribute mass : Real = 0.8259045990500599;
                                attribute 'σ_mass' : Real = 0.28909372274994966;
                                attribute Cx : Real = 14.283949974924326;
                                attribute 'σ_Cx' : Real = 28.721044428837228;
                                attribute Cy : Real = -13.152746018022299;
                                attribute 'σ_Cy' : Real = 28.23690002309109;
                                attribute Cz : Real = -27.273988351225853;
                                attribute 'σ_Cz' : Real = 29.057750463592832;
                                attribute Ixx : Real = 1.0355150587577753;
                                attribute 'σ_Ixx' : Real = 0.37074144170588635;
                                attribute Iyy : Real = 1.0395092993226673;
                                attribute 'σ_Iyy' : Real = 0.3723953238821935;
                                attribute Izz : Real = 1.3190653100202023;
                                attribute 'σ_Izz' : Real = 0.37017423652493897;
                                attribute Ixy : Real = -0.0022686051785832393;
                                attribute 'σ_Ixy' : Real = 0.02351283871158888;
                                attribute Ixz : Real = 0.027544862143464882;
                                attribute 'σ_Ixz' : Real = 0.022566176940390956;
                                attribute Iyz : Real = 0.044601215615107714;
                                attribute 'σ_Iyz' : Real = 0.02209918015384651;
                            }
                            part <'C.1.2.2.1.1.2.2'> 'Part 920' {
                                attribute POIconv : String = "-";
                                attribute Ipoint : Boolean = false;
                                attribute mass : Real = 0.7616543880011887;
                                attribute 'σ_mass' : Real = 0.28909372274994966;
                                attribute Cx : Real = 47.759889578446746;
                                attribute 'σ_Cx' : Real = 28.721044428837228;
                                attribute Cy : Real = 70.23149468004704;
                                attribute 'σ_Cy' : Real = 28.23690002309109;
                                attribute Cz : Real = 64.2881260253489;
                                attribute 'σ_Cz' : Real = 29.057750463592832;
                                attribute Ixx : Real = 0.8365410239384761;
                                attribute 'σ_Ixx' : Real = 0.37074144170588635;
                                attribute Iyy : Real = 0.9492416930287492;
                                attribute 'σ_Iyy' : Real = 0.3723953238821935;
                                attribute Izz : Real = 0.8685955399659884;
                                attribute 'σ_Izz' : Real = 0.37017423652493897;
                                attribute Ixy : Real = -0.003347153783754152;
                                attribute 'σ_Ixy' : Real = 0.02351283871158888;
                                attribute Ixz : Real = -0.011975874145181647;
                                attribute 'σ_Ixz' : Real = 0.022566176940390956;
                                attribute Iyz : Real = 0.005839179218359931;
                                attribute 'σ_Iyz' : Real = 0.02209918015384651;
                            }
                            part <'C.1.2.2.1.1.2.3'> 'Part 921' {
                                attribute POIconv : String = "+";
                                attribute Ipoint : Boolean = false;
                                attribute mass : Real = 0.021379657721845434;
                                attribute 'σ_mass' : Real = 0.28909372274994966;
                                attribute Cx : Real = 57.531608222052455;
                                attribute 'σ_Cx' : Real = 28.721044428837228;
                                attribute Cy : Real = 73.42850370332599;
                                attribute 'σ_Cy' : Real = 28.23690002309109;
                                attribute Cz : Real = 61.6898390930146;
                                attribute 'σ_Cz' : Real = 29.057750463592832;
                                attribute Ixx : Real = 0.021527752953343134;
                                attribute 'σ_Ixx' : Real = 0.37074144170588635;
                                attribute Iyy : Real = 0.02619449818308588;
                                attribute 'σ_Iyy' : Real = 0.3723953238821935;
                                attribute Izz : Real = 0.028343739182350582;
                                attribute 'σ_Izz' : Real = 0.37017423652493897;
                                attribute Ixy : Real = 8.116811288694989e-4;
                                attribute 'σ_Ixy' : Real = 0.02351283871158888;
                                attribute Ixz : Real = 6.632069751084687e-4;
                                attribute 'σ_Ixz' : Real = 0.022566176940390956;
                                attribute Iyz : Real = 1.13792767616614e-4;
                                attribute 'σ_Iyz' : Real = 0.02209918015384651;
                            }
                            part <'C.1.2.2.1.1.2.4'> 'Part 922' {
                                attribute POIconv : String = "+";
                                attribute Ipoint : Boolean = false;
                                attribute mass : Real = 0.3944050546500366;
                                attribute 'σ_mass' : Real = 0.28909372274994966;
                                attribute Cx : Real = -65.04850061610341;
                                attribute 'σ_Cx' : Real = 28.721044428837228;
                                attribute Cy : Real = -85.6566856149584;
                                attribute 'σ_Cy' : Real = 28.23690002309109;
                                attribute Cz : Real = 74.16435056366026;
                                attribute 'σ_Cz' : Real = 29.057750463592832;
                                attribute Ixx : Real = 0.5517367652677677;
                                attribute 'σ_Ixx' : Real = 0.37074144170588635;
                                attribute Iyy : Real = 0.4595055453477788;
                                attribute 'σ_Iyy' : Real = 0.3723953238821935;
                                attribute Izz : Real = 0.5089780501031764;
                                attribute 'σ_Izz' : Real = 0.37017423652493897;
                                attribute Ixy : Real = -0.0018066614633099939;
                                attribute 'σ_Ixy' : Real = 0.02351283871158888;
                                attribute Ixz : Real = -0.0039876135243384495;
                                attribute 'σ_Ixz' : Real = 0.022566176940390956;
                                attribute Iyz : Real = 0.003396071970097911;
                                attribute 'σ_Iyz' : Real = 0.02209918015384651;
                            }
                            part <'C.1.2.2.1.1.2.5'> 'Part 923' {
                                attribute POIconv : String = "-";
                                attribute Ipoint : Boolean = false;
                                attribute mass : Real = 0.3832627466998529;
                                attribute 'σ_mass' : Real = 0.28909372274994966;
                                attribute Cx : Real = -0.5101643968373537;
                                attribute 'σ_Cx' : Real = 28.721044428837228;
                                attribute Cy : Real = 6.384871248155832;
                                attribute 'σ_Cy' : Real = 28.23690002309109;
                                attribute Cz : Real = -34.1337448451668;
                                attribute 'σ_Cz' : Real = 29.057750463592832;
                                attribute Ixx : Real = 0.4477798341795467;
                                attribute 'σ_Ixx' : Real = 0.37074144170588635;
                                attribute Iyy : Real = 0.4419436298176441;
                                attribute 'σ_Iyy' : Real = 0.3723953238821935;
                                attribute Izz : Real = 0.5115002617604051;
                                attribute 'σ_Izz' : Real = 0.37017423652493897;
                                attribute Ixy : Real = -0.004129105121358612;
                                attribute 'σ_Ixy' : Real = 0.02351283871158888;
                                attribute Ixz : Real = 0.010683859248127748;
                                attribute 'σ_Ixz' : Real = 0.022566176940390956;
                                attribute Iyz : Real = 0.008836181083328244;
                                attribute 'σ_Iyz' : Real = 0.02209918015384651;
                            }
                        }
                        part <'C.1.2.2.1.1.3'> 'Subassembly 263' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.1.1.3.1'> 'Part 924' {
                                attribute POIconv : String = "+";
                                attribute Ipoint : Boolean = false;
                                attribute mass : Real = 0.9098902928296011;
                                attribute 'σ_mass' : Real = 0.28909372274994966;
                                attribute Cx : Real = -67.32482938095927;
                                attribute 'σ_Cx' : Real = 28.721044428837228;
                                attribute Cy : Real = 13.133474811911583;
                                attribute 'σ_Cy' : Real = 28.23690002309109;
                                attribute Cz : Real = 2.206150349229574;
                                attribute 'σ_Cz' : Real = 29.057750463592832;
                                attribute Ixx : Real = 1.361844708158152;
                                attribute 'σ_Ixx' : Real = 0.37074144170588635;
                                attribute Iyy : Real = 1.3298241465574654;
                                attribute 'σ_Iyy' : Real = 0.3723953238821935;
                                attribute Izz : Real = 1.3458447578579866;
                                attribute 'σ_Izz' : Real = 0.37017423652493897;
                                attribute Ixy : Real = -0.01226606230409862;
                                attribute 'σ_Ixy' : Real = 0.02351283871158888;
                                attribute Ixz : Real = -0.028852209553286642;
                                attribute 'σ_Ixz' : Real = 0.022566176940390956;
                                attribute Iyz : Real = -0.010151314568700009;
                                attribute 'σ_Iyz' : Real = 0.02209918015384651;
                            }
                            part <'C.1.2.2.1.1.3.2'> 'Part 925' {
                                attribute POIconv : String = "-";
                                attribute Ipoint : Boolean = false;
                                attribute mass : Real = 0.48804895440395923;
                                attribute 'σ_mass' : Real = 0.28909372274994966;
                                attribute Cx : Real = -74.20310853049159;
                                attribute 'σ_Cx' : Real = 28.721044428837228;
                                attribute Cy : Real = 29.36070477589965;
                                attribute 'σ_Cy' : Real = 28.23690002309109;
                                attribute Cz : Real = 48.44129062257707;
                                attribute 'σ_Cz' : Real = 29.057750463592832;
                                attribute Ixx : Real = 0.645321086113301;
                                attribute 'σ_Ixx' : Real = 0.37074144170588635;
                                attribute Iyy : Real = 0.6826182242447267;
                                attribute 'σ_Iyy' : Real = 0.3723953238821935;
                                attribute Izz : Real = 0.6597736995008983;
                                attribute 'σ_Izz' : Real = 0.37017423652493897;
                                attribute Ixy : Real = 0.021845674250418168;
                                attribute 'σ_Ixy' : Real = 0.02351283871158888;
                                attribute Ixz : Real = 0.01922806005937716;
                                attribute 'σ_Ixz' : Real = 0.022566176940390956;
                                attribute Iyz : Real = -0.02907158346786725;
                                attribute 'σ_Iyz' : Real = 0.02209918015384651;
                            }
                            part <'C.1.2.2.1.1.3.3'> 'Part 926' {
                                attribute POIconv : String = "+";
                                attribute Ipoint : Boolean = false;
                                attribute mass : Real = 0.5580423413272947;
                                attribute 'σ_mass' : Real = 0.28909372274994966;
                                attribute Cx : Real = -25.388148706406355;
                                attribute 'σ_Cx' : Real = 28.721044428837228;
                                attribute Cy : Real = 19.993044063448906;
                                attribute 'σ_Cy' : Real = 28.23690002309109;
                                attribute Cz : Real = 40.35831596702337;
                                attribute 'σ_Cz' : Real = 29.057750463592832;
                                attribute Ixx : Real = 0.6745063598180404;
                                attribute 'σ_Ixx' : Real = 0.37074144170588635;
                                attribute Iyy : Real = 0.6784042269102898;
                                attribute 'σ_Iyy' : Real = 0.3723953238821935;
                                attribute Izz : Real = 0.6459669176582017;
                                attribute 'σ_Izz' : Real = 0.37017423652493897;
                                attribute Ixy : Real = 0.040450960801018926;
                                attribute 'σ_Ixy' : Real = 0.02351283871158888;
                                attribute Ixz : Real = -0.02030124017871201;
                                attribute 'σ_Ixz' : Real = 0.022566176940390956;
                                attribute Iyz : Real = 0.06462954329343132;
                                attribute 'σ_Iyz' : Real = 0.02209918015384651;
                            }
                            part <'C.1.2.2.1.1.3.4'> 'Part 927' {
                                attribute POIconv : String = "-";
                                attribute Ipoint : Boolean = false;
                                attribute mass : Real = 0.40644716095970945;
                                attribute 'σ_mass' : Real = 0.28909372274994966;
                                attribute Cx : Real = 84.04793255031109;
                                attribute 'σ_Cx' : Real = 28.721044428837228;
                                attribute Cy : Real = -58.756082924082875;
                                attribute 'σ_Cy' : Real = 28.23690002309109;
                                attribute Cz : Real = 18.052408238872886;
                                attribute 'σ_Cz' : Real = 29.057750463592832;
                                attribute Ixx : Real = 0.4699585397163946;
                                attribute 'σ_Ixx' : Real = 0.37074144170588635;
                                attribute Iyy : Real = 0.47379991403944666;
                                attribute 'σ_Iyy' : Real = 0.3723953238821935;
                                attribute Izz : Real = 0.4698722999414431;
                                attribute 'σ_Izz' : Real = 0.37017423652493897;
                                attribute Ixy : Real = -0.016463384559653734;
                                attribute 'σ_Ixy' : Real = 0.02351283871158888;
                                attribute Ixz : Real = -0.0354527632987033;
                                attribute 'σ_Ixz' : Real = 0.022566176940390956;
                                attribute Iyz : Real = -0.004649885440174157;
                                attribute 'σ_Iyz' : Real = 0.02209918015384651;
                            }
                        }
                    }
                    part <'C.1.2.2.1.2'> 'Assembly 76' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.2.1.2.1'> 'Subassembly 264' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.1.2.1.1'> 'Part 928' {
                                attribute POIconv : String = "-";
                                attribute Ipoint : Boolean = false;
                                attribute mass : Real = 0.7995262390787248;
                                attribute 'σ_mass' : Real = 0.28909372274994966;
                                attribute Cx : Real = -70.02420681528747;
                                attribute 'σ_Cx' : Real = 28.721044428837228;
                                attribute Cy : Real = -45.677982131019235;
                                attribute 'σ_Cy' : Real = 28.23690002309109;
                                attribute Cz : Real = 37.172099854797125;
                                attribute 'σ_Cz' : Real = 29.057750463592832;
                                attribute Ixx : Real = 0.810093025908591;
                                attribute 'σ_Ixx' : Real = 0.37074144170588635;
                                attribute Iyy : Real = 0.7725583471161834;
                                attribute 'σ_Iyy' : Real = 0.3723953238821935;
                                attribute Izz : Real = 0.8106496361914727;
                                attribute 'σ_Izz' : Real = 0.37017423652493897;
                                attribute Ixy : Real = 0.00747103716986839;
                                attribute 'σ_Ixy' : Real = 0.02351283871158888;
                                attribute Ixz : Real = 0.002271714147283138;
                                attribute 'σ_Ixz' : Real = 0.022566176940390956;
                                attribute Iyz : Real = 0.014016636322683622;
                                attribute 'σ_Iyz' : Real = 0.02209918015384651;
                            }
                            part <'C.1.2.2.1.2.1.2'> 'Part 929' {
                                attribute POIconv : String = "-";
                                attribute Ipoint : Boolean = false;
                                attribute mass : Real = 0.7995670292919967;
                                attribute 'σ_mass' : Real = 0.28909372274994966;
                                attribute Cx : Real = -97.44771784171462;
                                attribute 'σ_Cx' : Real = 28.721044428837228;
                                attribute Cy : Real = -58.66879811510444;
                                attribute 'σ_Cy' : Real = 28.23690002309109;
                                attribute Cz : Real = -45.73369529098272;
                                attribute 'σ_Cz' : Real = 29.057750463592832;
                                attribute Ixx : Real = 0.8056292724888053;
                                attribute 'σ_Ixx' : Real = 0.37074144170588635;
                                attribute Iyy : Real = 0.8123907465948877;
                                attribute 'σ_Iyy' : Real = 0.3723953238821935;
                                attribute Izz : Real = 0.9152130513852671;
                                attribute 'σ_Izz' : Real = 0.37017423652493897;
                                attribute Ixy : Real = 0.008575871360702694;
                                attribute 'σ_Ixy' : Real = 0.02351283871158888;
                                attribute Ixz : Real = 0.019939681104693095;
                                attribute 'σ_Ixz' : Real = 0.022566176940390956;
                                attribute Iyz : Real = -0.025695000410455287;
                                attribute 'σ_Iyz' : Real = 0.02209918015384651;
                            }
                            part <'C.1.2.2.1.2.1.3'> 'Part 930' {
                                attribute POIconv : String = "+";
                                attribute Ipoint : Boolean = false;
                                attribute mass : Real = 0.9775735801451374;
                                attribute 'σ_mass' : Real = 0.28909372274994966;
                                attribute Cx : Real = -91.10767035745084;
                                attribute 'σ_Cx' : Real = 28.721044428837228;
                                attribute Cy : Real = 3.369822585955262;
                                attribute 'σ_Cy' : Real = 28.23690002309109;
                                attribute Cz : Real = 21.281422534957528;
                                attribute 'σ_Cz' : Real = 29.057750463592832;
                                attribute Ixx : Real = 1.4855871098462907;
                                attribute 'σ_Ixx' : Real = 0.37074144170588635;
                                attribute Iyy : Real = 1.491914369412807;
                                attribute 'σ_Iyy' : Real = 0.3723953238821935;
                                attribute Izz : Real = 1.4583468439755838;
                                attribute 'σ_Izz' : Real = 0.37017423652493897;
                                attribute Ixy : Real = -0.009982867245512811;
                                attribute 'σ_Ixy' : Real = 0.02351283871158888;
                                attribute Ixz : Real = 0.021534481927929873;
                                attribute 'σ_Ixz' : Real = 0.022566176940390956;
                                attribute Iyz : Real = -0.009394902390628075;
                                attribute 'σ_Iyz' : Real = 0.02209918015384651;
                            }
                        }
                        part <'C.1.2.2.1.2.2'> 'Subassembly 265' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.1.2.2.1'> 'Part 931' {
                                attribute POIconv : String = "+";
                                attribute Ipoint : Boolean = false;
                                attribute mass : Real = 0.021402636292390528;
                                attribute 'σ_mass' : Real = 0.28909372274994966;
                                attribute Cx : Real = -92.75170937180519;
                                attribute 'σ_Cx' : Real = 28.721044428837228;
                                attribute Cy : Real = 43.91828738152981;
                                attribute 'σ_Cy' : Real = 28.23690002309109;
                                attribute Cz : Real = -93.28296408057213;
                                attribute 'σ_Cz' : Real = 29.057750463592832;
                                attribute Ixx : Real = 0.02682958562219768;
                                attribute 'σ_Ixx' : Real = 0.37074144170588635;
                                attribute Iyy : Real = 0.028817092257073577;
                                attribute 'σ_Iyy' : Real = 0.3723953238821935;
                                attribute Izz : Real = 0.02694188151256071;
                                attribute 'σ_Izz' : Real = 0.37017423652493897;
                                attribute Ixy : Real = 6.6169702075143e-4;
                                attribute 'σ_Ixy' : Real = 0.02351283871158888;
                                attribute Ixz : Real = 0.002165462399996659;
                                attribute 'σ_Ixz' : Real = 0.022566176940390956;
                                attribute Iyz : Real = -5.7933430365538334e-5;
                                attribute 'σ_Iyz' : Real = 0.02209918015384651;
                            }
                            part <'C.1.2.2.1.2.2.2'> 'Part 932' {
                                attribute POIconv : String = "-";
                                attribute Ipoint : Boolean = false;
                                attribute mass : Real = 0.3272131983656436;
                                attribute 'σ_mass' : Real = 0.28909372274994966;
                                attribute Cx : Real = -84.2272687703371;
                                attribute 'σ_Cx' : Real = 28.721044428837228;
                                attribute Cy : Real = -42.10040234029293;
                                attribute 'σ_Cy' : Real = 28.23690002309109;
                                attribute Cz : Real = 26.3877481687814;
                                attribute 'σ_Cz' : Real = 29.057750463592832;
                                attribute Ixx : Real = 0.3927297203302749;
                                attribute 'σ_Ixx' : Real = 0.37074144170588635;
                                attribute Iyy : Real = 0.3667391269978756;
                                attribute 'σ_Iyy' : Real = 0.3723953238821935;
                                attribute Izz : Real = 0.43938759921654547;
                                attribute 'σ_Izz' : Real = 0.37017423652493897;
                                attribute Ixy : Real = -0.024800585605636784;
                                attribute 'σ_Ixy' : Real = 0.02351283871158888;
                                attribute Ixz : Real = -0.019196181839835603;
                                attribute 'σ_Ixz' : Real = 0.022566176940390956;
                                attribute Iyz : Real = -0.006210975820636622;
                                attribute 'σ_Iyz' : Real = 0.02209918015384651;
                            }
                            part <'C.1.2.2.1.2.2.3'> 'Part 933' {
                                attribute POIconv : String = "-";
                                attribute Ipoint : Boolean = false;
                                attribute mass : Real = 0.3637619523713365;
                                attribute 'σ_mass' : Real = 0.28909372274994966;
                                attribute Cx : Real = 56.703932071104646;
                                attribute 'σ_Cx' : Real = 28.721044428837228;
                                attribute Cy : Real = -91.10476705245674;
                                attribute 'σ_Cy' : Real = 28.23690002309109;
                                attribute Cz : Real = 57.741919392719865;
                                attribute 'σ_Cz' : Real = 29.057750463592832;
                                attribute Ixx : Real = 0.47905852257414216;
                                attribute 'σ_Ixx' : Real = 0.37074144170588635;
                                attribute Iyy : Real = 0.4028898340008814;
                                attribute 'σ_Iyy' : Real = 0.3723953238821935;
                                attribute Izz : Real = 0.4423681904178884;
                                attribute 'σ_Izz' : Real = 0.37017423652493897;
                                attribute Ixy : Real = -0.024919868043831037;
                                attribute 'σ_Ixy' : Real = 0.02351283871158888;
                                attribute Ixz : Real = -0.03699538509650166;
                                attribute 'σ_Ixz' : Real = 0.022566176940390956;
                                attribute Iyz : Real = 0.003665243380487599;
                                attribute 'σ_Iyz' : Real = 0.02209918015384651;
                            }
                            part <'C.1.2.2.1.2.2.4'> 'Part 934' {
                                attribute POIconv : String = "-";
                                attribute Ipoint : Boolean = false;
                                attribute mass : Real = 0.5193952887237537;
                                attribute 'σ_mass' : Real = 0.28909372274994966;
                                attribute Cx : Real = -23.044981574639678;
                                attribute 'σ_Cx' : Real = 28.721044428837228;
                                attribute Cy : Real = 51.513195876032114;
                                attribute 'σ_Cy' : Real = 28.23690002309109;
                                attribute Cz : Real = -25.090753939002752;
                                attribute 'σ_Cz' : Real = 29.057750463592832;
                                attribute Ixx : Real = 0.724839429412922;
                                attribute 'σ_Ixx' : Real = 0.37074144170588635;
                                attribute Iyy : Real = 0.6189863739809514;
                                attribute 'σ_Iyy' : Real = 0.3723953238821935;
                                attribute Izz : Real = 0.6621499257365612;
                                attribute 'σ_Izz' : Real = 0.37017423652493897;
                                attribute Ixy : Real = 0.021548560645599485;
                                attribute 'σ_Ixy' : Real = 0.02351283871158888;
                                attribute Ixz : Real = -0.017812116418874785;
                                attribute 'σ_Ixz' : Real = 0.022566176940390956;
                                attribute Iyz : Real = 0.015228660831936528;
                                attribute 'σ_Iyz' : Real = 0.02209918015384651;
                            }
                            part <'C.1.2.2.1.2.2.5'> 'Part 935' {
                                attribute POIconv : String = "-";
                                attribute Ipoint : Boolean = false;
                                attribute mass : Real = 0.58695749166538;
                                attribute 'σ_mass' : Real = 0.28909372274994966;
                                attribute Cx : Real = 40.622040862217546;
                                attribute 'σ_Cx' : Real = 28.721044428837228;
                                attribute Cy : Real = 67.94142634607852;
                                attribute 'σ_Cy' : Real = 28.23690002309109;
                                attribute Cz : Real = 49.45287965238094;
                                attribute 'σ_Cz' : Real = 29.057750463592832;
                                attribute Ixx : Real = 0.816131836828404;
                                attribute 'σ_Ixx' : Real = 0.37074144170588635;
                                attribute Iyy : Real = 0.8005513906078435;
                                attribute 'σ_Iyy' : Real = 0.3723953238821935;
                                attribute Izz : Real = 0.7879026653987344;
                                attribute 'σ_Izz' : Real = 0.37017423652493897;
                                attribute Ixy : Real = -0.026382847827147754;
                                attribute 'σ_Ixy' : Real = 0.02351283871158888;
                                attribute Ixz : Real = -0.014195410767882772;
                                attribute 'σ_Ixz' : Real = 0.022566176940390956;
                                attribute Iyz : Real = 1.9774592075020214e-4;
                                attribute 'σ_Iyz' : Real = 0.02209918015384651;
                            }
                        }
                        part <'C.1.2.2.1.2.3'> 'Subassembly 266' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.1.2.3.1'> 'Part 936' {
                                attribute POIconv : String = "-";
                                attribute Ipoint : Boolean = false;
                                attribute mass : Real = 0.8690858327089809;
                                attribute 'σ_mass' : Real = 0.28909372274994966;
                                attribute Cx : Real = 5.956424260511994;
                                attribute 'σ_Cx' : Real = 28.721044428837228;
                                attribute Cy : Real = -63.47609465010464;
                                attribute 'σ_Cy' : Real = 28.23690002309109;
                                attribute Cz : Real = 99.81979625299573;
                                attribute 'σ_Cz' : Real = 29.057750463592832;
                                attribute Ixx : Real = 1.0728206477751006;
                                attribute 'σ_Ixx' : Real = 0.37074144170588635;
                                attribute Iyy : Real = 0.9984520385474636;
                                attribute 'σ_Iyy' : Real = 0.3723953238821935;
                                attribute Izz : Real = 1.0343238929780978;
                                attribute 'σ_Izz' : Real = 0.37017423652493897;
                                attribute Ixy : Real = 0.03826574876350809;
                                attribute 'σ_Ixy' : Real = 0.02351283871158888;
                                attribute Ixz : Real = 0.109191755978082;
                                attribute 'σ_Ixz' : Real = 0.022566176940390956;
                                attribute Iyz : Real = 0.019069675750405357;
                                attribute 'σ_Iyz' : Real = 0.02209918015384651;
                            }
                            part <'C.1.2.2.1.2.3.2'> 'Part 937' {
                                attribute POIconv : String = "-";
                                attribute Ipoint : Boolean = false;
                                attribute mass : Real = 0.4456750747319311;
                                attribute 'σ_mass' : Real = 0.28909372274994966;
                                attribute Cx : Real = -21.321478625759482;
                                attribute 'σ_Cx' : Real = 28.721044428837228;
                                attribute Cy : Real = -59.986153710633516;
                                attribute 'σ_Cy' : Real = 28.23690002309109;
                                attribute Cz : Real = 62.09910814650357;
                                attribute 'σ_Cz' : Real = 29.057750463592832;
                                attribute Ixx : Real = 0.5609739261604525;
                                attribute 'σ_Ixx' : Real = 0.37074144170588635;
                                attribute Iyy : Real = 0.6079352732051975;
                                attribute 'σ_Iyy' : Real = 0.3723953238821935;
                                attribute Izz : Real = 0.5851442200880124;
                                attribute 'σ_Izz' : Real = 0.37017423652493897;
                                attribute Ixy : Real = -0.050481005002403184;
                                attribute 'σ_Ixy' : Real = 0.02351283871158888;
                                attribute Ixz : Real = -2.863930330591573e-4;
                                attribute 'σ_Ixz' : Real = 0.022566176940390956;
                                attribute Iyz : Real = -3.5979592361950986e-4;
                                attribute 'σ_Iyz' : Real = 0.02209918015384651;
                            }
                            part <'C.1.2.2.1.2.3.3'> 'Part 938' {
                                attribute POIconv : String = "+";
                                attribute Ipoint : Boolean = false;
                                attribute mass : Real = 0.8365796870754566;
                                attribute 'σ_mass' : Real = 0.28909372274994966;
                                attribute Cx : Real = -45.31658664345741;
                                attribute 'σ_Cx' : Real = 28.721044428837228;
                                attribute Cy : Real = -69.40311254002154;
                                attribute 'σ_Cy' : Real = 28.23690002309109;
                                attribute Cz : Real = 55.42219593189657;
                                attribute 'σ_Cz' : Real = 29.057750463592832;
                                attribute Ixx : Real = 1.1416474236276872;
                                attribute 'σ_Ixx' : Real = 0.37074144170588635;
                                attribute Iyy : Real = 1.1278183915803692;
                                attribute 'σ_Iyy' : Real = 0.3723953238821935;
                                attribute Izz : Real = 1.0989815533828418;
                                attribute 'σ_Izz' : Real = 0.37017423652493897;
                                attribute Ixy : Real = -0.010554908537077475;
                                attribute 'σ_Ixy' : Real = 0.02351283871158888;
                                attribute Ixz : Real = 0.017130195610554688;
                                attribute 'σ_Ixz' : Real = 0.022566176940390956;
                                attribute Iyz : Real = 0.00880700266928349;
                                attribute 'σ_Iyz' : Real = 0.02209918015384651;
                            }
                        }
                    }
                }
                part <'C.1.2.2.2'> 'Subsystem 21' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.2.2.2.1'> 'Assembly 77' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.2.2.1.1'> 'Subassembly 267' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.1.1.1'> 'Part 939' {
                                attribute POIconv : String = "-";
                                attribute Ipoint : Boolean = false;
                                attribute mass : Real = 0.5304808197803795;
                                attribute 'σ_mass' : Real = 0.28909372274994966;
                                attribute Cx : Real = 60.75750580057502;
                                attribute 'σ_Cx' : Real = 28.721044428837228;
                                attribute Cy : Real = -32.76290348730981;
                                attribute 'σ_Cy' : Real = 28.23690002309109;
                                attribute Cz : Real = -84.49718449264765;
                                attribute 'σ_Cz' : Real = 29.057750463592832;
                                attribute Ixx : Real = 0.7213257122723988;
                                attribute 'σ_Ixx' : Real = 0.37074144170588635;
                                attribute Iyy : Real = 0.7234731790778778;
                                attribute 'σ_Iyy' : Real = 0.3723953238821935;
                                attribute Izz : Real = 0.7185367014939027;
                                attribute 'σ_Izz' : Real = 0.37017423652493897;
                                attribute Ixy : Real = 0.01483740539071361;
                                attribute 'σ_Ixy' : Real = 0.02351283871158888;
                                attribute Ixz : Real = 0.04841522530425567;
                                attribute 'σ_Ixz' : Real = 0.022566176940390956;
                                attribute Iyz : Real = 0.028203966781611686;
                                attribute 'σ_Iyz' : Real = 0.02209918015384651;
                            }
                            part <'C.1.2.2.2.1.1.2'> 'Part 940' {
                                attribute POIconv : String = "-";
                                attribute Ipoint : Boolean = false;
                                attribute mass : Real = 0.7308029113435186;
                                attribute 'σ_mass' : Real = 0.28909372274994966;
                                attribute Cx : Real = 91.09971495345235;
                                attribute 'σ_Cx' : Real = 28.721044428837228;
                                attribute Cy : Real = 75.5786759313196;
                                attribute 'σ_Cy' : Real = 28.23690002309109;
                                attribute Cz : Real = 45.52659331820905;
                                attribute 'σ_Cz' : Real = 29.057750463592832;
                                attribute Ixx : Real = 1.007833088478367;
                                attribute 'σ_Ixx' : Real = 0.37074144170588635;
                                attribute Iyy : Real = 0.98129261330428;
                                attribute 'σ_Iyy' : Real = 0.3723953238821935;
                                attribute Izz : Real = 1.023527139249452;
                                attribute 'σ_Izz' : Real = 0.37017423652493897;
                                attribute Ixy : Real = -0.05562443555643414;
                                attribute 'σ_Ixy' : Real = 0.02351283871158888;
                                attribute Ixz : Real = 0.004041145063428419;
                                attribute 'σ_Ixz' : Real = 0.022566176940390956;
                                attribute Iyz : Real = -0.0319486739470413;
                                attribute 'σ_Iyz' : Real = 0.02209918015384651;
                            }
                            part <'C.1.2.2.2.1.1.3'> 'Part 941' {
                                attribute POIconv : String = "-";
                                attribute Ipoint : Boolean = false;
                                attribute mass : Real = 0.4371213127204683;
                                attribute 'σ_mass' : Real = 0.28909372274994966;
                                attribute Cx : Real = -32.463991176337004;
                                attribute 'σ_Cx' : Real = 28.721044428837228;
                                attribute Cy : Real = 73.74017057009041;
                                attribute 'σ_Cy' : Real = 28.23690002309109;
                                attribute Cz : Real = -20.926463743671775;
                                attribute 'σ_Cz' : Real = 29.057750463592832;
                                attribute Ixx : Real = 0.3995857926250314;
                                attribute 'σ_Ixx' : Real = 0.37074144170588635;
                                attribute Iyy : Real = 0.38502937842237395;
                                attribute 'σ_Iyy' : Real = 0.3723953238821935;
                                attribute Izz : Real = 0.41275025534529675;
                                attribute 'σ_Izz' : Real = 0.37017423652493897;
                                attribute Ixy : Real = 0.005558983815707172;
                                attribute 'σ_Ixy' : Real = 0.02351283871158888;
                                attribute Ixz : Real = 0.001144980919016476;
                                attribute 'σ_Ixz' : Real = 0.022566176940390956;
                                attribute Iyz : Real = -0.006669784596549803;
                                attribute 'σ_Iyz' : Real = 0.02209918015384651;
                            }
                        }
                        part <'C.1.2.2.2.1.2'> 'Subassembly 268' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.1.2.1'> 'Part 942' {
                                attribute POIconv : String = "+";
                                attribute Ipoint : Boolean = false;
                                attribute mass : Real = 0.9812123987139203;
                                attribute 'σ_mass' : Real = 0.28909372274994966;
                                attribute Cx : Real = -49.319747276604176;
                                attribute 'σ_Cx' : Real = 28.721044428837228;
                                attribute Cy : Real = 95.33907482400537;
                                attribute 'σ_Cy' : Real = 28.23690002309109;
                                attribute Cz : Real = 55.62381888739765;
                                attribute 'σ_Cz' : Real = 29.057750463592832;
                                attribute Ixx : Real = 1.0006192960276659;
                                attribute 'σ_Ixx' : Real = 0.37074144170588635;
                                attribute Iyy : Real = 1.2084499004363687;
                                attribute 'σ_Iyy' : Real = 0.3723953238821935;
                                attribute Izz : Real = 1.2096661175658778;
                                attribute 'σ_Izz' : Real = 0.37017423652493897;
                                attribute Ixy : Real = 0.011185861634035815;
                                attribute 'σ_Ixy' : Real = 0.02351283871158888;
                                attribute Ixz : Real = -0.012322805038329533;
                                attribute 'σ_Ixz' : Real = 0.022566176940390956;
                                attribute Iyz : Real = -0.0010512235113654103;
                                attribute 'σ_Iyz' : Real = 0.02209918015384651;
                            }
                            part <'C.1.2.2.2.1.2.2'> 'Part 943' {
                                attribute POIconv : String = "+";
                                attribute Ipoint : Boolean = false;
                                attribute mass : Real = 0.7293517280058004;
                                attribute 'σ_mass' : Real = 0.28909372274994966;
                                attribute Cx : Real = -5.361723201349378;
                                attribute 'σ_Cx' : Real = 28.721044428837228;
                                attribute Cy : Real = -43.36663968861103;
                                attribute 'σ_Cy' : Real = 28.23690002309109;
                                attribute Cz : Real = 14.300070377066731;
                                attribute 'σ_Cz' : Real = 29.057750463592832;
                                attribute Ixx : Real = 0.7939805078297852;
                                attribute 'σ_Ixx' : Real = 0.37074144170588635;
                                attribute Iyy : Real = 0.7369344379142871;
                                attribute 'σ_Iyy' : Real = 0.3723953238821935;
                                attribute Izz : Real = 0.722756761171007;
                                attribute 'σ_Izz' : Real = 0.37017423652493897;
                                attribute Ixy : Real = 0.013930435433064506;
                                attribute 'σ_Ixy' : Real = 0.02351283871158888;
                                attribute Ixz : Real = 0.012831483825266419;
                                attribute 'σ_Ixz' : Real = 0.022566176940390956;
                                attribute Iyz : Real = 0.039817308153053003;
                                attribute 'σ_Iyz' : Real = 0.02209918015384651;
                            }
                            part <'C.1.2.2.2.1.2.3'> 'Part 944' {
                                attribute POIconv : String = "-";
                                attribute Ipoint : Boolean = false;
                                attribute mass : Real = 0.42534472983982413;
                                attribute 'σ_mass' : Real = 0.28909372274994966;
                                attribute Cx : Real = 50.050278939306736;
                                attribute 'σ_Cx' : Real = 28.721044428837228;
                                attribute Cy : Real = 15.128774009644985;
                                attribute 'σ_Cy' : Real = 28.23690002309109;
                                attribute Cz : Real = -10.529186390340328;
                                attribute 'σ_Cz' : Real = 29.057750463592832;
                                attribute Ixx : Real = 0.5119424650658849;
                                attribute 'σ_Ixx' : Real = 0.37074144170588635;
                                attribute Iyy : Real = 0.5307585473489143;
                                attribute 'σ_Iyy' : Real = 0.3723953238821935;
                                attribute Izz : Real = 0.5022029988226561;
                                attribute 'σ_Izz' : Real = 0.37017423652493897;
                                attribute Ixy : Real = 0.04111003840472058;
                                attribute 'σ_Ixy' : Real = 0.02351283871158888;
                                attribute Ixz : Real = -0.01496749705211656;
                                attribute 'σ_Ixz' : Real = 0.022566176940390956;
                                attribute Iyz : Real = -0.005191622726144549;
                                attribute 'σ_Iyz' : Real = 0.02209918015384651;
                            }
                            part <'C.1.2.2.2.1.2.4'> 'Part 945' {
                                attribute POIconv : String = "-";
                                attribute Ipoint : Boolean = false;
                                attribute mass : Real = 0.9555976862048264;
                                attribute 'σ_mass' : Real = 0.28909372274994966;
                                attribute Cx : Real = -83.55107973329723;
                                attribute 'σ_Cx' : Real = 28.721044428837228;
                                attribute Cy : Real = -50.43617389164865;
                                attribute 'σ_Cy' : Real = 28.23690002309109;
                                attribute Cz : Real = -85.22074781358242;
                                attribute 'σ_Cz' : Real = 29.057750463592832;
                                attribute Ixx : Real = 1.1672360051465862;
                                attribute 'σ_Ixx' : Real = 0.37074144170588635;
                                attribute Iyy : Real = 1.1837072191293871;
                                attribute 'σ_Iyy' : Real = 0.3723953238821935;
                                attribute Izz : Real = 1.0958214495700125;
                                attribute 'σ_Izz' : Real = 0.37017423652493897;
                                attribute Ixy : Real = -0.0372436406590437;
                                attribute 'σ_Ixy' : Real = 0.02351283871158888;
                                attribute Ixz : Real = -0.07339301728699608;
                                attribute 'σ_Ixz' : Real = 0.022566176940390956;
                                attribute Iyz : Real = -0.06002581903944487;
                                attribute 'σ_Iyz' : Real = 0.02209918015384651;
                            }
                            part <'C.1.2.2.2.1.2.5'> 'Part 946' {
                                attribute POIconv : String = "-";
                                attribute Ipoint : Boolean = false;
                                attribute mass : Real = 0.42094266666821206;
                                attribute 'σ_mass' : Real = 0.28909372274994966;
                                attribute Cx : Real = -7.098900340497494;
                                attribute 'σ_Cx' : Real = 28.721044428837228;
                                attribute Cy : Real = -82.31172608211637;
                                attribute 'σ_Cy' : Real = 28.23690002309109;
                                attribute Cz : Real = 62.75307317264378;
                                attribute 'σ_Cz' : Real = 29.057750463592832;
                                attribute Ixx : Real = 0.5065569279605093;
                                attribute 'σ_Ixx' : Real = 0.37074144170588635;
                                attribute Iyy : Real = 0.5015888289180981;
                                attribute 'σ_Iyy' : Real = 0.3723953238821935;
                                attribute Izz : Real = 0.6041167793917881;
                                attribute 'σ_Izz' : Real = 0.37017423652493897;
                                attribute Ixy : Real = 0.01314653157414077;
                                attribute 'σ_Ixy' : Real = 0.02351283871158888;
                                attribute Ixz : Real = 0.04584804867370509;
                                attribute 'σ_Ixz' : Real = 0.022566176940390956;
                                attribute Iyz : Real = 0.02308903785672673;
                                attribute 'σ_Iyz' : Real = 0.02209918015384651;
                            }
                        }
                        part <'C.1.2.2.2.1.3'> 'Subassembly 269' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.1.3.1'> 'Part 947' {
                                attribute POIconv : String = "-";
                                attribute Ipoint : Boolean = false;
                                attribute mass : Real = 0.3024013258176856;
                                attribute 'σ_mass' : Real = 0.28909372274994966;
                                attribute Cx : Real = 45.85023648105562;
                                attribute 'σ_Cx' : Real = 28.721044428837228;
                                attribute Cy : Real = -3.684002533555031;
                                attribute 'σ_Cy' : Real = 28.23690002309109;
                                attribute Cz : Real = -94.07813153229654;
                                attribute 'σ_Cz' : Real = 29.057750463592832;
                                attribute Ixx : Real = 0.32725238184361594;
                                attribute 'σ_Ixx' : Real = 0.37074144170588635;
                                attribute Iyy : Real = 0.3526668346173522;
                                attribute 'σ_Iyy' : Real = 0.3723953238821935;
                                attribute Izz : Real = 0.3547297689551177;
                                attribute 'σ_Izz' : Real = 0.37017423652493897;
                                attribute Ixy : Real = 0.007379397694733824;
                                attribute 'σ_Ixy' : Real = 0.02351283871158888;
                                attribute Ixz : Real = -0.0018620467074161502;
                                attribute 'σ_Ixz' : Real = 0.022566176940390956;
                                attribute Iyz : Real = -0.002576270043918154;
                                attribute 'σ_Iyz' : Real = 0.02209918015384651;
                            }
                            part <'C.1.2.2.2.1.3.2'> 'Part 948' {
                                attribute POIconv : String = "+";
                                attribute Ipoint : Boolean = false;
                                attribute mass : Real = 0.7712300861815456;
                                attribute 'σ_mass' : Real = 0.28909372274994966;
                                attribute Cx : Real = 86.4832405000925;
                                attribute 'σ_Cx' : Real = 28.721044428837228;
                                attribute Cy : Real = -71.39332671649754;
                                attribute 'σ_Cy' : Real = 28.23690002309109;
                                attribute Cz : Real = 31.37113037519157;
                                attribute 'σ_Cz' : Real = 29.057750463592832;
                                attribute Ixx : Real = 1.0742444285834558;
                                attribute 'σ_Ixx' : Real = 0.37074144170588635;
                                attribute Iyy : Real = 1.0532506291283061;
                                attribute 'σ_Iyy' : Real = 0.3723953238821935;
                                attribute Izz : Real = 1.1129527430470079;
                                attribute 'σ_Izz' : Real = 0.37017423652493897;
                                attribute Ixy : Real = 0.014271390100853461;
                                attribute 'σ_Ixy' : Real = 0.02351283871158888;
                                attribute Ixz : Real = 0.009819387251517993;
                                attribute 'σ_Ixz' : Real = 0.022566176940390956;
                                attribute Iyz : Real = -0.04906542134574031;
                                attribute 'σ_Iyz' : Real = 0.02209918015384651;
                            }
                            part <'C.1.2.2.2.1.3.3'> 'Part 949' {
                                attribute POIconv : String = "-";
                                attribute Ipoint : Boolean = false;
                                attribute mass : Real = 0.6450899850483984;
                                attribute 'σ_mass' : Real = 0.28909372274994966;
                                attribute Cx : Real = -7.571651693433523;
                                attribute 'σ_Cx' : Real = 28.721044428837228;
                                attribute Cy : Real = 91.65872284211218;
                                attribute 'σ_Cy' : Real = 28.23690002309109;
                                attribute Cz : Real = -90.08773728273809;
                                attribute 'σ_Cz' : Real = 29.057750463592832;
                                attribute Ixx : Real = 0.7193817285350733;
                                attribute 'σ_Ixx' : Real = 0.37074144170588635;
                                attribute Iyy : Real = 0.7138839830932242;
                                attribute 'σ_Iyy' : Real = 0.3723953238821935;
                                attribute Izz : Real = 0.6593076541923454;
                                attribute 'σ_Izz' : Real = 0.37017423652493897;
                                attribute Ixy : Real = -0.016593916541461546;
                                attribute 'σ_Ixy' : Real = 0.02351283871158888;
                                attribute Ixz : Real = 0.0011190086397145083;
                                attribute 'σ_Ixz' : Real = 0.022566176940390956;
                                attribute Iyz : Real = 0.01123433779020476;
                                attribute 'σ_Iyz' : Real = 0.02209918015384651;
                            }
                            part <'C.1.2.2.2.1.3.4'> 'Part 950' {
                                attribute POIconv : String = "-";
                                attribute Ipoint : Boolean = false;
                                attribute mass : Real = 0.39505316310282795;
                                attribute 'σ_mass' : Real = 0.28909372274994966;
                                attribute Cx : Real = 24.153555231168866;
                                attribute 'σ_Cx' : Real = 28.721044428837228;
                                attribute Cy : Real = -28.724731458351016;
                                attribute 'σ_Cy' : Real = 28.23690002309109;
                                attribute Cz : Real = 2.1092519629746675;
                                attribute 'σ_Cz' : Real = 29.057750463592832;
                                attribute Ixx : Real = 0.4565105817478127;
                                attribute 'σ_Ixx' : Real = 0.37074144170588635;
                                attribute Iyy : Real = 0.4588437105696054;
                                attribute 'σ_Iyy' : Real = 0.3723953238821935;
                                attribute Izz : Real = 0.46545579412748667;
                                attribute 'σ_Izz' : Real = 0.37017423652493897;
                                attribute Ixy : Real = -0.012915001457887484;
                                attribute 'σ_Ixy' : Real = 0.02351283871158888;
                                attribute Ixz : Real = -0.011585624019641527;
                                attribute 'σ_Ixz' : Real = 0.022566176940390956;
                                attribute Iyz : Real = -0.019275062383034183;
                                attribute 'σ_Iyz' : Real = 0.02209918015384651;
                            }
                            part <'C.1.2.2.2.1.3.5'> 'Part 951' {
                                attribute POIconv : String = "-";
                                attribute Ipoint : Boolean = false;
                                attribute mass : Real = 0.931761880374048;
                                attribute 'σ_mass' : Real = 0.28909372274994966;
                                attribute Cx : Real = -30.304699996486306;
                                attribute 'σ_Cx' : Real = 28.721044428837228;
                                attribute Cy : Real = -91.6789770592004;
                                attribute 'σ_Cy' : Real = 28.23690002309109;
                                attribute Cz : Real = 62.852431274950504;
                                attribute 'σ_Cz' : Real = 29.057750463592832;
                                attribute Ixx : Real = 0.9589455054782718;
                                attribute 'σ_Ixx' : Real = 0.37074144170588635;
                                attribute Iyy : Real = 0.9426141595917784;
                                attribute 'σ_Iyy' : Real = 0.3723953238821935;
                                attribute Izz : Real = 1.1042672268306502;
                                attribute 'σ_Izz' : Real = 0.37017423652493897;
                                attribute Ixy : Real = -0.03446462598165776;
                                attribute 'σ_Ixy' : Real = 0.02351283871158888;
                                attribute Ixz : Real = 0.011123421512644175;
                                attribute 'σ_Ixz' : Real = 0.022566176940390956;
                                attribute Iyz : Real = 0.008326846277428385;
                                attribute 'σ_Iyz' : Real = 0.02209918015384651;
                            }
                        }
                    }
                    part <'C.1.2.2.2.2'> 'Assembly 78' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.2.2.2.1'> 'Subassembly 270' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.2.1.1'> 'Part 952' {
                                attribute POIconv : String = "+";
                                attribute Ipoint : Boolean = false;
                                attribute mass : Real = 0.5570705220787786;
                                attribute 'σ_mass' : Real = 0.28909372274994966;
                                attribute Cx : Real = 30.003085965290666;
                                attribute 'σ_Cx' : Real = 28.721044428837228;
                                attribute Cy : Real = -54.571036621928215;
                                attribute 'σ_Cy' : Real = 28.23690002309109;
                                attribute Cz : Real = 21.27750525251031;
                                attribute 'σ_Cz' : Real = 29.057750463592832;
                                attribute Ixx : Real = 0.7665951074163597;
                                attribute 'σ_Ixx' : Real = 0.37074144170588635;
                                attribute Iyy : Real = 0.6630523085738558;
                                attribute 'σ_Iyy' : Real = 0.3723953238821935;
                                attribute Izz : Real = 0.7396519992902546;
                                attribute 'σ_Izz' : Real = 0.37017423652493897;
                                attribute Ixy : Real = -0.01687849662981117;
                                attribute 'σ_Ixy' : Real = 0.02351283871158888;
                                attribute Ixz : Real = 0.043354766851987636;
                                attribute 'σ_Ixz' : Real = 0.022566176940390956;
                                attribute Iyz : Real = 0.017554973441418563;
                                attribute 'σ_Iyz' : Real = 0.02209918015384651;
                            }
                            part <'C.1.2.2.2.2.1.2'> 'Part 953' {
                                attribute POIconv : String = "+";
                                attribute Ipoint : Boolean = false;
                                attribute mass : Real = 0.23396996997622774;
                                attribute 'σ_mass' : Real = 0.28909372274994966;
                                attribute Cx : Real = 98.9019550383091;
                                attribute 'σ_Cx' : Real = 28.721044428837228;
                                attribute Cy : Real = -30.013889400288463;
                                attribute 'σ_Cy' : Real = 28.23690002309109;
                                attribute Cz : Real = -92.65798064880073;
                                attribute 'σ_Cz' : Real = 29.057750463592832;
                                attribute Ixx : Real = 0.2879445622774804;
                                attribute 'σ_Ixx' : Real = 0.37074144170588635;
                                attribute Iyy : Real = 0.2862266629321412;
                                attribute 'σ_Iyy' : Real = 0.3723953238821935;
                                attribute Izz : Real = 0.3546024794657702;
                                attribute 'σ_Izz' : Real = 0.37017423652493897;
                                attribute Ixy : Real = -0.0037929954483616156;
                                attribute 'σ_Ixy' : Real = 0.02351283871158888;
                                attribute Ixz : Real = 0.02380493223724639;
                                attribute 'σ_Ixz' : Real = 0.022566176940390956;
                                attribute Iyz : Real = 0.0024373370542601913;
                                attribute 'σ_Iyz' : Real = 0.02209918015384651;
                            }
                            part <'C.1.2.2.2.2.1.3'> 'Part 954' {
                                attribute POIconv : String = "-";
                                attribute Ipoint : Boolean = false;
                                attribute mass : Real = 0.86733810041775;
                                attribute 'σ_mass' : Real = 0.28909372274994966;
                                attribute Cx : Real = 18.01522821187973;
                                attribute 'σ_Cx' : Real = 28.721044428837228;
                                attribute Cy : Real = 61.25991437584162;
                                attribute 'σ_Cy' : Real = 28.23690002309109;
                                attribute Cz : Real = -5.63686559908092;
                                attribute 'σ_Cz' : Real = 29.057750463592832;
                                attribute Ixx : Real = 1.1507957085401581;
                                attribute 'σ_Ixx' : Real = 0.37074144170588635;
                                attribute Iyy : Real = 1.1557880380325536;
                                attribute 'σ_Iyy' : Real = 0.3723953238821935;
                                attribute Izz : Real = 1.2012781496508196;
                                attribute 'σ_Izz' : Real = 0.37017423652493897;
                                attribute Ixy : Real = -0.01147436534047317;
                                attribute 'σ_Ixy' : Real = 0.02351283871158888;
                                attribute Ixz : Real = 4.259336001753675e-4;
                                attribute 'σ_Ixz' : Real = 0.022566176940390956;
                                attribute Iyz : Real = 0.005690544168021413;
                                attribute 'σ_Iyz' : Real = 0.02209918015384651;
                            }
                            part <'C.1.2.2.2.2.1.4'> 'Part 955' {
                                attribute POIconv : String = "+";
                                attribute Ipoint : Boolean = false;
                                attribute mass : Real = 0.2448255994936917;
                                attribute 'σ_mass' : Real = 0.28909372274994966;
                                attribute Cx : Real = 70.93952926807106;
                                attribute 'σ_Cx' : Real = 28.721044428837228;
                                attribute Cy : Real = 69.69455098733306;
                                attribute 'σ_Cy' : Real = 28.23690002309109;
                                attribute Cz : Real = -87.3676841147244;
                                attribute 'σ_Cz' : Real = 29.057750463592832;
                                attribute Ixx : Real = 0.3050342462555332;
                                attribute 'σ_Ixx' : Real = 0.37074144170588635;
                                attribute Iyy : Real = 0.3633899289650806;
                                attribute 'σ_Iyy' : Real = 0.3723953238821935;
                                attribute Izz : Real = 0.28125321359133754;
                                attribute 'σ_Izz' : Real = 0.37017423652493897;
                                attribute Ixy : Real = -0.007141392777173988;
                                attribute 'σ_Ixy' : Real = 0.02351283871158888;
                                attribute Ixz : Real = 0.00116163306847005;
                                attribute 'σ_Ixz' : Real = 0.022566176940390956;
                                attribute Iyz : Real = 0.0065718634573092355;
                                attribute 'σ_Iyz' : Real = 0.02209918015384651;
                            }
                        }
                        part <'C.1.2.2.2.2.2'> 'Subassembly 271' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.2.2.1'> 'Part 956' {
                                attribute POIconv : String = "-";
                                attribute Ipoint : Boolean = false;
                                attribute mass : Real = 0.9265268304713536;
                                attribute 'σ_mass' : Real = 0.28909372274994966;
                                attribute Cx : Real = -22.51451276242733;
                                attribute 'σ_Cx' : Real = 28.721044428837228;
                                attribute Cy : Real = -61.963509768247604;
                                attribute 'σ_Cy' : Real = 28.23690002309109;
                                attribute Cz : Real = 55.60203264467418;
                                attribute 'σ_Cz' : Real = 29.057750463592832;
                                attribute Ixx : Real = 0.9988361908372292;
                                attribute 'σ_Ixx' : Real = 0.37074144170588635;
                                attribute Iyy : Real = 1.0387515322180894;
                                attribute 'σ_Iyy' : Real = 0.3723953238821935;
                                attribute Izz : Real = 1.1441927486948744;
                                attribute 'σ_Izz' : Real = 0.37017423652493897;
                                attribute Ixy : Real = 0.11200498302669121;
                                attribute 'σ_Ixy' : Real = 0.02351283871158888;
                                attribute Ixz : Real = -9.169841521839241e-4;
                                attribute 'σ_Ixz' : Real = 0.022566176940390956;
                                attribute Iyz : Real = 0.028143453031371238;
                                attribute 'σ_Iyz' : Real = 0.02209918015384651;
                            }
                            part <'C.1.2.2.2.2.2.2'> 'Part 957' {
                                attribute POIconv : String = "+";
                                attribute Ipoint : Boolean = false;
                                attribute mass : Real = 0.19667191374581308;
                                attribute 'σ_mass' : Real = 0.28909372274994966;
                                attribute Cx : Real = -99.83924245461822;
                                attribute 'σ_Cx' : Real = 28.721044428837228;
                                attribute Cy : Real = -42.325388733297586;
                                attribute 'σ_Cy' : Real = 28.23690002309109;
                                attribute Cz : Real = 63.988291611894965;
                                attribute 'σ_Cz' : Real = 29.057750463592832;
                                attribute Ixx : Real = 0.23759592093800355;
                                attribute 'σ_Ixx' : Real = 0.37074144170588635;
                                attribute Iyy : Real = 0.2494436476457511;
                                attribute 'σ_Iyy' : Real = 0.3723953238821935;
                                attribute Izz : Real = 0.19041222416218706;
                                attribute 'σ_Izz' : Real = 0.37017423652493897;
                                attribute Ixy : Real = -0.0023721276633502306;
                                attribute 'σ_Ixy' : Real = 0.02351283871158888;
                                attribute Ixz : Real = -0.02768849944165324;
                                attribute 'σ_Ixz' : Real = 0.022566176940390956;
                                attribute Iyz : Real = -0.003604262125553083;
                                attribute 'σ_Iyz' : Real = 0.02209918015384651;
                            }
                        }
                        part <'C.1.2.2.2.2.3'> 'Subassembly 272' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.2.3.1'> 'Part 958' {
                                attribute POIconv : String = "-";
                                attribute Ipoint : Boolean = false;
                                attribute mass : Real = 0.6220170653872192;
                                attribute 'σ_mass' : Real = 0.28909372274994966;
                                attribute Cx : Real = -88.4271802380681;
                                attribute 'σ_Cx' : Real = 28.721044428837228;
                                attribute Cy : Real = -81.5281419083476;
                                attribute 'σ_Cy' : Real = 28.23690002309109;
                                attribute Cz : Real = -27.723316801711917;
                                attribute 'σ_Cz' : Real = 29.057750463592832;
                                attribute Ixx : Real = 0.7736162177564065;
                                attribute 'σ_Ixx' : Real = 0.37074144170588635;
                                attribute Iyy : Real = 0.8860050731648637;
                                attribute 'σ_Iyy' : Real = 0.3723953238821935;
                                attribute Izz : Real = 0.7255147558331203;
                                attribute 'σ_Izz' : Real = 0.37017423652493897;
                                attribute Ixy : Real = -0.046987189859727774;
                                attribute 'σ_Ixy' : Real = 0.02351283871158888;
                                attribute Ixz : Real = 0.025245912547133355;
                                attribute 'σ_Ixz' : Real = 0.022566176940390956;
                                attribute Iyz : Real = -0.013774643422691968;
                                attribute 'σ_Iyz' : Real = 0.02209918015384651;
                            }
                            part <'C.1.2.2.2.2.3.2'> 'Part 959' {
                                attribute POIconv : String = "+";
                                attribute Ipoint : Boolean = false;
                                attribute mass : Real = 0.823775424022926;
                                attribute 'σ_mass' : Real = 0.28909372274994966;
                                attribute Cx : Real = -43.416218645870686;
                                attribute 'σ_Cx' : Real = 28.721044428837228;
                                attribute Cy : Real = 71.37513617053628;
                                attribute 'σ_Cy' : Real = 28.23690002309109;
                                attribute Cz : Real = -34.72619606181979;
                                attribute 'σ_Cz' : Real = 29.057750463592832;
                                attribute Ixx : Real = 1.3041354088849226;
                                attribute 'σ_Ixx' : Real = 0.37074144170588635;
                                attribute Iyy : Real = 1.1654770404293808;
                                attribute 'σ_Iyy' : Real = 0.3723953238821935;
                                attribute Izz : Real = 1.1427817380818417;
                                attribute 'σ_Izz' : Real = 0.37017423652493897;
                                attribute Ixy : Real = 0.015010004872013545;
                                attribute 'σ_Ixy' : Real = 0.02351283871158888;
                                attribute Ixz : Real = 0.01782261799650988;
                                attribute 'σ_Ixz' : Real = 0.022566176940390956;
                                attribute Iyz : Real = 0.014099498696372635;
                                attribute 'σ_Iyz' : Real = 0.02209918015384651;
                            }
                            part <'C.1.2.2.2.2.3.3'> 'Part 960' {
                                attribute POIconv : String = "-";
                                attribute Ipoint : Boolean = false;
                                attribute mass : Real = 0.643063347045565;
                                attribute 'σ_mass' : Real = 0.28909372274994966;
                                attribute Cx : Real = 73.45139910466969;
                                attribute 'σ_Cx' : Real = 28.721044428837228;
                                attribute Cy : Real = -93.64247056655586;
                                attribute 'σ_Cy' : Real = 28.23690002309109;
                                attribute Cz : Real = 66.66100104339421;
                                attribute 'σ_Cz' : Real = 29.057750463592832;
                                attribute Ixx : Real = 0.6549345347317238;
                                attribute 'σ_Ixx' : Real = 0.37074144170588635;
                                attribute Iyy : Real = 0.8409070444321589;
                                attribute 'σ_Iyy' : Real = 0.3723953238821935;
                                attribute Izz : Real = 0.7583692077825698;
                                attribute 'σ_Izz' : Real = 0.37017423652493897;
                                attribute Ixy : Real = 0.0428066388724407;
                                attribute 'σ_Ixy' : Real = 0.02351283871158888;
                                attribute Ixz : Real = 0.08521091190831898;
                                attribute 'σ_Ixz' : Real = 0.022566176940390956;
                                attribute Iyz : Real = -0.027444675440931342;
                                attribute 'σ_Iyz' : Real = 0.02209918015384651;
                            }
                            part <'C.1.2.2.2.2.3.4'> 'Part 961' {
                                attribute POIconv : String = "+";
                                attribute Ipoint : Boolean = false;
                                attribute mass : Real = 0.7869032913711853;
                                attribute 'σ_mass' : Real = 0.28909372274994966;
                                attribute Cx : Real = 1.5268539544194937;
                                attribute 'σ_Cx' : Real = 28.721044428837228;
                                attribute Cy : Real = 99.22892670147121;
                                attribute 'σ_Cy' : Real = 28.23690002309109;
                                attribute Cz : Real = 73.58403005637228;
                                attribute 'σ_Cz' : Real = 29.057750463592832;
                                attribute Ixx : Real = 0.7824877417217395;
                                attribute 'σ_Ixx' : Real = 0.37074144170588635;
                                attribute Iyy : Real = 0.7504723209460015;
                                attribute 'σ_Iyy' : Real = 0.3723953238821935;
                                attribute Izz : Real = 0.76235124883583;
                                attribute 'σ_Izz' : Real = 0.37017423652493897;
                                attribute Ixy : Real = 0.010626578362149159;
                                attribute 'σ_Ixy' : Real = 0.02351283871158888;
                                attribute Ixz : Real = 0.005201274982690693;
                                attribute 'σ_Ixz' : Real = 0.022566176940390956;
                                attribute Iyz : Real = -0.01605734714355661;
                                attribute 'σ_Iyz' : Real = 0.02209918015384651;
                            }
                            part <'C.1.2.2.2.2.3.5'> 'Part 962' {
                                attribute POIconv : String = "-";
                                attribute Ipoint : Boolean = false;
                                attribute mass : Real = 0.06666130894469097;
                                attribute 'σ_mass' : Real = 0.28909372274994966;
                                attribute Cx : Real = -40.534817148;
                                attribute 'σ_Cx' : Real = 28.721044428837228;
                                attribute Cy : Real = 60.644725197926164;
                                attribute 'σ_Cy' : Real = 28.23690002309109;
                                attribute Cz : Real = -88.8822975102812;
                                attribute 'σ_Cz' : Real = 29.057750463592832;
                                attribute Ixx : Real = 0.10365734419264018;
                                attribute 'σ_Ixx' : Real = 0.37074144170588635;
                                attribute Iyy : Real = 0.08204556296858923;
                                attribute 'σ_Iyy' : Real = 0.3723953238821935;
                                attribute Izz : Real = 0.08352699397535596;
                                attribute 'σ_Izz' : Real = 0.37017423652493897;
                                attribute Ixy : Real = -5.733377728265961e-5;
                                attribute 'σ_Ixy' : Real = 0.02351283871158888;
                                attribute Ixz : Real = 0.0029487717074824634;
                                attribute 'σ_Ixz' : Real = 0.022566176940390956;
                                attribute Iyz : Real = -3.9419111941320047e-4;
                                attribute 'σ_Iyz' : Real = 0.02209918015384651;
                            }
                        }
                        part <'C.1.2.2.2.2.4'> 'Subassembly 273' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.2.4.1'> 'Part 963' {
                                attribute POIconv : String = "+";
                                attribute Ipoint : Boolean = false;
                                attribute mass : Real = 0.041582843948155646;
                                attribute 'σ_mass' : Real = 0.28909372274994966;
                                attribute Cx : Real = 2.6299283374100924;
                                attribute 'σ_Cx' : Real = 28.721044428837228;
                                attribute Cy : Real = -89.00875230319798;
                                attribute 'σ_Cy' : Real = 28.23690002309109;
                                attribute Cz : Real = 61.91454012878239;
                                attribute 'σ_Cz' : Real = 29.057750463592832;
                                attribute Ixx : Real = 0.06251470225361101;
                                attribute 'σ_Ixx' : Real = 0.37074144170588635;
                                attribute Iyy : Real = 0.06655216657533557;
                                attribute 'σ_Iyy' : Real = 0.3723953238821935;
                                attribute Izz : Real = 0.06251163909186692;
                                attribute 'σ_Izz' : Real = 0.37017423652493897;
                                attribute Ixy : Real = 7.832442366003815e-4;
                                attribute 'σ_Ixy' : Real = 0.02351283871158888;
                                attribute Ixz : Real = 4.6678940832468006e-4;
                                attribute 'σ_Ixz' : Real = 0.022566176940390956;
                                attribute Iyz : Real = -0.0023940572901619975;
                                attribute 'σ_Iyz' : Real = 0.02209918015384651;
                            }
                            part <'C.1.2.2.2.2.4.2'> 'Part 964' {
                                attribute POIconv : String = "-";
                                attribute Ipoint : Boolean = false;
                                attribute mass : Real = 0.3805989583923947;
                                attribute 'σ_mass' : Real = 0.28909372274994966;
                                attribute Cx : Real = -58.100847620517015;
                                attribute 'σ_Cx' : Real = 28.721044428837228;
                                attribute Cy : Real = -47.9768980294466;
                                attribute 'σ_Cy' : Real = 28.23690002309109;
                                attribute Cz : Real = 88.36092092096806;
                                attribute 'σ_Cz' : Real = 29.057750463592832;
                                attribute Ixx : Real = 0.42014221032729493;
                                attribute 'σ_Ixx' : Real = 0.37074144170588635;
                                attribute Iyy : Real = 0.42071249358644336;
                                attribute 'σ_Iyy' : Real = 0.3723953238821935;
                                attribute Izz : Real = 0.38071988731261963;
                                attribute 'σ_Izz' : Real = 0.37017423652493897;
                                attribute Ixy : Real = 0.00327987965315247;
                                attribute 'σ_Ixy' : Real = 0.02351283871158888;
                                attribute Ixz : Real = -0.008576809208006127;
                                attribute 'σ_Ixz' : Real = 0.022566176940390956;
                                attribute Iyz : Real = 0.011310037607792516;
                                attribute 'σ_Iyz' : Real = 0.02209918015384651;
                            }
                            part <'C.1.2.2.2.2.4.3'> 'Part 965' {
                                attribute POIconv : String = "+";
                                attribute Ipoint : Boolean = false;
                                attribute mass : Real = 0.09968985624075867;
                                attribute 'σ_mass' : Real = 0.28909372274994966;
                                attribute Cx : Real = -60.995100950822234;
                                attribute 'σ_Cx' : Real = 28.721044428837228;
                                attribute Cy : Real = 91.09862949699163;
                                attribute 'σ_Cy' : Real = 28.23690002309109;
                                attribute Cz : Real = -9.59267821162939;
                                attribute 'σ_Cz' : Real = 29.057750463592832;
                                attribute Ixx : Real = 0.1594884376434478;
                                attribute 'σ_Ixx' : Real = 0.37074144170588635;
                                attribute Iyy : Real = 0.15928204896182166;
                                attribute 'σ_Iyy' : Real = 0.3723953238821935;
                                attribute Izz : Real = 0.16095520879840836;
                                attribute 'σ_Izz' : Real = 0.37017423652493897;
                                attribute Ixy : Real = -0.0016440301855379074;
                                attribute 'σ_Ixy' : Real = 0.02351283871158888;
                                attribute Ixz : Real = 2.1439563241317495e-4;
                                attribute 'σ_Ixz' : Real = 0.022566176940390956;
                                attribute Iyz : Real = -2.172842045158165e-4;
                                attribute 'σ_Iyz' : Real = 0.02209918015384651;
                            }
                        }
                    }
                    part <'C.1.2.2.2.3'> 'Assembly 79' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.2.2.3.1'> 'Subassembly 274' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.3.1.1'> 'Part 966' {
                                attribute POIconv : String = "-";
                                attribute Ipoint : Boolean = false;
                                attribute mass : Real = 0.345393353250809;
                                attribute 'σ_mass' : Real = 0.28909372274994966;
                                attribute Cx : Real = 49.225673638284206;
                                attribute 'σ_Cx' : Real = 28.721044428837228;
                                attribute Cy : Real = -13.037929870188236;
                                attribute 'σ_Cy' : Real = 28.23690002309109;
                                attribute Cz : Real = -34.64252627454698;
                                attribute 'σ_Cz' : Real = 29.057750463592832;
                                attribute Ixx : Real = 0.47913723832637867;
                                attribute 'σ_Ixx' : Real = 0.37074144170588635;
                                attribute Iyy : Real = 0.4586625256694213;
                                attribute 'σ_Iyy' : Real = 0.3723953238821935;
                                attribute Izz : Real = 0.47473932191825574;
                                attribute 'σ_Izz' : Real = 0.37017423652493897;
                                attribute Ixy : Real = 0.017509495424065775;
                                attribute 'σ_Ixy' : Real = 0.02351283871158888;
                                attribute Ixz : Real = -0.02868000192956314;
                                attribute 'σ_Ixz' : Real = 0.022566176940390956;
                                attribute Iyz : Real = 0.002978637095086272;
                                attribute 'σ_Iyz' : Real = 0.02209918015384651;
                            }
                            part <'C.1.2.2.2.3.1.2'> 'Part 967' {
                                attribute POIconv : String = "+";
                                attribute Ipoint : Boolean = false;
                                attribute mass : Real = 0.147076126674423;
                                attribute 'σ_mass' : Real = 0.28909372274994966;
                                attribute Cx : Real = 72.91318336501718;
                                attribute 'σ_Cx' : Real = 28.721044428837228;
                                attribute Cy : Real = 25.294630136340857;
                                attribute 'σ_Cy' : Real = 28.23690002309109;
                                attribute Cz : Real = 6.516283191740513;
                                attribute 'σ_Cz' : Real = 29.057750463592832;
                                attribute Ixx : Real = 0.21739396030556551;
                                attribute 'σ_Ixx' : Real = 0.37074144170588635;
                                attribute Iyy : Real = 0.23286888073360199;
                                attribute 'σ_Iyy' : Real = 0.3723953238821935;
                                attribute Izz : Real = 0.22638707764568097;
                                attribute 'σ_Izz' : Real = 0.37017423652493897;
                                attribute Ixy : Real = 6.615551163557344e-4;
                                attribute 'σ_Ixy' : Real = 0.02351283871158888;
                                attribute Ixz : Real = 0.0015978837683497038;
                                attribute 'σ_Ixz' : Real = 0.022566176940390956;
                                attribute Iyz : Real = 3.3473494387656984e-4;
                                attribute 'σ_Iyz' : Real = 0.02209918015384651;
                            }
                            part <'C.1.2.2.2.3.1.3'> 'Part 968' {
                                attribute POIconv : String = "-";
                                attribute Ipoint : Boolean = false;
                                attribute mass : Real = 0.5250803465456702;
                                attribute 'σ_mass' : Real = 0.28909372274994966;
                                attribute Cx : Real = 41.28240216523409;
                                attribute 'σ_Cx' : Real = 28.721044428837228;
                                attribute Cy : Real = 56.341146072372794;
                                attribute 'σ_Cy' : Real = 28.23690002309109;
                                attribute Cz : Real = 29.793682508170605;
                                attribute 'σ_Cz' : Real = 29.057750463592832;
                                attribute Ixx : Real = 0.6142898985369039;
                                attribute 'σ_Ixx' : Real = 0.37074144170588635;
                                attribute Iyy : Real = 0.6230022973423036;
                                attribute 'σ_Iyy' : Real = 0.3723953238821935;
                                attribute Izz : Real = 0.6394846616925042;
                                attribute 'σ_Izz' : Real = 0.37017423652493897;
                                attribute Ixy : Real = 0.06041707099300492;
                                attribute 'σ_Ixy' : Real = 0.02351283871158888;
                                attribute Ixz : Real = 0.04082566972114808;
                                attribute 'σ_Ixz' : Real = 0.022566176940390956;
                                attribute Iyz : Real = -0.012794288708073476;
                                attribute 'σ_Iyz' : Real = 0.02209918015384651;
                            }
                            part <'C.1.2.2.2.3.1.4'> 'Part 969' {
                                attribute POIconv : String = "+";
                                attribute Ipoint : Boolean = false;
                                attribute mass : Real = 0.4892021876189392;
                                attribute 'σ_mass' : Real = 0.28909372274994966;
                                attribute Cx : Real = -14.718003058806062;
                                attribute 'σ_Cx' : Real = 28.721044428837228;
                                attribute Cy : Real = -77.48289168812335;
                                attribute 'σ_Cy' : Real = 28.23690002309109;
                                attribute Cz : Real = -9.802870312705636;
                                attribute 'σ_Cz' : Real = 29.057750463592832;
                                attribute Ixx : Real = 0.6526306182681287;
                                attribute 'σ_Ixx' : Real = 0.37074144170588635;
                                attribute Iyy : Real = 0.5867509579436452;
                                attribute 'σ_Iyy' : Real = 0.3723953238821935;
                                attribute Izz : Real = 0.5518915429797854;
                                attribute 'σ_Izz' : Real = 0.37017423652493897;
                                attribute Ixy : Real = 0.06013613675420441;
                                attribute 'σ_Ixy' : Real = 0.02351283871158888;
                                attribute Ixz : Real = 0.004444479745731449;
                                attribute 'σ_Ixz' : Real = 0.022566176940390956;
                                attribute Iyz : Real = -0.002495198961270224;
                                attribute 'σ_Iyz' : Real = 0.02209918015384651;
                            }
                            part <'C.1.2.2.2.3.1.5'> 'Part 970' {
                                attribute POIconv : String = "-";
                                attribute Ipoint : Boolean = false;
                                attribute mass : Real = 0.3681091385083273;
                                attribute 'σ_mass' : Real = 0.28909372274994966;
                                attribute Cx : Real = 53.410716308280826;
                                attribute 'σ_Cx' : Real = 28.721044428837228;
                                attribute Cy : Real = 36.58010014332831;
                                attribute 'σ_Cy' : Real = 28.23690002309109;
                                attribute Cz : Real = 64.2720723990351;
                                attribute 'σ_Cz' : Real = 29.057750463592832;
                                attribute Ixx : Real = 0.4316995717801538;
                                attribute 'σ_Ixx' : Real = 0.37074144170588635;
                                attribute Iyy : Real = 0.45032304653763955;
                                attribute 'σ_Iyy' : Real = 0.3723953238821935;
                                attribute Izz : Real = 0.40388473713453177;
                                attribute 'σ_Izz' : Real = 0.37017423652493897;
                                attribute Ixy : Real = -0.006765216340014524;
                                attribute 'σ_Ixy' : Real = 0.02351283871158888;
                                attribute Ixz : Real = -0.005028606381440707;
                                attribute 'σ_Ixz' : Real = 0.022566176940390956;
                                attribute Iyz : Real = -0.01898847873314777;
                                attribute 'σ_Iyz' : Real = 0.02209918015384651;
                            }
                        }
                        part <'C.1.2.2.2.3.2'> 'Subassembly 275' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.3.2.1'> 'Part 971' {
                                attribute POIconv : String = "+";
                                attribute Ipoint : Boolean = false;
                                attribute mass : Real = 0.2022086534788832;
                                attribute 'σ_mass' : Real = 0.28909372274994966;
                                attribute Cx : Real = 50.79826274886727;
                                attribute 'σ_Cx' : Real = 28.721044428837228;
                                attribute Cy : Real = -89.359991904348135;
                                attribute 'σ_Cy' : Real = 28.23690002309109;
                                attribute Cz : Real = -90.66908159293234;
                                attribute 'σ_Cz' : Real = 29.057750463592832;
                                attribute Ixx : Real = 0.304458476429242;
                                attribute 'σ_Ixx' : Real = 0.37074144170588635;
                                attribute Iyy : Real = 0.2881186650118538;
                                attribute 'σ_Iyy' : Real = 0.3723953238821935;
                                attribute Izz : Real = 0.3122199907550542;
                                attribute 'σ_Izz' : Real = 0.37017423652493897;
                                attribute Ixy : Real = 0.007494641712167683;
                                attribute 'σ_Ixy' : Real = 0.02351283871158888;
                                attribute Ixz : Real = 0.022637634702947024;
                                attribute 'σ_Ixz' : Real = 0.022566176940390956;
                                attribute Iyz : Real = -0.007655420762313105;
                                attribute 'σ_Iyz' : Real = 0.02209918015384651;
                            }
                            part <'C.1.2.2.2.3.2.2'> 'Part 972' {
                                attribute POIconv : String = "-";
                                attribute Ipoint : Boolean = false;
                                attribute mass : Real = 0.7260099024197553;
                                attribute 'σ_mass' : Real = 0.28909372274994966;
                                attribute Cx : Real = 65.38590369746089;
                                attribute 'σ_Cx' : Real = 28.721044428837228;
                                attribute Cy : Real = -32.00422446243465;
                                attribute 'σ_Cy' : Real = 28.23690002309109;
                                attribute Cz : Real = -55.6092987768352;
                                attribute 'σ_Cz' : Real = 29.057750463592832;
                                attribute Ixx : Real = 0.9560992614910911;
                                attribute 'σ_Ixx' : Real = 0.37074144170588635;
                                attribute Iyy : Real = 0.9985063911532315;
                                attribute 'σ_Iyy' : Real = 0.3723953238821935;
                                attribute Izz : Real = 0.9197697673823055;
                                attribute 'σ_Izz' : Real = 0.37017423652493897;
                                attribute Ixy : Real = -0.012492996004439965;
                                attribute 'σ_Ixy' : Real = 0.02351283871158888;
                                attribute Ixz : Real = 0.008983591062734532;
                                attribute 'σ_Ixz' : Real = 0.022566176940390956;
                                attribute Iyz : Real = 0.05464491021346929;
                                attribute 'σ_Iyz' : Real = 0.02209918015384651;
                            }
                            part <'C.1.2.2.2.3.2.3'> 'Part 973' {
                                attribute POIconv : String = "-";
                                attribute Ipoint : Boolean = false;
                                attribute mass : Real = 0.47460219804244114;
                                attribute 'σ_mass' : Real = 0.28909372274994966;
                                attribute Cx : Real = -59.95682361535728;
                                attribute 'σ_Cx' : Real = 28.721044428837228;
                                attribute Cy : Real = 23.87014077976346;
                                attribute 'σ_Cy' : Real = 28.23690002309109;
                                attribute Cz : Real = -2.4481114000082016;
                                attribute 'σ_Cz' : Real = 29.057750463592832;
                                attribute Ixx : Real = 0.5965026386467733;
                                attribute 'σ_Ixx' : Real = 0.37074144170588635;
                                attribute Iyy : Real = 0.5850507321042127;
                                attribute 'σ_Iyy' : Real = 0.3723953238821935;
                                attribute Izz : Real = 0.5739573068366166;
                                attribute 'σ_Izz' : Real = 0.37017423652493897;
                                attribute Ixy : Real = 0.017461955802500373;
                                attribute 'σ_Ixy' : Real = 0.02351283871158888;
                                attribute Ixz : Real = 7.807431255930462e-4;
                                attribute 'σ_Ixz' : Real = 0.022566176940390956;
                                attribute Iyz : Real = -2.0049108263685717e-4;
                                attribute 'σ_Iyz' : Real = 0.02209918015384651;
                            }
                            part <'C.1.2.2.2.3.2.4'> 'Part 974' {
                                attribute POIconv : String = "+";
                                attribute Ipoint : Boolean = false;
                                attribute mass : Real = 0.7313970257029868;
                                attribute 'σ_mass' : Real = 0.28909372274994966;
                                attribute Cx : Real = 33.90182601287961;
                                attribute 'σ_Cx' : Real = 28.721044428837228;
                                attribute Cy : Real = -52.097645588219166;
                                attribute 'σ_Cy' : Real = 28.23690002309109;
                                attribute Cz : Real = 99.86968045122921;
                                attribute 'σ_Cz' : Real = 29.057750463592832;
                                attribute Ixx : Real = 0.8877209397004133;
                                attribute 'σ_Ixx' : Real = 0.37074144170588635;
                                attribute Iyy : Real = 0.9488907643141312;
                                attribute 'σ_Iyy' : Real = 0.3723953238821935;
                                attribute Izz : Real = 0.8792649348780672;
                                attribute 'σ_Izz' : Real = 0.37017423652493897;
                                attribute Ixy : Real = 0.022408164986990456;
                                attribute 'σ_Ixy' : Real = 0.02351283871158888;
                                attribute Ixz : Real = 0.0759425053446322;
                                attribute 'σ_Ixz' : Real = 0.022566176940390956;
                                attribute Iyz : Real = 0.0380751266551434;
                                attribute 'σ_Iyz' : Real = 0.02209918015384651;
                            }
                        }
                        part <'C.1.2.2.2.3.3'> 'Subassembly 276' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.3.3.1'> 'Part 975' {
                                attribute POIconv : String = "-";
                                attribute Ipoint : Boolean = false;
                                attribute mass : Real = 0.7002253949027508;
                                attribute 'σ_mass' : Real = 0.28909372274994966;
                                attribute Cx : Real = -48.32895137369633;
                                attribute 'σ_Cx' : Real = 28.721044428837228;
                                attribute Cy : Real = 94.38803419470787;
                                attribute 'σ_Cy' : Real = 28.23690002309109;
                                attribute Cz : Real = -73.54296059347689;
                                attribute 'σ_Cz' : Real = 29.057750463592832;
                                attribute Ixx : Real = 0.9179289537677093;
                                attribute 'σ_Ixx' : Real = 0.37074144170588635;
                                attribute Iyy : Real = 0.9453526066367571;
                                attribute 'σ_Iyy' : Real = 0.3723953238821935;
                                attribute Izz : Real = 1.0598639204396196;
                                attribute 'σ_Izz' : Real = 0.37017423652493897;
                                attribute Ixy : Real = 0.005793379845730145;
                                attribute 'σ_Ixy' : Real = 0.02351283871158888;
                                attribute Ixz : Real = 0.009932665524244062;
                                attribute 'σ_Ixz' : Real = 0.022566176940390956;
                                attribute Iyz : Real = -0.003364331952347276;
                                attribute 'σ_Iyz' : Real = 0.02209918015384651;
                            }
                            part <'C.1.2.2.2.3.3.2'> 'Part 976' {
                                attribute POIconv : String = "+";
                                attribute Ipoint : Boolean = false;
                                attribute mass : Real = 0.7271825440614484;
                                attribute 'σ_mass' : Real = 0.28909372274994966;
                                attribute Cx : Real = -27.61601754464209;
                                attribute 'σ_Cx' : Real = 28.721044428837228;
                                attribute Cy : Real = -61.12668598070741;
                                attribute 'σ_Cy' : Real = 28.23690002309109;
                                attribute Cz : Real = -75.3458530176431;
                                attribute 'σ_Cz' : Real = 29.057750463592832;
                                attribute Ixx : Real = 0.9541210459817209;
                                attribute 'σ_Ixx' : Real = 0.37074144170588635;
                                attribute Iyy : Real = 0.9697491713331543;
                                attribute 'σ_Iyy' : Real = 0.3723953238821935;
                                attribute Izz : Real = 1.1351335287392776;
                                attribute 'σ_Izz' : Real = 0.37017423652493897;
                                attribute Ixy : Real = 0.005582495038339213;
                                attribute 'σ_Ixy' : Real = 0.02351283871158888;
                                attribute Ixz : Real = 0.006671195595068952;
                                attribute 'σ_Ixz' : Real = 0.022566176940390956;
                                attribute Iyz : Real = 0.0011535569103235399;
                                attribute 'σ_Iyz' : Real = 0.02209918015384651;
                            }
                            part <'C.1.2.2.2.3.3.3'> 'Part 977' {
                                attribute POIconv : String = "-";
                                attribute Ipoint : Boolean = false;
                                attribute mass : Real = 0.38601829275116323;
                                attribute 'σ_mass' : Real = 0.28909372274994966;
                                attribute Cx : Real = 10.229263873770833;
                                attribute 'σ_Cx' : Real = 28.721044428837228;
                                attribute Cy : Real = 32.793070236220956;
                                attribute 'σ_Cy' : Real = 28.23690002309109;
                                attribute Cz : Real = 30.60879916884005;
                                attribute 'σ_Cz' : Real = 29.057750463592832;
                                attribute Ixx : Real = 0.4794250298044296;
                                attribute 'σ_Ixx' : Real = 0.37074144170588635;
                                attribute Iyy : Real = 0.4519723346396494;
                                attribute 'σ_Iyy' : Real = 0.3723953238821935;
                                attribute Izz : Real = 0.473361332684626;
                                attribute 'σ_Izz' : Real = 0.37017423652493897;
                                attribute Ixy : Real = -0.02470872411088412;
                                attribute 'σ_Ixy' : Real = 0.02351283871158888;
                                attribute Ixz : Real = -0.016706551862551232;
                                attribute 'σ_Ixz' : Real = 0.022566176940390956;
                                attribute Iyz : Real = 0.00608256028791015;
                                attribute 'σ_Iyz' : Real = 0.02209918015384651;
                            }
                            part <'C.1.2.2.2.3.3.4'> 'Part 978' {
                                attribute POIconv : String = "-";
                                attribute Ipoint : Boolean = false;
                                attribute mass : Real = 0.29627420678082855;
                                attribute 'σ_mass' : Real = 0.28909372274994966;
                                attribute Cx : Real = -1.0771852917969227;
                                attribute 'σ_Cx' : Real = 28.721044428837228;
                                attribute Cy : Real = -32.89890778250992;
                                attribute 'σ_Cy' : Real = 28.23690002309109;
                                attribute Cz : Real = -20.413750782608986;
                                attribute 'σ_Cz' : Real = 29.057750463592832;
                                attribute Ixx : Real = 0.3830441099038879;
                                attribute 'σ_Ixx' : Real = 0.37074144170588635;
                                attribute Iyy : Real = 0.4326566646366207;
                                attribute 'σ_Iyy' : Real = 0.3723953238821935;
                                attribute Izz : Real = 0.372606716061135;
                                attribute 'σ_Izz' : Real = 0.37017423652493897;
                                attribute Ixy : Real = 0.019626688675236842;
                                attribute 'σ_Ixy' : Real = 0.02351283871158888;
                                attribute Ixz : Real = 0.011439537622117968;
                                attribute 'σ_Ixz' : Real = 0.022566176940390956;
                                attribute Iyz : Real = 0.01459983770374012;
                                attribute 'σ_Iyz' : Real = 0.02209918015384651;
                            }
                        }
                        part <'C.1.2.2.2.3.4'> 'Subassembly 277' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.3.4.1'> 'Part 979' {
                                attribute POIconv : String = "-";
                                attribute Ipoint : Boolean = false;
                                attribute mass : Real = 0.27105822088592685;
                                attribute 'σ_mass' : Real = 0.28909372274994966;
                                attribute Cx : Real = -9.020871249958873;
                                attribute 'σ_Cx' : Real = 28.721044428837228;
                                attribute Cy : Real = 94.69756302423775;
                                attribute 'σ_Cy' : Real = 28.23690002309109;
                                attribute Cz : Real = -74.91972697898746;
                                attribute 'σ_Cz' : Real = 29.057750463592832;
                                attribute Ixx : Real = 0.39951975900346126;
                                attribute 'σ_Ixx' : Real = 0.37074144170588635;
                                attribute Iyy : Real = 0.4168247106634905;
                                attribute 'σ_Iyy' : Real = 0.3723953238821935;
                                attribute Izz : Real = 0.38660585833770034;
                                attribute 'σ_Izz' : Real = 0.37017423652493897;
                                attribute Ixy : Real = 0.02142547459437949;
                                attribute 'σ_Ixy' : Real = 0.02351283871158888;
                                attribute Ixz : Real = -0.006735890149523673;
                                attribute 'σ_Ixz' : Real = 0.022566176940390956;
                                attribute Iyz : Real = -0.010790705266209476;
                                attribute 'σ_Iyz' : Real = 0.02209918015384651;
                            }
                            part <'C.1.2.2.2.3.4.2'> 'Part 980' {
                                attribute POIconv : String = "-";
                                attribute Ipoint : Boolean = false;
                                attribute mass : Real = 0.887400543800788;
                                attribute 'σ_mass' : Real = 0.28909372274994966;
                                attribute Cx : Real = -78.64561681635678;
                                attribute 'σ_Cx' : Real = 28.721044428837228;
                                attribute Cy : Real = -30.86143396794796;
                                attribute 'σ_Cy' : Real = 28.23690002309109;
                                attribute Cz : Real = 81.71482505276799;
                                attribute 'σ_Cz' : Real = 29.057750463592832;
                                attribute Ixx : Real = 1.0497478499469302;
                                attribute 'σ_Ixx' : Real = 0.37074144170588635;
                                attribute Iyy : Real = 1.127254465104757;
                                attribute 'σ_Iyy' : Real = 0.3723953238821935;
                                attribute Izz : Real = 1.0835139532825706;
                                attribute 'σ_Izz' : Real = 0.37017423652493897;
                                attribute Ixy : Real = 0.0013066053331645168;
                                attribute 'σ_Ixy' : Real = 0.02351283871158888;
                                attribute Ixz : Real = 0.025583120864450644;
                                attribute 'σ_Ixz' : Real = 0.022566176940390956;
                                attribute Iyz : Real = -0.05861376076331369;
                                attribute 'σ_Iyz' : Real = 0.02209918015384651;
                            }
                            part <'C.1.2.2.2.3.4.3'> 'Part 981' {
                                attribute POIconv : String = "+";
                                attribute Ipoint : Boolean = false;
                                attribute mass : Real = 0.18562814097455702;
                                attribute 'σ_mass' : Real = 0.28909372274994966;
                                attribute Cx : Real = 49.00281825102866;
                                attribute 'σ_Cx' : Real = 28.721044428837228;
                                attribute Cy : Real = -38.7052065692842;
                                attribute 'σ_Cy' : Real = 28.23690002309109;
                                attribute Cz : Real = -38.003188418224454;
                                attribute 'σ_Cz' : Real = 29.057750463592832;
                                attribute Ixx : Real = 0.2746480668830507;
                                attribute 'σ_Ixx' : Real = 0.37074144170588635;
                                attribute Iyy : Real = 0.24110169344856022;
                                attribute 'σ_Iyy' : Real = 0.3723953238821935;
                                attribute Izz : Real = 0.25797114857032255;
                                attribute 'σ_Izz' : Real = 0.37017423652493897;
                                attribute Ixy : Real = 0.011830825459521818;
                                attribute 'σ_Ixy' : Real = 0.02351283871158888;
                                attribute Ixz : Real = -0.0054154966043420275;
                                attribute 'σ_Ixz' : Real = 0.022566176940390956;
                                attribute Iyz : Real = -3.837476468564319e-4;
                                attribute 'σ_Iyz' : Real = 0.02209918015384651;
                            }
                            part <'C.1.2.2.2.3.4.4'> 'Part 982' {
                                attribute POIconv : String = "+";
                                attribute Ipoint : Boolean = false;
                                attribute mass : Real = 0.676604886027053;
                                attribute 'σ_mass' : Real = 0.28909372274994966;
                                attribute Cx : Real = -4.235508479177952;
                                attribute 'σ_Cx' : Real = 28.721044428837228;
                                attribute Cy : Real = -88.00108162686229;
                                attribute 'σ_Cy' : Real = 28.23690002309109;
                                attribute Cz : Real = -14.42916439846158;
                                attribute 'σ_Cz' : Real = 29.057750463592832;
                                attribute Ixx : Real = 0.7873501772649654;
                                attribute 'σ_Ixx' : Real = 0.37074144170588635;
                                attribute Iyy : Real = 0.9006000958302612;
                                attribute 'σ_Iyy' : Real = 0.3723953238821935;
                                attribute Izz : Real = 0.7933242008254806;
                                attribute 'σ_Izz' : Real = 0.37017423652493897;
                                attribute Ixy : Real = -0.0555925947585104;
                                attribute 'σ_Ixy' : Real = 0.02351283871158888;
                                attribute Ixz : Real = -0.03199452924541006;
                                attribute 'σ_Ixz' : Real = 0.022566176940390956;
                                attribute Iyz : Real = 0.03426014756302768;
                                attribute 'σ_Iyz' : Real = 0.02209918015384651;
                            }
                            part <'C.1.2.2.2.3.4.5'> 'Part 983' {
                                attribute POIconv : String = "-";
                                attribute Ipoint : Boolean = false;
                                attribute mass : Real = 0.9299982009441592;
                                attribute 'σ_mass' : Real = 0.28909372274994966;
                                attribute Cx : Real = 94.47850789874792;
                                attribute 'σ_Cx' : Real = 28.721044428837228;
                                attribute Cy : Real = 83.77207573503256;
                                attribute 'σ_Cy' : Real = 28.23690002309109;
                                attribute Cz : Real = -11.404815874993801;
                                attribute 'σ_Cz' : Real = 29.057750463592832;
                                attribute Ixx : Real = 0.9704152538984083;
                                attribute 'σ_Ixx' : Real = 0.37074144170588635;
                                attribute Iyy : Real = 1.096893040094133;
                                attribute 'σ_Iyy' : Real = 0.3723953238821935;
                                attribute Izz : Real = 1.1274372848676895;
                                attribute 'σ_Izz' : Real = 0.37017423652493897;
                                attribute Ixy : Real = 0.12173459347731425;
                                attribute 'σ_Ixy' : Real = 0.02351283871158888;
                                attribute Ixz : Real = -0.0744546613558762;
                                attribute 'σ_Ixz' : Real = 0.022566176940390956;
                                attribute Iyz : Real = 0.0017807762575389099;
                                attribute 'σ_Iyz' : Real = 0.02209918015384651;
                            }
                        }
                    }
                    part <'C.1.2.2.2.4'> 'Assembly 80' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.2.2.4.1'> 'Subassembly 278' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.4.1.1'> 'Part 984' {
                                attribute POIconv : String = "-";
                                attribute Ipoint : Boolean = false;
                                attribute mass : Real = 0.9030830010336358;
                                attribute 'σ_mass' : Real = 0.28909372274994966;
                                attribute Cx : Real = 36.13886944949627;
                                attribute 'σ_Cx' : Real = 28.721044428837228;
                                attribute Cy : Real = -30.839394126087427;
                                attribute 'σ_Cy' : Real = 28.23690002309109;
                                attribute Cz : Real = 77.82481363974512;
                                attribute 'σ_Cz' : Real = 29.057750463592832;
                                attribute Ixx : Real = 1.1268388168502792;
                                attribute 'σ_Ixx' : Real = 0.37074144170588635;
                                attribute Iyy : Real = 1.2171843808899903;
                                attribute 'σ_Iyy' : Real = 0.3723953238821935;
                                attribute Izz : Real = 1.1231479180062338;
                                attribute 'σ_Izz' : Real = 0.37017423652493897;
                                attribute Ixy : Real = -0.08846523203018197;
                                attribute 'σ_Ixy' : Real = 0.02351283871158888;
                                attribute Ixz : Real = 0.09914636000065566;
                                attribute 'σ_Ixz' : Real = 0.022566176940390956;
                                attribute Iyz : Real = -0.08055238601559153;
                                attribute 'σ_Iyz' : Real = 0.02209918015384651;
                            }
                            part <'C.1.2.2.2.4.1.2'> 'Part 985' {
                                attribute POIconv : String = "-";
                                attribute Ipoint : Boolean = false;
                                attribute mass : Real = 0.3415137503563892;
                                attribute 'σ_mass' : Real = 0.28909372274994966;
                                attribute Cx : Real = 97.62425692752004;
                                attribute 'σ_Cx' : Real = 28.721044428837228;
                                attribute Cy : Real = -79.90222480148077;
                                attribute 'σ_Cy' : Real = 28.23690002309109;
                                attribute Cz : Real = -94.51555516570807;
                                attribute 'σ_Cz' : Real = 29.057750463592832;
                                attribute Ixx : Real = 0.4679269479194403;
                                attribute 'σ_Ixx' : Real = 0.37074144170588635;
                                attribute Iyy : Real = 0.4454066207291212;
                                attribute 'σ_Iyy' : Real = 0.3723953238821935;
                                attribute Izz : Real = 0.5002983039618605;
                                attribute 'σ_Izz' : Real = 0.37017423652493897;
                                attribute Ixy : Real = -6.597816268589537e-4;
                                attribute 'σ_Ixy' : Real = 0.02351283871158888;
                                attribute Ixz : Real = 0.03247867099086059;
                                attribute 'σ_Ixz' : Real = 0.022566176940390956;
                                attribute Iyz : Real = -0.00825297436467821;
                                attribute 'σ_Iyz' : Real = 0.02209918015384651;
                            }
                            part <'C.1.2.2.2.4.1.3'> 'Part 986' {
                                attribute POIconv : String = "+";
                                attribute Ipoint : Boolean = false;
                                attribute mass : Real = 0.07597253154916689;
                                attribute 'σ_mass' : Real = 0.28909372274994966;
                                attribute Cx : Real = -20.72984711267054;
                                attribute 'σ_Cx' : Real = 28.721044428837228;
                                attribute Cy : Real = 79.02218238450587;
                                attribute 'σ_Cy' : Real = 28.23690002309109;
                                attribute Cz : Real = 64.00230983272195;
                                attribute 'σ_Cz' : Real = 29.057750463592832;
                                attribute Ixx : Real = 0.09544365421840321;
                                attribute 'σ_Ixx' : Real = 0.37074144170588635;
                                attribute Iyy : Real = 0.09426236339841801;
                                attribute 'σ_Iyy' : Real = 0.3723953238821935;
                                attribute Izz : Real = 0.11696165641742655;
                                attribute 'σ_Izz' : Real = 0.37017423652493897;
                                attribute Ixy : Real = 0.0033198360274207302;
                                attribute 'σ_Ixy' : Real = 0.02351283871158888;
                                attribute Ixz : Real = 1.5352305710691155e-5;
                                attribute 'σ_Ixz' : Real = 0.022566176940390956;
                                attribute Iyz : Real = 4.469069577196507e-4;
                                attribute 'σ_Iyz' : Real = 0.02209918015384651;
                            }
                        }
                        part <'C.1.2.2.2.4.2'> 'Subassembly 279' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.4.2.1'> 'Part 987' {
                                attribute POIconv : String = "+";
                                attribute Ipoint : Boolean = false;
                                attribute mass : Real = 0.21710612030676565;
                                attribute 'σ_mass' : Real = 0.28909372274994966;
                                attribute Cx : Real = 82.39852315746248;
                                attribute 'σ_Cx' : Real = 28.721044428837228;
                                attribute Cy : Real = -78.42894098721445;
                                attribute 'σ_Cy' : Real = 28.23690002309109;
                                attribute Cz : Real = -16.184576554223895;
                                attribute 'σ_Cz' : Real = 29.057750463592832;
                                attribute Ixx : Real = 0.26668405798555145;
                                attribute 'σ_Ixx' : Real = 0.37074144170588635;
                                attribute Iyy : Real = 0.27468988228096763;
                                attribute 'σ_Iyy' : Real = 0.3723953238821935;
                                attribute Izz : Real = 0.2675272316883201;
                                attribute 'σ_Izz' : Real = 0.37017423652493897;
                                attribute Ixy : Real = 0.0029725788459559724;
                                attribute 'σ_Ixy' : Real = 0.02351283871158888;
                                attribute Ixz : Real = -5.922818851304952e-4;
                                attribute 'σ_Ixz' : Real = 0.022566176940390956;
                                attribute Iyz : Real = 0.0022198716083646182;
                                attribute 'σ_Iyz' : Real = 0.02209918015384651;
                            }
                            part <'C.1.2.2.2.4.2.2'> 'Part 988' {
                                attribute POIconv : String = "-";
                                attribute Ipoint : Boolean = false;
                                attribute mass : Real = 0.49863429153943434;
                                attribute 'σ_mass' : Real = 0.28909372274994966;
                                attribute Cx : Real = -42.80372844077647;
                                attribute 'σ_Cx' : Real = 28.721044428837228;
                                attribute Cy : Real = 95.792077062651515;
                                attribute 'σ_Cy' : Real = 28.23690002309109;
                                attribute Cz : Real = 73.12487671151757;
                                attribute 'σ_Cz' : Real = 29.057750463592832;
                                attribute Ixx : Real = 0.5813596533493391;
                                attribute 'σ_Ixx' : Real = 0.37074144170588635;
                                attribute Iyy : Real = 0.5358367288501008;
                                attribute 'σ_Iyy' : Real = 0.3723953238821935;
                                attribute Izz : Real = 0.585394063557518;
                                attribute 'σ_Izz' : Real = 0.37017423652493897;
                                attribute Ixy : Real = 0.006298687734254323;
                                attribute 'σ_Ixy' : Real = 0.02351283871158888;
                                attribute Ixz : Real = 0.031030187734254443;
                                attribute 'σ_Ixz' : Real = 0.022566176940390956;
                                attribute Iyz : Real = -0.04051270492051397;
                                attribute 'σ_Iyz' : Real = 0.02209918015384651;
                            }
                            part <'C.1.2.2.2.4.2.3'> 'Part 989' {
                                attribute POIconv : String = "+";
                                attribute Ipoint : Boolean = false;
                                attribute mass : Real = 0.46388317182497124;
                                attribute 'σ_mass' : Real = 0.28909372274994966;
                                attribute Cx : Real = 2.812653360888362;
                                attribute 'σ_Cx' : Real = 28.721044428837228;
                                attribute Cy : Real = 51.59658817574382;
                                attribute 'σ_Cy' : Real = 28.23690002309109;
                                attribute Cz : Real = 82.1117902174592;
                                attribute 'σ_Cz' : Real = 29.057750463592832;
                                attribute Ixx : Real = 0.6308201406250765;
                                attribute 'σ_Ixx' : Real = 0.37074144170588635;
                                attribute Iyy : Real = 0.603732900834014;
                                attribute 'σ_Iyy' : Real = 0.3723953238821935;
                                attribute Izz : Real = 0.6379810658410099;
                                attribute 'σ_Izz' : Real = 0.37017423652493897;
                                attribute Ixy : Real = -0.01752834907061877;
                                attribute 'σ_Ixy' : Real = 0.02351283871158888;
                                attribute Ixz : Real = 0.003630522253380732;
                                attribute 'σ_Ixz' : Real = 0.022566176940390956;
                                attribute Iyz : Real = -0.007568302627131665;
                                attribute 'σ_Iyz' : Real = 0.02209918015384651;
                            }
                            part <'C.1.2.2.2.4.2.4'> 'Part 990' {
                                attribute POIconv : String = "-";
                                attribute Ipoint : Boolean = false;
                                attribute mass : Real = 0.2931565045390744;
                                attribute 'σ_mass' : Real = 0.28909372274994966;
                                attribute Cx : Real = 98.2056837528944;
                                attribute 'σ_Cx' : Real = 28.721044428837228;
                                attribute Cy : Real = 41.02588784880936;
                                attribute 'σ_Cy' : Real = 28.23690002309109;
                                attribute Cz : Real = 64.80340650305152;
                                attribute 'σ_Cz' : Real = 29.057750463592832;
                                attribute Ixx : Real = 0.3358473755738956;
                                attribute 'σ_Ixx' : Real = 0.37074144170588635;
                                attribute Iyy : Real = 0.3608381384022047;
                                attribute 'σ_Iyy' : Real = 0.3723953238821935;
                                attribute Izz : Real = 0.3748945659860809;
                                attribute 'σ_Izz' : Real = 0.37017423652493897;
                                attribute Ixy : Real = 0.010142787058466472;
                                attribute 'σ_Ixy' : Real = 0.02351283871158888;
                                attribute Ixz : Real = -7.219834211158215e-4;
                                attribute 'σ_Ixz' : Real = 0.022566176940390956;
                                attribute Iyz : Real = -2.5641610775973736e-5;
                                attribute 'σ_Iyz' : Real = 0.02209918015384651;
                            }
                        }
                        part <'C.1.2.2.2.4.3'> 'Subassembly 280' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.4.3.1'> 'Part 991' {
                                attribute POIconv : String = "-";
                                attribute Ipoint : Boolean = false;
                                attribute mass : Real = 0.6313824032684788;
                                attribute 'σ_mass' : Real = 0.28909372274994966;
                                attribute Cx : Real = -82.62024247087538;
                                attribute 'σ_Cx' : Real = 28.721044428837228;
                                attribute Cy : Real = 75.72377445176244;
                                attribute 'σ_Cy' : Real = 28.23690002309109;
                                attribute Cz : Real = 19.779780320823193;
                                attribute 'σ_Cz' : Real = 29.057750463592832;
                                attribute Ixx : Real = 0.8917810433568049;
                                attribute 'σ_Ixx' : Real = 0.37074144170588635;
                                attribute Iyy : Real = 0.9115619872194086;
                                attribute 'σ_Iyy' : Real = 0.3723953238821935;
                                attribute Izz : Real = 0.9320077385812765;
                                attribute 'σ_Izz' : Real = 0.37017423652493897;
                                attribute Ixy : Real = -0.01827074584355858;
                                attribute 'σ_Ixy' : Real = 0.02351283871158888;
                                attribute Ixz : Real = -0.02323207921547763;
                                attribute 'σ_Ixz' : Real = 0.022566176940390956;
                                attribute Iyz : Real = -0.016588898753466086;
                                attribute 'σ_Iyz' : Real = 0.02209918015384651;
                            }
                            part <'C.1.2.2.2.4.3.2'> 'Part 992' {
                                attribute POIconv : String = "+";
                                attribute Ipoint : Boolean = false;
                                attribute mass : Real = 0.24557517129927875;
                                attribute 'σ_mass' : Real = 0.28909372274994966;
                                attribute Cx : Real = 92.48381964862347;
                                attribute 'σ_Cx' : Real = 28.721044428837228;
                                attribute Cy : Real = 4.165562381967902;
                                attribute 'σ_Cy' : Real = 28.23690002309109;
                                attribute Cz : Real = 67.82564986497164;
                                attribute 'σ_Cz' : Real = 29.057750463592832;
                                attribute Ixx : Real = 0.3425471784754824;
                                attribute 'σ_Ixx' : Real = 0.37074144170588635;
                                attribute Iyy : Real = 0.3258620340522138;
                                attribute 'σ_Iyy' : Real = 0.3723953238821935;
                                attribute Izz : Real = 0.351794054832525;
                                attribute 'σ_Izz' : Real = 0.37017423652493897;
                                attribute Ixy : Real = -0.01275755595874368;
                                attribute 'σ_Ixy' : Real = 0.02351283871158888;
                                attribute Ixz : Real = 0.013639279830247812;
                                attribute 'σ_Ixz' : Real = 0.022566176940390956;
                                attribute Iyz : Real = 0.01231523268030764;
                                attribute 'σ_Iyz' : Real = 0.02209918015384651;
                            }
                        }
                        part <'C.1.2.2.2.4.4'> 'Subassembly 281' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.2.4.4.1'> 'Part 993' {
                                attribute POIconv : String = "+";
                                attribute Ipoint : Boolean = false;
                                attribute mass : Real = 0.987849029772915;
                                attribute 'σ_mass' : Real = 0.28909372274994966;
                                attribute Cx : Real = -49.96312544681132;
                                attribute 'σ_Cx' : Real = 28.721044428837228;
                                attribute Cy : Real = -51.87025321647525;
                                attribute 'σ_Cy' : Real = 28.23690002309109;
                                attribute Cz : Real = -14.14846871048212;
                                attribute 'σ_Cz' : Real = 29.057750463592832;
                                attribute Ixx : Real = 1.4704006816222968;
                                attribute 'σ_Ixx' : Real = 0.37074144170588635;
                                attribute Iyy : Real = 1.4577969816124652;
                                attribute 'σ_Iyy' : Real = 0.3723953238821935;
                                attribute Izz : Real = 1.376753891657765;
                                attribute 'σ_Izz' : Real = 0.37017423652493897;
                                attribute Ixy : Real = 0.031299230820461495;
                                attribute 'σ_Ixy' : Real = 0.02351283871158888;
                                attribute Ixz : Real = 0.06320668326105389;
                                attribute 'σ_Ixz' : Real = 0.022566176940390956;
                                attribute Iyz : Real = 0.002905841821107236;
                                attribute 'σ_Iyz' : Real = 0.02209918015384651;
                            }
                            part <'C.1.2.2.2.4.4.2'> 'Part 994' {
                                attribute POIconv : String = "+";
                                attribute Ipoint : Boolean = false;
                                attribute mass : Real = 0.9620267251112964;
                                attribute 'σ_mass' : Real = 0.28909372274994966;
                                attribute Cx : Real = -51.747614378109574;
                                attribute 'σ_Cx' : Real = 28.721044428837228;
                                attribute Cy : Real = 86.72565501183271;
                                attribute 'σ_Cy' : Real = 28.23690002309109;
                                attribute Cz : Real = -31.803484773263335;
                                attribute 'σ_Cz' : Real = 29.057750463592832;
                                attribute Ixx : Real = 1.152836859204256;
                                attribute 'σ_Ixx' : Real = 0.37074144170588635;
                                attribute Iyy : Real = 1.1308468342306088;
                                attribute 'σ_Iyy' : Real = 0.3723953238821935;
                                attribute Izz : Real = 1.2019860712454171;
                                attribute 'σ_Izz' : Real = 0.37017423652493897;
                                attribute Ixy : Real = -0.03274092054828336;
                                attribute 'σ_Ixy' : Real = 0.02351283871158888;
                                attribute Ixz : Real = -0.0693662484351279;
                                attribute 'σ_Ixz' : Real = 0.022566176940390956;
                                attribute Iyz : Real = 0.06692376995962773;
                                attribute 'σ_Iyz' : Real = 0.02209918015384651;
                            }
                            part <'C.1.2.2.2.4.4.3'> 'Part 995' {
                                attribute POIconv : String = "+";
                                attribute Ipoint : Boolean = false;
                                attribute mass : Real = 0.5036204764358699;
                                attribute 'σ_mass' : Real = 0.28909372274994966;
                                attribute Cx : Real = -44.637550646439195;
                                attribute 'σ_Cx' : Real = 28.721044428837228;
                                attribute Cy : Real = 72.92668838053942;
                                attribute 'σ_Cy' : Real = 28.23690002309109;
                                attribute Cz : Real = 22.411220660433173;
                                attribute 'σ_Cz' : Real = 29.057750463592832;
                                attribute Ixx : Real = 0.6675448327208635;
                                attribute 'σ_Ixx' : Real = 0.37074144170588635;
                                attribute Iyy : Real = 0.6936215132887461;
                                attribute 'σ_Iyy' : Real = 0.3723953238821935;
                                attribute Izz : Real = 0.6079922988006617;
                                attribute 'σ_Izz' : Real = 0.37017423652493897;
                                attribute Ixy : Real = -0.009897934627693127;
                                attribute 'σ_Ixy' : Real = 0.02351283871158888;
                                attribute Ixz : Real = -0.052925781095782734;
                                attribute 'σ_Ixz' : Real = 0.022566176940390956;
                                attribute Iyz : Real = 0.016357303494848038;
                                attribute 'σ_Iyz' : Real = 0.02209918015384651;
                            }
                            part <'C.1.2.2.2.4.4.4'> 'Part 996' {
                                attribute POIconv : String = "-";
                                attribute Ipoint : Boolean = false;
                                attribute mass : Real = 0.5350742662933189;
                                attribute 'σ_mass' : Real = 0.28909372274994966;
                                attribute Cx : Real = 11.9660132098943;
                                attribute 'σ_Cx' : Real = 28.721044428837228;
                                attribute Cy : Real = 18.348637269809842;
                                attribute 'σ_Cy' : Real = 28.23690002309109;
                                attribute Cz : Real = 44.33038090355694;
                                attribute 'σ_Cz' : Real = 29.057750463592832;
                                attribute Ixx : Real = 0.5921547951577714;
                                attribute 'σ_Ixx' : Real = 0.37074144170588635;
                                attribute Iyy : Real = 0.669506709333052;
                                attribute 'σ_Iyy' : Real = 0.3723953238821935;
                                attribute Izz : Real = 0.6754079509520082;
                                attribute 'σ_Izz' : Real = 0.37017423652493897;
                                attribute Ixy : Real = -0.009678963877177461;
                                attribute 'σ_Ixy' : Real = 0.02351283871158888;
                                attribute Ixz : Real = 0.004621268934198031;
                                attribute 'σ_Ixz' : Real = 0.022566176940390956;
                                attribute Iyz : Real = 0.0010303968120061496;
                                attribute 'σ_Iyz' : Real = 0.02209918015384651;
                            }
                            part <'C.1.2.2.2.4.4.5'> 'Part 997' {
                                attribute POIconv : String = "+";
                                attribute Ipoint : Boolean = false;
                                attribute mass : Real = 0.0867748331334442;
                                attribute 'σ_mass' : Real = 0.28909372274994966;
                                attribute Cx : Real = -13.0377440713346;
                                attribute 'σ_Cx' : Real = 28.721044428837228;
                                attribute Cy : Real = -94.63196410797536;
                                attribute 'σ_Cy' : Real = 28.23690002309109;
                                attribute Cz : Real = 32.34167182818055;
                                attribute 'σ_Cz' : Real = 29.057750463592832;
                                attribute Ixx : Real = 0.12903011300564224;
                                attribute 'σ_Ixx' : Real = 0.37074144170588635;
                                attribute Iyy : Real = 0.13199233109532665;
                                attribute 'σ_Iyy' : Real = 0.3723953238821935;
                                attribute Izz : Real = 0.13243203648030988;
                                attribute 'σ_Izz' : Real = 0.37017423652493897;
                                attribute Ixy : Real = 0.0024587243176823915;
                                attribute 'σ_Ixy' : Real = 0.02351283871158888;
                                attribute Ixz : Real = 0.0040101692353868065;
                                attribute 'σ_Ixz' : Real = 0.022566176940390956;
                                attribute Iyz : Real = -0.0036114126380190764;
                                attribute 'σ_Iyz' : Real = 0.02209918015384651;
                            }
                        }
                    }
                }
                part <'C.1.2.2.3'> 'Subsystem 22' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.2.2.3.1'> 'Assembly 81' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.2.3.1.1'> 'Subassembly 282' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.3.1.1.1'> 'Part 998' {
                                attribute POIconv : String = "+";
                                attribute Ipoint : Boolean = false;
                                attribute mass : Real = 0.2682770018510055;
                                attribute 'σ_mass' : Real = 0.28909372274994966;
                                attribute Cx : Real = -38.14990087412298;
                                attribute 'σ_Cx' : Real = 28.721044428837228;
                                attribute Cy : Real = 98.45185899175704;
                                attribute 'σ_Cy' : Real = 28.23690002309109;
                                attribute Cz : Real = 65.6827942468226;
                                attribute 'σ_Cz' : Real = 29.057750463592832;
                                attribute Ixx : Real = 0.2734833661725806;
                                attribute 'σ_Ixx' : Real = 0.37074144170588635;
                                attribute Iyy : Real = 0.2794214069698289;
                                attribute 'σ_Iyy' : Real = 0.3723953238821935;
                                attribute Izz : Real = 0.2675526860049357;
                                attribute 'σ_Izz' : Real = 0.37017423652493897;
                                attribute Ixy : Real = 0.00351054849216403;
                                attribute 'σ_Ixy' : Real = 0.02351283871158888;
                                attribute Ixz : Real = -0.0041970819578815224;
                                attribute 'σ_Ixz' : Real = 0.022566176940390956;
                                attribute Iyz : Real = -0.005158917155448491;
                                attribute 'σ_Iyz' : Real = 0.02209918015384651;
                            }
                            part <'C.1.2.2.3.1.1.2'> 'Part 999' {
                                attribute POIconv : String = "+";
                                attribute Ipoint : Boolean = false;
                                attribute mass : Real = 0.5181016515605151;
                                attribute 'σ_mass' : Real = 0.28909372274994966;
                                attribute Cx : Real = 20.26623683050275;
                                attribute 'σ_Cx' : Real = 28.721044428837228;
                                attribute Cy : Real = -94.88800340332091;
                                attribute 'σ_Cy' : Real = 28.23690002309109;
                                attribute Cz : Real = -84.30977887474;
                                attribute 'σ_Cz' : Real = 29.057750463592832;
                                attribute Ixx : Real = 0.6617302139178972;
                                attribute 'σ_Ixx' : Real = 0.37074144170588635;
                                attribute Iyy : Real = 0.5890508131589117;
                                attribute 'σ_Iyy' : Real = 0.3723953238821935;
                                attribute Izz : Real = 0.6030236177772124;
                                attribute 'σ_Izz' : Real = 0.37017423652493897;
                                attribute Ixy : Real = 0.007426176634679011;
                                attribute 'σ_Ixy' : Real = 0.02351283871158888;
                                attribute Ixz : Real = 0.036556870971465254;
                                attribute 'σ_Ixz' : Real = 0.022566176940390956;
                                attribute Iyz : Real = 0.05498798482147681;
                                attribute 'σ_Iyz' : Real = 0.02209918015384651;
                            }
                        }
                        part <'C.1.2.2.3.1.2'> 'Subassembly 283' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.3.1.2.1'> 'Part 1000' {
                                attribute POIconv : String = "-";
                                attribute Ipoint : Boolean = false;
                                attribute mass : Real = 0.08781051513529382;
                                attribute 'σ_mass' : Real = 0.28909372274994966;
                                attribute Cx : Real = 93.75454084947705;
                                attribute 'σ_Cx' : Real = 28.721044428837228;
                                attribute Cy : Real = -64.90565417334437;
                                attribute 'σ_Cy' : Real = 28.23690002309109;
                                attribute Cz : Real = -7.389143481850624;
                                attribute 'σ_Cz' : Real = 29.057750463592832;
                                attribute Ixx : Real = 0.11349920599823053;
                                attribute 'σ_Ixx' : Real = 0.37074144170588635;
                                attribute Iyy : Real = 0.11743811639927669;
                                attribute 'σ_Iyy' : Real = 0.3723953238821935;
                                attribute Izz : Real = 0.11701770605778841;
                                attribute 'σ_Izz' : Real = 0.37017423652493897;
                                attribute Ixy : Real = 0.0026483268710255107;
                                attribute 'σ_Ixy' : Real = 0.02351283871158888;
                                attribute Ixz : Real = -0.0024529174055099986;
                                attribute 'σ_Ixz' : Real = 0.022566176940390956;
                                attribute Iyz : Real = -0.005056335373681012;
                                attribute 'σ_Iyz' : Real = 0.02209918015384651;
                            }
                            part <'C.1.2.2.3.1.2.2'> 'Part 1001' {
                                attribute POIconv : String = "-";
                                attribute Ipoint : Boolean = false;
                                attribute mass : Real = 0.36019444992020727;
                                attribute 'σ_mass' : Real = 0.28909372274994966;
                                attribute Cx : Real = -32.9376395791769;
                                attribute 'σ_Cx' : Real = 28.721044428837228;
                                attribute Cy : Real = 79.80054975487292;
                                attribute 'σ_Cy' : Real = 28.23690002309109;
                                attribute Cz : Real = 83.71249507181346;
                                attribute 'σ_Cz' : Real = 29.057750463592832;
                                attribute Ixx : Real = 0.37424472474082926;
                                attribute 'σ_Ixx' : Real = 0.37074144170588635;
                                attribute Iyy : Real = 0.3537332332729534;
                                attribute 'σ_Iyy' : Real = 0.3723953238821935;
                                attribute Izz : Real = 0.36519784775002373;
                                attribute 'σ_Izz' : Real = 0.37017423652493897;
                                attribute Ixy : Real = 0.028299732583257065;
                                attribute 'σ_Ixy' : Real = 0.02351283871158888;
                                attribute Ixz : Real = -0.0017474358014942146;
                                attribute 'σ_Ixz' : Real = 0.022566176940390956;
                                attribute Iyz : Real = 0.0016867036581789156;
                                attribute 'σ_Iyz' : Real = 0.02209918015384651;
                            }
                            part <'C.1.2.2.3.1.2.3'> 'Part 1002' {
                                attribute POIconv : String = "-";
                                attribute Ipoint : Boolean = false;
                                attribute mass : Real = 0.9131225092548412;
                                attribute 'σ_mass' : Real = 0.28909372274994966;
                                attribute Cx : Real = 8.811583882197738;
                                attribute 'σ_Cx' : Real = 28.721044428837228;
                                attribute Cy : Real = 18.899534223601222;
                                attribute 'σ_Cy' : Real = 28.23690002309109;
                                attribute Cz : Real = 54.688904574140906;
                                attribute 'σ_Cz' : Real = 29.057750463592832;
                                attribute Ixx : Real = 1.206763664569927;
                                attribute 'σ_Ixx' : Real = 0.37074144170588635;
                                attribute Iyy : Real = 1.281416933150703;
                                attribute 'σ_Iyy' : Real = 0.3723953238821935;
                                attribute Izz : Real = 1.2006552373138228;
                                attribute 'σ_Izz' : Real = 0.37017423652493897;
                                attribute Ixy : Real = 0.043673574884466715;
                                attribute 'σ_Ixy' : Real = 0.02351283871158888;
                                attribute Ixz : Real = -3.940934767997017e-4;
                                attribute 'σ_Ixz' : Real = 0.022566176940390956;
                                attribute Iyz : Real = 0.011064303191600802;
                                attribute 'σ_Iyz' : Real = 0.02209918015384651;
                            }
                        }
                    }
                    part <'C.1.2.2.3.2'> 'Assembly 82' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.2.3.2.1'> 'Subassembly 284' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.3.2.1.1'> 'Part 1003' {
                                attribute POIconv : String = "-";
                                attribute Ipoint : Boolean = false;
                                attribute mass : Real = 0.3176887161303312;
                                attribute 'σ_mass' : Real = 0.28909372274994966;
                                attribute Cx : Real = -65.99662681110203;
                                attribute 'σ_Cx' : Real = 28.721044428837228;
                                attribute Cy : Real = 88.88293546624482;
                                attribute 'σ_Cy' : Real = 28.23690002309109;
                                attribute Cz : Real = -47.47326597571373;
                                attribute 'σ_Cz' : Real = 29.057750463592832;
                                attribute Ixx : Real = 0.37047545833452283;
                                attribute 'σ_Ixx' : Real = 0.37074144170588635;
                                attribute Iyy : Real = 0.4026334890313699;
                                attribute 'σ_Iyy' : Real = 0.3723953238821935;
                                attribute Izz : Real = 0.42084579870170047;
                                attribute 'σ_Izz' : Real = 0.37017423652493897;
                                attribute Ixy : Real = -0.009684507846894837;
                                attribute 'σ_Ixy' : Real = 0.02351283871158888;
                                attribute Ixz : Real = 0.012490113221948936;
                                attribute 'σ_Ixz' : Real = 0.022566176940390956;
                                attribute Iyz : Real = 0.02777157782135361;
                                attribute 'σ_Iyz' : Real = 0.02209918015384651;
                            }
                            part <'C.1.2.2.3.2.1.2'> 'Part 1004' {
                                attribute POIconv : String = "+";
                                attribute Ipoint : Boolean = false;
                                attribute mass : Real = 0.7609557169706095;
                                attribute 'σ_mass' : Real = 0.28909372274994966;
                                attribute Cx : Real = 1.4426170382648706;
                                attribute 'σ_Cx' : Real = 28.721044428837228;
                                attribute Cy : Real = 95.131212240085;
                                attribute 'σ_Cy' : Real = 28.23690002309109;
                                attribute Cz : Real = -36.56750405207276;
                                attribute 'σ_Cz' : Real = 29.057750463592832;
                                attribute Ixx : Real = 0.7739821382407648;
                                attribute 'σ_Ixx' : Real = 0.37074144170588635;
                                attribute Iyy : Real = 0.7590513650103857;
                                attribute 'σ_Iyy' : Real = 0.3723953238821935;
                                attribute Izz : Real = 0.7131505687926795;
                                attribute 'σ_Izz' : Real = 0.37017423652493897;
                                attribute Ixy : Real = 0.024479287743045974;
                                attribute 'σ_Ixy' : Real = 0.02351283871158888;
                                attribute Ixz : Real = -0.02176595292603893;
                                attribute 'σ_Ixz' : Real = 0.022566176940390956;
                                attribute Iyz : Real = 0.024230138917593402;
                                attribute 'σ_Iyz' : Real = 0.02209918015384651;
                            }
                            part <'C.1.2.2.3.2.1.3'> 'Part 1005' {
                                attribute POIconv : String = "+";
                                attribute Ipoint : Boolean = false;
                                attribute mass : Real = 0.29240573113318535;
                                attribute 'σ_mass' : Real = 0.28909372274994966;
                                attribute Cx : Real = 2.9813415370881557;
                                attribute 'σ_Cx' : Real = 28.721044428837228;
                                attribute Cy : Real = 52.419610135257244;
                                attribute 'σ_Cy' : Real = 28.23690002309109;
                                attribute Cz : Real = -87.7942037768662;
                                attribute 'σ_Cz' : Real = 29.057750463592832;
                                attribute Ixx : Real = 0.325210686802862;
                                attribute 'σ_Ixx' : Real = 0.37074144170588635;
                                attribute Iyy : Real = 0.37241270770813645;
                                attribute 'σ_Iyy' : Real = 0.3723953238821935;
                                attribute Izz : Real = 0.4123770118399169;
                                attribute 'σ_Izz' : Real = 0.37017423652493897;
                                attribute Ixy : Real = 0.00301387373979163;
                                attribute 'σ_Ixy' : Real = 0.02351283871158888;
                                attribute Ixz : Real = 0.02151111045569789;
                                attribute 'σ_Ixz' : Real = 0.022566176940390956;
                                attribute Iyz : Real = -0.004386168386778359;
                                attribute 'σ_Iyz' : Real = 0.02209918015384651;
                            }
                        }
                        part <'C.1.2.2.3.2.2'> 'Subassembly 285' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.3.2.2.1'> 'Part 1006' {
                                attribute POIconv : String = "-";
                                attribute Ipoint : Boolean = false;
                                attribute mass : Real = 0.20961525726504623;
                                attribute 'σ_mass' : Real = 0.28909372274994966;
                                attribute Cx : Real = 82.92951546609402;
                                attribute 'σ_Cx' : Real = 28.721044428837228;
                                attribute Cy : Real = 87.53000176511705;
                                attribute 'σ_Cy' : Real = 28.23690002309109;
                                attribute Cz : Real = 31.493828119710088;
                                attribute 'σ_Cz' : Real = 29.057750463592832;
                                attribute Ixx : Real = 0.26866215960934225;
                                attribute 'σ_Ixx' : Real = 0.37074144170588635;
                                attribute Iyy : Real = 0.28258058165029315;
                                attribute 'σ_Iyy' : Real = 0.3723953238821935;
                                attribute Izz : Real = 0.29801919076629313;
                                attribute 'σ_Izz' : Real = 0.37017423652493897;
                                attribute Ixy : Real = -0.0057529824619327995;
                                attribute 'σ_Ixy' : Real = 0.02351283871158888;
                                attribute Ixz : Real = -0.005598120417871369;
                                attribute 'σ_Ixz' : Real = 0.022566176940390956;
                                attribute Iyz : Real = -0.007110050984442776;
                                attribute 'σ_Iyz' : Real = 0.02209918015384651;
                            }
                            part <'C.1.2.2.3.2.2.2'> 'Part 1007' {
                                attribute POIconv : String = "+";
                                attribute Ipoint : Boolean = false;
                                attribute mass : Real = 0.5236412878341508;
                                attribute 'σ_mass' : Real = 0.28909372274994966;
                                attribute Cx : Real = 40.28734490275383;
                                attribute 'σ_Cx' : Real = 28.721044428837228;
                                attribute Cy : Real = -96.53971642255783;
                                attribute 'σ_Cy' : Real = 28.23690002309109;
                                attribute Cz : Real = -88.59279761090875;
                                attribute 'σ_Cz' : Real = 29.057750463592832;
                                attribute Ixx : Real = 0.6576317562732735;
                                attribute 'σ_Ixx' : Real = 0.37074144170588635;
                                attribute Iyy : Real = 0.7321373599512839;
                                attribute 'σ_Iyy' : Real = 0.3723953238821935;
                                attribute Izz : Real = 0.5767785828398014;
                                attribute 'σ_Izz' : Real = 0.37017423652493897;
                                attribute Ixy : Real = 0.041556770873983365;
                                attribute 'σ_Ixy' : Real = 0.02351283871158888;
                                attribute Ixz : Real = -0.0018276718436292454;
                                attribute 'σ_Ixz' : Real = 0.022566176940390956;
                                attribute Iyz : Real = -0.04015842932084851;
                                attribute 'σ_Iyz' : Real = 0.02209918015384651;
                            }
                            part <'C.1.2.2.3.2.2.3'> 'Part 1008' {
                                attribute POIconv : String = "-";
                                attribute Ipoint : Boolean = false;
                                attribute mass : Real = 0.3170905596860684;
                                attribute 'σ_mass' : Real = 0.28909372274994966;
                                attribute Cx : Real = -43.32383400760591;
                                attribute 'σ_Cx' : Real = 28.721044428837228;
                                attribute Cy : Real = -74.38644138164818;
                                attribute 'σ_Cy' : Real = 28.23690002309109;
                                attribute Cz : Real = -50.76702176593244;
                                attribute 'σ_Cz' : Real = 29.057750463592832;
                                attribute Ixx : Real = 0.3545937751506153;
                                attribute 'σ_Ixx' : Real = 0.37074144170588635;
                                attribute Iyy : Real = 0.3919489871103486;
                                attribute 'σ_Iyy' : Real = 0.3723953238821935;
                                attribute Izz : Real = 0.4047535362964869;
                                attribute 'σ_Izz' : Real = 0.37017423652493897;
                                attribute Ixy : Real = 0.02109445813379975;
                                attribute 'σ_Ixy' : Real = 0.02351283871158888;
                                attribute Ixz : Real = -0.030998759528186412;
                                attribute 'σ_Ixz' : Real = 0.022566176940390956;
                                attribute Iyz : Real = 0.007082155674338354;
                                attribute 'σ_Iyz' : Real = 0.02209918015384651;
                            }
                            part <'C.1.2.2.3.2.2.4'> 'Part 1009' {
                                attribute POIconv : String = "+";
                                attribute Ipoint : Boolean = false;
                                attribute mass : Real = 0.7079495586680714;
                                attribute 'σ_mass' : Real = 0.28909372274994966;
                                attribute Cx : Real = -90.43888384476304;
                                attribute 'σ_Cx' : Real = 28.721044428837228;
                                attribute Cy : Real = 95.80949177034199;
                                attribute 'σ_Cy' : Real = 28.23690002309109;
                                attribute Cz : Real = 8.222177624702454;
                                attribute 'σ_Cz' : Real = 29.057750463592832;
                                attribute Ixx : Real = 0.7643217213278611;
                                attribute 'σ_Ixx' : Real = 0.37074144170588635;
                                attribute Iyy : Real = 0.8899502003034849;
                                attribute 'σ_Iyy' : Real = 0.3723953238821935;
                                attribute Izz : Real = 0.8161325789900538;
                                attribute 'σ_Izz' : Real = 0.37017423652493897;
                                attribute Ixy : Real = -0.020719804189385148;
                                attribute 'σ_Ixy' : Real = 0.02351283871158888;
                                attribute Ixz : Real = 0.02030532740862295;
                                attribute 'σ_Ixz' : Real = 0.022566176940390956;
                                attribute Iyz : Real = 0.06275005787363168;
                                attribute 'σ_Iyz' : Real = 0.02209918015384651;
                            }
                        }
                        part <'C.1.2.2.3.2.3'> 'Subassembly 286' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.3.2.3.1'> 'Part 1010' {
                                attribute POIconv : String = "-";
                                attribute Ipoint : Boolean = false;
                                attribute mass : Real = 0.00490983270178549;
                                attribute 'σ_mass' : Real = 0.28909372274994966;
                                attribute Cx : Real = -8.017859747633338;
                                attribute 'σ_Cx' : Real = 28.721044428837228;
                                attribute Cy : Real = 11.19074528105557;
                                attribute 'σ_Cy' : Real = 28.23690002309109;
                                attribute Cz : Real = 51.94290429353714;
                                attribute 'σ_Cz' : Real = 29.057750463592832;
                                attribute Ixx : Real = 0.006025597062580873;
                                attribute 'σ_Ixx' : Real = 0.37074144170588635;
                                attribute Iyy : Real = 0.0063606194350507165;
                                attribute 'σ_Iyy' : Real = 0.3723953238821935;
                                attribute Izz : Real = 0.006147788323704245;
                                attribute 'σ_Izz' : Real = 0.37017423652493897;
                                attribute Ixy : Real = -1.0238701415248559e-4;
                                attribute 'σ_Ixy' : Real = 0.02351283871158888;
                                attribute Ixz : Real = 3.089362430248738e-4;
                                attribute 'σ_Ixz' : Real = 0.022566176940390956;
                                attribute Iyz : Real = -5.072236912534451e-4;
                                attribute 'σ_Iyz' : Real = 0.02209918015384651;
                            }
                            part <'C.1.2.2.3.2.3.2'> 'Part 1011' {
                                attribute POIconv : String = "+";
                                attribute Ipoint : Boolean = false;
                                attribute mass : Real = 0.23015673840255477;
                                attribute 'σ_mass' : Real = 0.28909372274994966;
                                attribute Cx : Real = -7.633649092167616;
                                attribute 'σ_Cx' : Real = 28.721044428837228;
                                attribute Cy : Real = -11.86889042146504;
                                attribute 'σ_Cy' : Real = 28.23690002309109;
                                attribute Cz : Real = 52.535229129716754;
                                attribute 'σ_Cz' : Real = 29.057750463592832;
                                attribute Ixx : Real = 0.2501456030298357;
                                attribute 'σ_Ixx' : Real = 0.37074144170588635;
                                attribute Iyy : Real = 0.25709420167183045;
                                attribute 'σ_Iyy' : Real = 0.3723953238821935;
                                attribute Izz : Real = 0.24923941688212842;
                                attribute 'σ_Izz' : Real = 0.37017423652493897;
                                attribute Ixy : Real = 0.010666510238599467;
                                attribute 'σ_Ixy' : Real = 0.02351283871158888;
                                attribute Ixz : Real = 0.009097009448384053;
                                attribute 'σ_Ixz' : Real = 0.022566176940390956;
                                attribute Iyz : Real = -0.01014688042309085;
                                attribute 'σ_Iyz' : Real = 0.02209918015384651;
                            }
                            part <'C.1.2.2.3.2.3.3'> 'Part 1012' {
                                attribute POIconv : String = "-";
                                attribute Ipoint : Boolean = false;
                                attribute mass : Real = 0.405842741121538;
                                attribute 'σ_mass' : Real = 0.28909372274994966;
                                attribute Cx : Real = 28.45844253897667;
                                attribute 'σ_Cx' : Real = 28.721044428837228;
                                attribute Cy : Real = 2.3775546345859766;
                                attribute 'σ_Cy' : Real = 28.23690002309109;
                                attribute Cz : Real = -73.55268327519298;
                                attribute 'σ_Cz' : Real = 29.057750463592832;
                                attribute Ixx : Real = 0.4223758790032171;
                                attribute 'σ_Ixx' : Real = 0.37074144170588635;
                                attribute Iyy : Real = 0.42987435048775297;
                                attribute 'σ_Iyy' : Real = 0.3723953238821935;
                                attribute Izz : Real = 0.447437250621488;
                                attribute 'σ_Izz' : Real = 0.37017423652493897;
                                attribute Ixy : Real = -0.012859265413095882;
                                attribute 'σ_Ixy' : Real = 0.02351283871158888;
                                attribute Ixz : Real = 0.01219929930809871;
                                attribute 'σ_Ixz' : Real = 0.022566176940390956;
                                attribute Iyz : Real = -0.021227213646902998;
                                attribute 'σ_Iyz' : Real = 0.02209918015384651;
                            }
                            part <'C.1.2.2.3.2.3.4'> 'Part 1013' {
                                attribute POIconv : String = "+";
                                attribute Ipoint : Boolean = false;
                                attribute mass : Real = 0.7539108669806738;
                                attribute 'σ_mass' : Real = 0.28909372274994966;
                                attribute Cx : Real = -91.96384167298675;
                                attribute 'σ_Cx' : Real = 28.721044428837228;
                                attribute Cy : Real = 85.1940150372684;
                                attribute 'σ_Cy' : Real = 28.23690002309109;
                                attribute Cz : Real = 62.23730780184269;
                                attribute 'σ_Cz' : Real = 29.057750463592832;
                                attribute Ixx : Real = 1.173633832226925;
                                attribute 'σ_Ixx' : Real = 0.37074144170588635;
                                attribute Iyy : Real = 1.0665241032263855;
                                attribute 'σ_Iyy' : Real = 0.3723953238821935;
                                attribute Izz : Real = 1.0795789652396484;
                                attribute 'σ_Izz' : Real = 0.37017423652493897;
                                attribute Ixy : Real = 0.009276259752856897;
                                attribute 'σ_Ixy' : Real = 0.02351283871158888;
                                attribute Ixz : Real = 0.043136850591862196;
                                attribute 'σ_Ixz' : Real = 0.022566176940390956;
                                attribute Iyz : Real = -0.0018029021425642155;
                                attribute 'σ_Iyz' : Real = 0.02209918015384651;
                            }
                        }
                        part <'C.1.2.2.3.2.4'> 'Subassembly 287' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.2.3.2.4.1'> 'Part 1014' {
                                attribute POIconv : String = "-";
                                attribute Ipoint : Boolean = false;
                                attribute mass : Real = 0.6338044687181246;
                                attribute 'σ_mass' : Real = 0.28909372274994966;
                                attribute Cx : Real = -37.18947251327336;
                                attribute 'σ_Cx' : Real = 28.721044428837228;
                                attribute Cy : Real = -75.01696199178696;
                                attribute 'σ_Cy' : Real = 28.23690002309109;
                                attribute Cz : Real = -38.12561030499637;
                                attribute 'σ_Cz' : Real = 29.057750463592832;
                                attribute Ixx : Real = 0.8006787546998893;
                                attribute 'σ_Ixx' : Real = 0.37074144170588635;
                                attribute Iyy : Real = 0.6991374430848829;
                                attribute 'σ_Iyy' : Real = 0.3723953238821935;
                                attribute Izz : Real = 0.8404919150082512;
                                attribute 'σ_Izz' : Real = 0.37017423652493897;
                                attribute Ixy : Real = -0.024535888686501674;
                                attribute 'σ_Ixy' : Real = 0.02351283871158888;
                                attribute Ixz : Real = -0.03505527345171007;
                                attribute 'σ_Ixz' : Real = 0.022566176940390956;
                                attribute Iyz : Real = 0.06594037674886585;
                                attribute 'σ_Iyz' : Real = 0.02209918015384651;
                            }
                            part <'C.1.2.2.3.2.4.2'> 'Part 1015' {
                                attribute POIconv : String = "-";
                                attribute Ipoint : Boolean = false;
                                attribute mass : Real = 0.030522787004010753;
                                attribute 'σ_mass' : Real = 0.28909372274994966;
                                attribute Cx : Real = 37.39647245965898;
                                attribute 'σ_Cx' : Real = 28.721044428837228;
                                attribute Cy : Real = -49.916549073532224;
                                attribute 'σ_Cy' : Real = 28.23690002309109;
                                attribute Cz : Real = -64.78401878848672;
                                attribute 'σ_Cz' : Real = 29.057750463592832;
                                attribute Ixx : Real = 0.039653479324651145;
                                attribute 'σ_Ixx' : Real = 0.37074144170588635;
                                attribute Iyy : Real = 0.03988449348235366;
                                attribute 'σ_Iyy' : Real = 0.3723953238821935;
                                attribute Izz : Real = 0.04167912098722391;
                                attribute 'σ_Izz' : Real = 0.37017423652493897;
                                attribute Ixy : Real = -8.866876591976072e-4;
                                attribute 'σ_Ixy' : Real = 0.02351283871158888;
                                attribute Ixz : Real = 8.401707250535846e-4;
                                attribute 'σ_Ixz' : Real = 0.022566176940390956;
                                attribute Iyz : Real = -0.0011150046633223952;
                                attribute 'σ_Iyz' : Real = 0.02209918015384651;
                            }
                            part <'C.1.2.2.3.2.4.3'> 'Part 1016' {
                                attribute POIconv : String = "+";
                                attribute Ipoint : Boolean = false;
                                attribute mass : Real = 0.6805104270665906;
                                attribute 'σ_mass' : Real = 0.28909372274994966;
                                attribute Cx : Real = 85.85417056456208;
                                attribute 'σ_Cx' : Real = 28.721044428837228;
                                attribute Cy : Real = 29.997750418260694;
                                attribute 'σ_Cy' : Real = 28.23690002309109;
                                attribute Cz : Real = 46.22967317700386;
                                attribute 'σ_Cz' : Real = 29.057750463592832;
                                attribute Ixx : Real = 0.8726368522280162;
                                attribute 'σ_Ixx' : Real = 0.37074144170588635;
                                attribute Iyy : Real = 0.8710918434618221;
                                attribute 'σ_Iyy' : Real = 0.3723953238821935;
                                attribute Izz : Real = 0.8806345565258799;
                                attribute 'σ_Izz' : Real = 0.37017423652493897;
                                attribute Ixy : Real = -0.005378031021421724;
                                attribute 'σ_Ixy' : Real = 0.02351283871158888;
                                attribute Ixz : Real = 9.754780818239108e-4;
                                attribute 'σ_Ixz' : Real = 0.022566176940390956;
                                attribute Iyz : Real = 0.0012612562220211878;
                                attribute 'σ_Iyz' : Real = 0.02209918015384651;
                            }
                            part <'C.1.2.2.3.2.4.4'> 'Part 1017' {
                                attribute POIconv : String = "-";
                                attribute Ipoint : Boolean = false;
                                attribute mass : Real = 0.9481028071292676;
                                attribute 'σ_mass' : Real = 0.28909372274994966;
                                attribute Cx : Real = -73.64065079018474;
                                attribute 'σ_Cx' : Real = 28.721044428837228;
                                attribute Cy : Real = 38.0268766079098;
                                attribute 'σ_Cy' : Real = 28.23690002309109;
                                attribute Cz : Real = -23.092368990182877;
                                attribute 'σ_Cz' : Real = 29.057750463592832;
                                attribute Ixx : Real = 1.246507812897894;
                                attribute 'σ_Ixx' : Real = 0.37074144170588635;
                                attribute Iyy : Real = 1.1209699773329378;
                                attribute 'σ_Iyy' : Real = 0.3723953238821935;
                                attribute Izz : Real = 1.0497519594501963;
                                attribute 'σ_Izz' : Real = 0.37017423652493897;
                                attribute Ixy : Real = 0.012960458026935231;
                                attribute 'σ_Ixy' : Real = 0.02351283871158888;
                                attribute Ixz : Real = -0.07955311331156094;
                                attribute 'σ_Ixz' : Real = 0.022566176940390956;
                                attribute Iyz : Real = 0.14042367031222563;
                                attribute 'σ_Iyz' : Real = 0.02209918015384651;
                            }
                        }
                    }
                }
            }
            part <'C.1.2.3'> 'Element 7' {
                attribute POIconv : String = "-";
                attribute Ipoint : Boolean;
                attribute mass : Real;
                attribute 'σ_mass' : Real;
                attribute Cx : Real;
                attribute 'σ_Cx' : Real;
                attribute Cy : Real;
                attribute 'σ_Cy' : Real;
                attribute Cz : Real;
                attribute 'σ_Cz' : Real;
                attribute Ixx : Real;
                attribute 'σ_Ixx' : Real;
                attribute Iyy : Real;
                attribute 'σ_Iyy' : Real;
                attribute Izz : Real;
                attribute 'σ_Izz' : Real;
                attribute Ixy : Real;
                attribute 'σ_Ixy' : Real;
                attribute Ixz : Real;
                attribute 'σ_Ixz' : Real;
                attribute Iyz : Real;
                attribute 'σ_Iyz' : Real;
                part <'C.1.2.3.1'> 'Subsystem 23' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.2.3.1.1'> 'Assembly 83' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.1.1.1'> 'Subassembly 288' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.1.1.1'> 'Part 1018' {
                                attribute POIconv : String = "+";
                                attribute Ipoint : Boolean = false;
                                attribute mass : Real = 0.2714737224543933;
                                attribute 'σ_mass' : Real = 0.28909372274994966;
                                attribute Cx : Real = 79.75672213360667;
                                attribute 'σ_Cx' : Real = 28.721044428837228;
                                attribute Cy : Real = -47.84345794469118;
                                attribute 'σ_Cy' : Real = 28.23690002309109;
                                attribute Cz : Real = 37.33013062737882;
                                attribute 'σ_Cz' : Real = 29.057750463592832;
                                attribute Ixx : Real = 0.338813851766033;
                                attribute 'σ_Ixx' : Real = 0.37074144170588635;
                                attribute Iyy : Real = 0.32808673555829204;
                                attribute 'σ_Iyy' : Real = 0.3723953238821935;
                                attribute Izz : Real = 0.2635997353238293;
                                attribute 'σ_Izz' : Real = 0.37017423652493897;
                                attribute Ixy : Real = -0.00348121279006372;
                                attribute 'σ_Ixy' : Real = 0.02351283871158888;
                                attribute Ixz : Real = -0.0059289411663554226;
                                attribute 'σ_Ixz' : Real = 0.022566176940390956;
                                attribute Iyz : Real = 0.0010905838823576167;
                                attribute 'σ_Iyz' : Real = 0.02209918015384651;
                            }
                            part <'C.1.2.3.1.1.1.2'> 'Part 1019' {
                                attribute POIconv : String = "-";
                                attribute Ipoint : Boolean = false;
                                attribute mass : Real = 0.6140720751190092;
                                attribute 'σ_mass' : Real = 0.28909372274994966;
                                attribute Cx : Real = 41.76371074281633;
                                attribute 'σ_Cx' : Real = 28.721044428837228;
                                attribute Cy : Real = -13.316352106630802;
                                attribute 'σ_Cy' : Real = 28.23690002309109;
                                attribute Cz : Real = -30.140276066958904;
                                attribute 'σ_Cz' : Real = 29.057750463592832;
                                attribute Ixx : Real = 0.9758292338339816;
                                attribute 'σ_Ixx' : Real = 0.37074144170588635;
                                attribute Iyy : Real = 0.9945128023725424;
                                attribute 'σ_Iyy' : Real = 0.3723953238821935;
                                attribute Izz : Real = 0.9677428445822156;
                                attribute 'σ_Izz' : Real = 0.37017423652493897;
                                attribute Ixy : Real = 0.01581042094337401;
                                attribute 'σ_Ixy' : Real = 0.02351283871158888;
                                attribute Ixz : Real = 0.002628492911459966;
                                attribute 'σ_Ixz' : Real = 0.022566176940390956;
                                attribute Iyz : Real = 0.012784974508136617;
                                attribute 'σ_Iyz' : Real = 0.02209918015384651;
                            }
                            part <'C.1.2.3.1.1.1.3'> 'Part 1020' {
                                attribute POIconv : String = "-";
                                attribute Ipoint : Boolean = false;
                                attribute mass : Real = 0.3992901132279076;
                                attribute 'σ_mass' : Real = 0.28909372274994966;
                                attribute Cx : Real = 22.544915741309524;
                                attribute 'σ_Cx' : Real = 28.721044428837228;
                                attribute Cy : Real = 16.845566825941205;
                                attribute 'σ_Cy' : Real = 28.23690002309109;
                                attribute Cz : Real = 88.00809560343623;
                                attribute 'σ_Cz' : Real = 29.057750463592832;
                                attribute Ixx : Real = 0.49613217247505165;
                                attribute 'σ_Ixx' : Real = 0.37074144170588635;
                                attribute Iyy : Real = 0.5586903756185922;
                                attribute 'σ_Iyy' : Real = 0.3723953238821935;
                                attribute Izz : Real = 0.455115033082299;
                                attribute 'σ_Izz' : Real = 0.37017423652493897;
                                attribute Ixy : Real = 0.003961459110997396;
                                attribute 'σ_Ixy' : Real = 0.02351283871158888;
                                attribute Ixz : Real = -0.004567387177313131;
                                attribute 'σ_Ixz' : Real = 0.022566176940390956;
                                attribute Iyz : Real = 0.027750189879247933;
                                attribute 'σ_Iyz' : Real = 0.02209918015384651;
                            }
                            part <'C.1.2.3.1.1.1.4'> 'Part 1021' {
                                attribute POIconv : String = "-";
                                attribute Ipoint : Boolean = false;
                                attribute mass : Real = 0.5259728841318283;
                                attribute 'σ_mass' : Real = 0.28909372274994966;
                                attribute Cx : Real = -58.118884498253465;
                                attribute 'σ_Cx' : Real = 28.721044428837228;
                                attribute Cy : Real = -87.555838143453;
                                attribute 'σ_Cy' : Real = 28.23690002309109;
                                attribute Cz : Real = -98.82878721691668;
                                attribute 'σ_Cz' : Real = 29.057750463592832;
                                attribute Ixx : Real = 0.6712742996562501;
                                attribute 'σ_Ixx' : Real = 0.37074144170588635;
                                attribute Iyy : Real = 0.6522892461739314;
                                attribute 'σ_Iyy' : Real = 0.3723953238821935;
                                attribute Izz : Real = 0.6461367813144506;
                                attribute 'σ_Izz' : Real = 0.37017423652493897;
                                attribute Ixy : Real = 0.0046570648083672245;
                                attribute 'σ_Ixy' : Real = 0.02351283871158888;
                                attribute Ixz : Real = -0.021496487245712896;
                                attribute 'σ_Ixz' : Real = 0.022566176940390956;
                                attribute Iyz : Real = 0.05979432298398718;
                                attribute 'σ_Iyz' : Real = 0.02209918015384651;
                            }
                        }
                        part <'C.1.2.3.1.1.2'> 'Subassembly 289' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.1.2.1'> 'Part 1022' {
                                attribute POIconv : String = "+";
                                attribute Ipoint : Boolean = false;
                                attribute mass : Real = 0.3233482847209089;
                                attribute 'σ_mass' : Real = 0.28909372274994966;
                                attribute Cx : Real = 96.91439098678529;
                                attribute 'σ_Cx' : Real = 28.721044428837228;
                                attribute Cy : Real = -59.92609802633524;
                                attribute 'σ_Cy' : Real = 28.23690002309109;
                                attribute Cz : Real = -4.8784935381263494;
                                attribute 'σ_Cz' : Real = 29.057750463592832;
                                attribute Ixx : Real = 0.3794431984809574;
                                attribute 'σ_Ixx' : Real = 0.37074144170588635;
                                attribute Iyy : Real = 0.39538334417695803;
                                attribute 'σ_Iyy' : Real = 0.3723953238821935;
                                attribute Izz : Real = 0.3882085156366992;
                                attribute 'σ_Izz' : Real = 0.37017423652493897;
                                attribute Ixy : Real = -0.00833593018547131;
                                attribute 'σ_Ixy' : Real = 0.02351283871158888;
                                attribute Ixz : Real = 0.01595120031159023;
                                attribute 'σ_Ixz' : Real = 0.022566176940390956;
                                attribute Iyz : Real = -0.016044849710204007;
                                attribute 'σ_Iyz' : Real = 0.02209918015384651;
                            }
                            part <'C.1.2.3.1.1.2.2'> 'Part 1023' {
                                attribute POIconv : String = "-";
                                attribute Ipoint : Boolean = false;
                                attribute mass : Real = 0.8967885313592852;
                                attribute 'σ_mass' : Real = 0.28909372274994966;
                                attribute Cx : Real = 96.58187446184456;
                                attribute 'σ_Cx' : Real = 28.721044428837228;
                                attribute Cy : Real = -25.16317144036293;
                                attribute 'σ_Cy' : Real = 28.23690002309109;
                                attribute Cz : Real = 59.0921348426491;
                                attribute 'σ_Cz' : Real = 29.057750463592832;
                                attribute Ixx : Real = 0.9634658175781806;
                                attribute 'σ_Ixx' : Real = 0.37074144170588635;
                                attribute Iyy : Real = 1.074516750064507;
                                attribute 'σ_Iyy' : Real = 0.3723953238821935;
                                attribute Izz : Real = 1.0870171880647128;
                                attribute 'σ_Izz' : Real = 0.37017423652493897;
                                attribute Ixy : Real = 0.030280719388407304;
                                attribute 'σ_Ixy' : Real = 0.02351283871158888;
                                attribute Ixz : Real = -0.11039760567095933;
                                attribute 'σ_Ixz' : Real = 0.022566176940390956;
                                attribute Iyz : Real = 0.06213998552283999;
                                attribute 'σ_Iyz' : Real = 0.02209918015384651;
                            }
                        }
                    }
                    part <'C.1.2.3.1.2'> 'Assembly 84' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.1.2.1'> 'Subassembly 290' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.2.1.1'> 'Part 1024' {
                                attribute POIconv : String = "-";
                                attribute Ipoint : Boolean = false;
                                attribute mass : Real = 0.36056349496007895;
                                attribute 'σ_mass' : Real = 0.28909372274994966;
                                attribute Cx : Real = 74.903594981879;
                                attribute 'σ_Cx' : Real = 28.721044428837228;
                                attribute Cy : Real = -43.962585320696235;
                                attribute 'σ_Cy' : Real = 28.23690002309109;
                                attribute Cz : Real = -14.050036296248436;
                                attribute 'σ_Cz' : Real = 29.057750463592832;
                                attribute Ixx : Real = 0.37645157575398197;
                                attribute 'σ_Ixx' : Real = 0.37074144170588635;
                                attribute Iyy : Real = 0.4339364569021059;
                                attribute 'σ_Iyy' : Real = 0.3723953238821935;
                                attribute Izz : Real = 0.4222303506634136;
                                attribute 'σ_Izz' : Real = 0.37017423652493897;
                                attribute Ixy : Real = -0.012832195169406983;
                                attribute 'σ_Ixy' : Real = 0.02351283871158888;
                                attribute Ixz : Real = -0.028196857768589087;
                                attribute 'σ_Ixz' : Real = 0.022566176940390956;
                                attribute Iyz : Real = -0.006867982665523601;
                                attribute 'σ_Iyz' : Real = 0.02209918015384651;
                            }
                            part <'C.1.2.3.1.2.1.2'> 'Part 1025' {
                                attribute POIconv : String = "-";
                                attribute Ipoint : Boolean = false;
                                attribute mass : Real = 0.28386467407946475;
                                attribute 'σ_mass' : Real = 0.28909372274994966;
                                attribute Cx : Real = 68.0945314001292;
                                attribute 'σ_Cx' : Real = 28.721044428837228;
                                attribute Cy : Real = -54.774394957348704;
                                attribute 'σ_Cy' : Real = 28.23690002309109;
                                attribute Cz : Real = 2.8109159786254168;
                                attribute 'σ_Cz' : Real = 29.057750463592832;
                                attribute Ixx : Real = 0.3455054282681242;
                                attribute 'σ_Ixx' : Real = 0.37074144170588635;
                                attribute Iyy : Real = 0.319335019885562;
                                attribute 'σ_Iyy' : Real = 0.3723953238821935;
                                attribute Izz : Real = 0.3377785699564937;
                                attribute 'σ_Izz' : Real = 0.37017423652493897;
                                attribute Ixy : Real = -0.019487729589842406;
                                attribute 'σ_Ixy' : Real = 0.02351283871158888;
                                attribute Ixz : Real = -0.030441392086136818;
                                attribute 'σ_Ixz' : Real = 0.022566176940390956;
                                attribute Iyz : Real = 0.012651754000112921;
                                attribute 'σ_Iyz' : Real = 0.02209918015384651;
                            }
                            part <'C.1.2.3.1.2.1.3'> 'Part 1026' {
                                attribute POIconv : String = "+";
                                attribute Ipoint : Boolean = false;
                                attribute mass : Real = 0.23156337600271218;
                                attribute 'σ_mass' : Real = 0.28909372274994966;
                                attribute Cx : Real = -67.61877932585776;
                                attribute 'σ_Cx' : Real = 28.721044428837228;
                                attribute Cy : Real = 7.986530475318432;
                                attribute 'σ_Cy' : Real = 28.23690002309109;
                                attribute Cz : Real = -22.457342129200697;
                                attribute 'σ_Cz' : Real = 29.057750463592832;
                                attribute Ixx : Real = 0.29036869938459164;
                                attribute 'σ_Ixx' : Real = 0.37074144170588635;
                                attribute Iyy : Real = 0.3037983540131558;
                                attribute 'σ_Iyy' : Real = 0.3723953238821935;
                                attribute Izz : Real = 0.3033854697711728;
                                attribute 'σ_Izz' : Real = 0.37017423652493897;
                                attribute Ixy : Real = -0.015408500102457081;
                                attribute 'σ_Ixy' : Real = 0.02351283871158888;
                                attribute Ixz : Real = 0.0086938966227247845;
                                attribute 'σ_Ixz' : Real = 0.022566176940390956;
                                attribute Iyz : Real = -0.02130395195673237;
                                attribute 'σ_Iyz' : Real = 0.02209918015384651;
                            }
                            part <'C.1.2.3.1.2.1.4'> 'Part 1027' {
                                attribute POIconv : String = "-";
                                attribute Ipoint : Boolean = false;
                                attribute mass : Real = 0.2350679253905546;
                                attribute 'σ_mass' : Real = 0.28909372274994966;
                                attribute Cx : Real = 74.80033696629107;
                                attribute 'σ_Cx' : Real = 28.721044428837228;
                                attribute Cy : Real = 10.899268742650747;
                                attribute 'σ_Cy' : Real = 28.23690002309109;
                                attribute Cz : Real = -22.739830799400806;
                                attribute 'σ_Cz' : Real = 29.057750463592832;
                                attribute Ixx : Real = 0.2970339860488817;
                                attribute 'σ_Ixx' : Real = 0.37074144170588635;
                                attribute Iyy : Real = 0.298674204183194;
                                attribute 'σ_Iyy' : Real = 0.3723953238821935;
                                attribute Izz : Real = 0.32429851049119174;
                                attribute 'σ_Izz' : Real = 0.37017423652493897;
                                attribute Ixy : Real = 0.0021527023303478036;
                                attribute 'σ_Ixy' : Real = 0.02351283871158888;
                                attribute Ixz : Real = 0.010038598246872399;
                                attribute 'σ_Ixz' : Real = 0.022566176940390956;
                                attribute Iyz : Real = 4.260807488943631e-4;
                                attribute 'σ_Iyz' : Real = 0.02209918015384651;
                            }
                        }
                        part <'C.1.2.3.1.2.2'> 'Subassembly 291' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.2.2.1'> 'Part 1028' {
                                attribute POIconv : String = "-";
                                attribute Ipoint : Boolean = false;
                                attribute mass : Real = 0.9854304553838447;
                                attribute 'σ_mass' : Real = 0.28909372274994966;
                                attribute Cx : Real = -46.41855643130839;
                                attribute 'σ_Cx' : Real = 28.721044428837228;
                                attribute Cy : Real = 69.41389311105013;
                                attribute 'σ_Cy' : Real = 28.23690002309109;
                                attribute Cz : Real = -34.333817986771464;
                                attribute 'σ_Cz' : Real = 29.057750463592832;
                                attribute Ixx : Real = 1.1745379913630323;
                                attribute 'σ_Ixx' : Real = 0.37074144170588635;
                                attribute Iyy : Real = 1.2318771445603012;
                                attribute 'σ_Iyy' : Real = 0.3723953238821935;
                                attribute Izz : Real = 1.0344128409711042;
                                attribute 'σ_Izz' : Real = 0.37017423652493897;
                                attribute Ixy : Real = -0.0248720546664876;
                                attribute 'σ_Ixy' : Real = 0.02351283871158888;
                                attribute Ixz : Real = 0.11754377707019359;
                                attribute 'σ_Ixz' : Real = 0.022566176940390956;
                                attribute Iyz : Real = 0.07310842433924039;
                                attribute 'σ_Iyz' : Real = 0.02209918015384651;
                            }
                            part <'C.1.2.3.1.2.2.2'> 'Part 1029' {
                                attribute POIconv : String = "-";
                                attribute Ipoint : Boolean = false;
                                attribute mass : Real = 0.4805381577296648;
                                attribute 'σ_mass' : Real = 0.28909372274994966;
                                attribute Cx : Real = -51.79176856763661;
                                attribute 'σ_Cx' : Real = 28.721044428837228;
                                attribute Cy : Real = -68.34773179143667;
                                attribute 'σ_Cy' : Real = 28.23690002309109;
                                attribute Cz : Real = -19.806827697902918;
                                attribute 'σ_Cz' : Real = 29.057750463592832;
                                attribute Ixx : Real = 0.4252615031969518;
                                attribute 'σ_Ixx' : Real = 0.37074144170588635;
                                attribute Iyy : Real = 0.4468632274660892;
                                attribute 'σ_Iyy' : Real = 0.3723953238821935;
                                attribute Izz : Real = 0.4520839455535829;
                                attribute 'σ_Izz' : Real = 0.37017423652493897;
                                attribute Ixy : Real = -0.015775196673174598;
                                attribute 'σ_Ixy' : Real = 0.02351283871158888;
                                attribute Ixz : Real = 0.0024492739737420996;
                                attribute 'σ_Ixz' : Real = 0.022566176940390956;
                                attribute Iyz : Real = -0.007405177985282297;
                                attribute 'σ_Iyz' : Real = 0.02209918015384651;
                            }
                            part <'C.1.2.3.1.2.2.3'> 'Part 1030' {
                                attribute POIconv : String = "+";
                                attribute Ipoint : Boolean = false;
                                attribute mass : Real = 0.19013544256146997;
                                attribute 'σ_mass' : Real = 0.28909372274994966;
                                attribute Cx : Real = -61.670681508257985;
                                attribute 'σ_Cx' : Real = 28.721044428837228;
                                attribute Cy : Real = -26.477308245375752;
                                attribute 'σ_Cy' : Real = 28.23690002309109;
                                attribute Cz : Real = -12.132368283346295;
                                attribute 'σ_Cz' : Real = 29.057750463592832;
                                attribute Ixx : Real = 0.25479736142580073;
                                attribute 'σ_Ixx' : Real = 0.37074144170588635;
                                attribute Iyy : Real = 0.2763441582313683;
                                attribute 'σ_Iyy' : Real = 0.3723953238821935;
                                attribute Izz : Real = 0.22144415543644014;
                                attribute 'σ_Izz' : Real = 0.37017423652493897;
                                attribute Ixy : Real = -0.006838077576182519;
                                attribute 'σ_Ixy' : Real = 0.02351283871158888;
                                attribute Ixz : Real = 0.005283864889242323;
                                attribute 'σ_Ixz' : Real = 0.022566176940390956;
                                attribute Iyz : Real = -4.3688253103186885e-4;
                                attribute 'σ_Iyz' : Real = 0.02209918015384651;
                            }
                            part <'C.1.2.3.1.2.2.4'> 'Part 1031' {
                                attribute POIconv : String = "-";
                                attribute Ipoint : Boolean = false;
                                attribute mass : Real = 0.11593558303709142;
                                attribute 'σ_mass' : Real = 0.28909372274994966;
                                attribute Cx : Real = -32.33528942801058;
                                attribute 'σ_Cx' : Real = 28.721044428837228;
                                attribute Cy : Real = 72.48143367469311;
                                attribute 'σ_Cy' : Real = 28.23690002309109;
                                attribute Cz : Real = -67.7624145988375;
                                attribute 'σ_Cz' : Real = 29.057750463592832;
                                attribute Ixx : Real = 0.16064184465428846;
                                attribute 'σ_Ixx' : Real = 0.37074144170588635;
                                attribute Iyy : Real = 0.1581539359278079;
                                attribute 'σ_Iyy' : Real = 0.3723953238821935;
                                attribute Izz : Real = 0.13849539528318897;
                                attribute 'σ_Izz' : Real = 0.37017423652493897;
                                attribute Ixy : Real = 0.00633287031607507;
                                attribute 'σ_Ixy' : Real = 0.02351283871158888;
                                attribute Ixz : Real = -0.007801961933453122;
                                attribute 'σ_Ixz' : Real = 0.022566176940390956;
                                attribute Iyz : Real = -0.00675677936258264;
                                attribute 'σ_Iyz' : Real = 0.02209918015384651;
                            }
                            part <'C.1.2.3.1.2.2.5'> 'Part 1032' {
                                attribute POIconv : String = "-";
                                attribute Ipoint : Boolean = false;
                                attribute mass : Real = 0.36539430637820625;
                                attribute 'σ_mass' : Real = 0.28909372274994966;
                                attribute Cx : Real = 6.901369569823146;
                                attribute 'σ_Cx' : Real = 28.721044428837228;
                                attribute Cy : Real = -8.53817998431623;
                                attribute 'σ_Cy' : Real = 28.23690002309109;
                                attribute Cz : Real = -26.222652290016413;
                                attribute 'σ_Cz' : Real = 29.057750463592832;
                                attribute Ixx : Real = 0.47870142572940394;
                                attribute 'σ_Ixx' : Real = 0.37074144170588635;
                                attribute Iyy : Real = 0.45534335620023697;
                                attribute 'σ_Iyy' : Real = 0.3723953238821935;
                                attribute Izz : Real = 0.4424887476004629;
                                attribute 'σ_Izz' : Real = 0.37017423652493897;
                                attribute Ixy : Real = 0.057474077807164646;
                                attribute 'σ_Ixy' : Real = 0.02351283871158888;
                                attribute Ixz : Real = 0.025208377588377406;
                                attribute 'σ_Ixz' : Real = 0.022566176940390956;
                                attribute Iyz : Real = 0.01665357844630759;
                                attribute 'σ_Iyz' : Real = 0.02209918015384651;
                            }
                        }
                        part <'C.1.2.3.1.2.3'> 'Subassembly 292' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.2.3.1'> 'Part 1033' {
                                attribute POIconv : String = "-";
                                attribute Ipoint : Boolean = false;
                                attribute mass : Real = 0.8863196952578146;
                                attribute 'σ_mass' : Real = 0.28909372274994966;
                                attribute Cx : Real = -52.10150717757642;
                                attribute 'σ_Cx' : Real = 28.721044428837228;
                                attribute Cy : Real = -67.03568380326033;
                                attribute 'σ_Cy' : Real = 28.23690002309109;
                                attribute Cz : Real = -95.41013021953404;
                                attribute 'σ_Cz' : Real = 29.057750463592832;
                                attribute Ixx : Real = 1.0591793710191624;
                                attribute 'σ_Ixx' : Real = 0.37074144170588635;
                                attribute Iyy : Real = 1.2510701729432208;
                                attribute 'σ_Iyy' : Real = 0.3723953238821935;
                                attribute Izz : Real = 1.0887818618774248;
                                attribute 'σ_Izz' : Real = 0.37017423652493897;
                                attribute Ixy : Real = -0.040112172222578915;
                                attribute 'σ_Ixy' : Real = 0.02351283871158888;
                                attribute Ixz : Real = -0.005120049018534828;
                                attribute 'σ_Ixz' : Real = 0.022566176940390956;
                                attribute Iyz : Real = 0.024889461881570832;
                                attribute 'σ_Iyz' : Real = 0.02209918015384651;
                            }
                            part <'C.1.2.3.1.2.3.2'> 'Part 1034' {
                                attribute POIconv : String = "+";
                                attribute Ipoint : Boolean = false;
                                attribute mass : Real = 0.006527662138221786;
                                attribute 'σ_mass' : Real = 0.28909372274994966;
                                attribute Cx : Real = 43.002137867733836;
                                attribute 'σ_Cx' : Real = 28.721044428837228;
                                attribute Cy : Real = 1.2415521778166294;
                                attribute 'σ_Cy' : Real = 28.23690002309109;
                                attribute Cz : Real = -43.24038987979293;
                                attribute 'σ_Cz' : Real = 29.057750463592832;
                                attribute Ixx : Real = 0.007583466824313199;
                                attribute 'σ_Ixx' : Real = 0.37074144170588635;
                                attribute Iyy : Real = 0.007143444902016918;
                                attribute 'σ_Iyy' : Real = 0.3723953238821935;
                                attribute Izz : Real = 0.006801558438289208;
                                attribute 'σ_Izz' : Real = 0.37017423652493897;
                                attribute Ixy : Real = 1.073007562773667e-4;
                                attribute 'σ_Ixy' : Real = 0.02351283871158888;
                                attribute Ixz : Real = -4.781643862808727e-4;
                                attribute 'σ_Ixz' : Real = 0.022566176940390956;
                                attribute Iyz : Real = -7.264905940677425e-4;
                                attribute 'σ_Iyz' : Real = 0.02209918015384651;
                            }
                            part <'C.1.2.3.1.2.3.3'> 'Part 1035' {
                                attribute POIconv : String = "-";
                                attribute Ipoint : Boolean = false;
                                attribute mass : Real = 0.01258344086725265;
                                attribute 'σ_mass' : Real = 0.28909372274994966;
                                attribute Cx : Real = -64.23425571992993;
                                attribute 'σ_Cx' : Real = 28.721044428837228;
                                attribute Cy : Real = 23.354554967954755;
                                attribute 'σ_Cy' : Real = 28.23690002309109;
                                attribute Cz : Real = -5.638757953420281;
                                attribute 'σ_Cz' : Real = 29.057750463592832;
                                attribute Ixx : Real = 0.017135310471390098;
                                attribute 'σ_Ixx' : Real = 0.37074144170588635;
                                attribute Iyy : Real = 0.01609576890067113;
                                attribute 'σ_Iyy' : Real = 0.3723953238821935;
                                attribute Izz : Real = 0.017034289421131867;
                                attribute 'σ_Izz' : Real = 0.37017423652493897;
                                attribute Ixy : Real = 7.043150609314924e-4;
                                attribute 'σ_Ixy' : Real = 0.02351283871158888;
                                attribute Ixz : Real = 1.3538241598545948e-4;
                                attribute 'σ_Ixz' : Real = 0.022566176940390956;
                                attribute Iyz : Real = 6.950651548896436e-4;
                                attribute 'σ_Iyz' : Real = 0.02209918015384651;
                            }
                            part <'C.1.2.3.1.2.3.4'> 'Part 1036' {
                                attribute POIconv : String = "+";
                                attribute Ipoint : Boolean = false;
                                attribute mass : Real = 0.268131818715483;
                                attribute 'σ_mass' : Real = 0.28909372274994966;
                                attribute Cx : Real = -24.453301914036274;
                                attribute 'σ_Cx' : Real = 28.721044428837228;
                                attribute Cy : Real = 37.71373191848397;
                                attribute 'σ_Cy' : Real = 28.23690002309109;
                                attribute Cz : Real = -80.053954385221;
                                attribute 'σ_Cz' : Real = 29.057750463592832;
                                attribute Ixx : Real = 0.40041169517935266;
                                attribute 'σ_Ixx' : Real = 0.37074144170588635;
                                attribute Iyy : Real = 0.327437737724792;
                                attribute 'σ_Iyy' : Real = 0.3723953238821935;
                                attribute Izz : Real = 0.3363708239324448;
                                attribute 'σ_Izz' : Real = 0.37017423652493897;
                                attribute Ixy : Real = -0.029975816930480827;
                                attribute 'σ_Ixy' : Real = 0.02351283871158888;
                                attribute Ixz : Real = 0.012019934535980445;
                                attribute 'σ_Ixz' : Real = 0.022566176940390956;
                                attribute Iyz : Real = 0.0012284113063380474;
                                attribute 'σ_Iyz' : Real = 0.02209918015384651;
                            }
                            part <'C.1.2.3.1.2.3.5'> 'Part 1037' {
                                attribute POIconv : String = "+";
                                attribute Ipoint : Boolean = false;
                                attribute mass : Real = 0.6671921835553367;
                                attribute 'σ_mass' : Real = 0.28909372274994966;
                                attribute Cx : Real = -22.613744344562292;
                                attribute 'σ_Cx' : Real = 28.721044428837228;
                                attribute Cy : Real = 5.095232650637627;
                                attribute 'σ_Cy' : Real = 28.23690002309109;
                                attribute Cz : Real = -63.575286930426955;
                                attribute 'σ_Cz' : Real = 29.057750463592832;
                                attribute Ixx : Real = 0.7633558794777816;
                                attribute 'σ_Ixx' : Real = 0.37074144170588635;
                                attribute Iyy : Real = 0.6969343406144651;
                                attribute 'σ_Iyy' : Real = 0.3723953238821935;
                                attribute Izz : Real = 0.7637621574057223;
                                attribute 'σ_Izz' : Real = 0.37017423652493897;
                                attribute Ixy : Real = 0.03459677537013358;
                                attribute 'σ_Ixy' : Real = 0.02351283871158888;
                                attribute Ixz : Real = -0.029188026897170583;
                                attribute 'σ_Ixz' : Real = 0.022566176940390956;
                                attribute Iyz : Real = -0.04084380930445912;
                                attribute 'σ_Iyz' : Real = 0.02209918015384651;
                            }
                        }
                    }
                    part <'C.1.2.3.1.3'> 'Assembly 85' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.1.3.1'> 'Subassembly 293' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.3.1.1'> 'Part 1038' {
                                attribute POIconv : String = "+";
                                attribute Ipoint : Boolean = false;
                                attribute mass : Real = 0.5550174316570629;
                                attribute 'σ_mass' : Real = 0.28909372274994966;
                                attribute Cx : Real = -83.23413799516857;
                                attribute 'σ_Cx' : Real = 28.721044428837228;
                                attribute Cy : Real = -75.53682094439864;
                                attribute 'σ_Cy' : Real = 28.23690002309109;
                                attribute Cz : Real = 11.247013928368688;
                                attribute 'σ_Cz' : Real = 29.057750463592832;
                                attribute Ixx : Real = 0.7261047515231042;
                                attribute 'σ_Ixx' : Real = 0.37074144170588635;
                                attribute Iyy : Real = 0.8144103175995534;
                                attribute 'σ_Iyy' : Real = 0.3723953238821935;
                                attribute Izz : Real = 0.7389736737162942;
                                attribute 'σ_Izz' : Real = 0.37017423652493897;
                                attribute Ixy : Real = -6.030436115606549e-4;
                                attribute 'σ_Ixy' : Real = 0.02351283871158888;
                                attribute Ixz : Real = 0.011390652148165729;
                                attribute 'σ_Ixz' : Real = 0.022566176940390956;
                                attribute Iyz : Real = 0.005607807353903772;
                                attribute 'σ_Iyz' : Real = 0.02209918015384651;
                            }
                            part <'C.1.2.3.1.3.1.2'> 'Part 1039' {
                                attribute POIconv : String = "+";
                                attribute Ipoint : Boolean = false;
                                attribute mass : Real = 0.6380803078019526;
                                attribute 'σ_mass' : Real = 0.28909372274994966;
                                attribute Cx : Real = 28.728295722976327;
                                attribute 'σ_Cx' : Real = 28.721044428837228;
                                attribute Cy : Real = 16.28398336470127;
                                attribute 'σ_Cy' : Real = 28.23690002309109;
                                attribute Cz : Real = -48.897430719807744;
                                attribute 'σ_Cz' : Real = 29.057750463592832;
                                attribute Ixx : Real = 0.736063269747002;
                                attribute 'σ_Ixx' : Real = 0.37074144170588635;
                                attribute Iyy : Real = 0.7347650639624751;
                                attribute 'σ_Iyy' : Real = 0.3723953238821935;
                                attribute Izz : Real = 0.8064009702170114;
                                attribute 'σ_Izz' : Real = 0.37017423652493897;
                                attribute Ixy : Real = 4.1781764174185656e-4;
                                attribute 'σ_Ixy' : Real = 0.02351283871158888;
                                attribute Ixz : Real = 0.0028424401788568494;
                                attribute 'σ_Ixz' : Real = 0.022566176940390956;
                                attribute Iyz : Real = -0.010720685006515032;
                                attribute 'σ_Iyz' : Real = 0.02209918015384651;
                            }
                            part <'C.1.2.3.1.3.1.3'> 'Part 1040' {
                                attribute POIconv : String = "-";
                                attribute Ipoint : Boolean = false;
                                attribute mass : Real = 0.3094720288219396;
                                attribute 'σ_mass' : Real = 0.28909372274994966;
                                attribute Cx : Real = -24.840944446623325;
                                attribute 'σ_Cx' : Real = 28.721044428837228;
                                attribute Cy : Real = -5.2813556510955095;
                                attribute 'σ_Cy' : Real = 28.23690002309109;
                                attribute Cz : Real = -75.69127320311964;
                                attribute 'σ_Cz' : Real = 29.057750463592832;
                                attribute Ixx : Real = 0.36016045845070477;
                                attribute 'σ_Ixx' : Real = 0.37074144170588635;
                                attribute Iyy : Real = 0.35454182068610607;
                                attribute 'σ_Iyy' : Real = 0.3723953238821935;
                                attribute Izz : Real = 0.35479705701181236;
                                attribute 'σ_Izz' : Real = 0.37017423652493897;
                                attribute Ixy : Real = 0.0039038446238540627;
                                attribute 'σ_Ixy' : Real = 0.02351283871158888;
                                attribute Ixz : Real = -0.001795304792344311;
                                attribute 'σ_Ixz' : Real = 0.022566176940390956;
                                attribute Iyz : Real = -0.008648017760423093;
                                attribute 'σ_Iyz' : Real = 0.02209918015384651;
                            }
                            part <'C.1.2.3.1.3.1.4'> 'Part 1041' {
                                attribute POIconv : String = "-";
                                attribute Ipoint : Boolean = false;
                                attribute mass : Real = 0.16986004425073042;
                                attribute 'σ_mass' : Real = 0.28909372274994966;
                                attribute Cx : Real = -0.2717094961553812;
                                attribute 'σ_Cx' : Real = 28.721044428837228;
                                attribute Cy : Real = -21.255956683307886;
                                attribute 'σ_Cy' : Real = 28.23690002309109;
                                attribute Cz : Real = -38.88189485296607;
                                attribute 'σ_Cz' : Real = 29.057750463592832;
                                attribute Ixx : Real = 0.21849133361234896;
                                attribute 'σ_Ixx' : Real = 0.37074144170588635;
                                attribute Iyy : Real = 0.18388470079723432;
                                attribute 'σ_Iyy' : Real = 0.3723953238821935;
                                attribute Izz : Real = 0.2200873704419569;
                                attribute 'σ_Izz' : Real = 0.37017423652493897;
                                attribute Ixy : Real = 0.006259424424891615;
                                attribute 'σ_Ixy' : Real = 0.02351283871158888;
                                attribute Ixz : Real = 0.00038441467799992017;
                                attribute 'σ_Ixz' : Real = 0.022566176940390956;
                                attribute Iyz : Real = 2.6529433137622075e-4;
                                attribute 'σ_Iyz' : Real = 0.02209918015384651;
                            }
                            part <'C.1.2.3.1.3.1.5'> 'Part 1042' {
                                attribute POIconv : String = "-";
                                attribute Ipoint : Boolean = false;
                                attribute mass : Real = 0.5001672283564694;
                                attribute 'σ_mass' : Real = 0.28909372274994966;
                                attribute Cx : Real = -27.933583734557033;
                                attribute 'σ_Cx' : Real = 28.721044428837228;
                                attribute Cy : Real = -75.44109709560871;
                                attribute 'σ_Cy' : Real = 28.23690002309109;
                                attribute Cz : Real = -52.39798869006336;
                                attribute 'σ_Cz' : Real = 29.057750463592832;
                                attribute Ixx : Real = 0.6248696392366354;
                                attribute 'σ_Ixx' : Real = 0.37074144170588635;
                                attribute Iyy : Real = 0.6197903049561545;
                                attribute 'σ_Iyy' : Real = 0.3723953238821935;
                                attribute Izz : Real = 0.6683337745048498;
                                attribute 'σ_Izz' : Real = 0.37017423652493897;
                                attribute Ixy : Real = -0.0188628541866031;
                                attribute 'σ_Ixy' : Real = 0.02351283871158888;
                                attribute Ixz : Real = -6.235961041831588e-4;
                                attribute 'σ_Ixz' : Real = 0.022566176940390956;
                                attribute Iyz : Real = 0.008185718381841973;
                                attribute 'σ_Iyz' : Real = 0.02209918015384651;
                            }
                        }
                        part <'C.1.2.3.1.3.2'> 'Subassembly 294' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.3.2.1'> 'Part 1043' {
                                attribute POIconv : String = "+";
                                attribute Ipoint : Boolean = false;
                                attribute mass : Real = 0.8633369037602097;
                                attribute 'σ_mass' : Real = 0.28909372274994966;
                                attribute Cx : Real = -29.717338038608432;
                                attribute 'σ_Cx' : Real = 28.721044428837228;
                                attribute Cy : Real = -75.35580983385444;
                                attribute 'σ_Cy' : Real = 28.23690002309109;
                                attribute Cz : Real = 71.45699337124825;
                                attribute 'σ_Cz' : Real = 29.057750463592832;
                                attribute Ixx : Real = 1.0316033114297507;
                                attribute 'σ_Ixx' : Real = 0.37074144170588635;
                                attribute Iyy : Real = 1.130442947356974;
                                attribute 'σ_Iyy' : Real = 0.3723953238821935;
                                attribute Izz : Real = 1.2345906690436015;
                                attribute 'σ_Izz' : Real = 0.37017423652493897;
                                attribute Ixy : Real = 0.051741394502052014;
                                attribute 'σ_Ixy' : Real = 0.02351283871158888;
                                attribute Ixz : Real = -0.07750720716025238;
                                attribute 'σ_Ixz' : Real = 0.022566176940390956;
                                attribute Iyz : Real = 0.013980486910605699;
                                attribute 'σ_Iyz' : Real = 0.02209918015384651;
                            }
                            part <'C.1.2.3.1.3.2.2'> 'Part 1044' {
                                attribute POIconv : String = "+";
                                attribute Ipoint : Boolean = false;
                                attribute mass : Real = 0.09922996710124425;
                                attribute 'σ_mass' : Real = 0.28909372274994966;
                                attribute Cx : Real = 99.88611694425344;
                                attribute 'σ_Cx' : Real = 28.721044428837228;
                                attribute Cy : Real = -91.37837020680308;
                                attribute 'σ_Cy' : Real = 28.23690002309109;
                                attribute Cz : Real = 65.90019408613443;
                                attribute 'σ_Cz' : Real = 29.057750463592832;
                                attribute Ixx : Real = 0.12816754401706107;
                                attribute 'σ_Ixx' : Real = 0.37074144170588635;
                                attribute Iyy : Real = 0.13774139237629984;
                                attribute 'σ_Iyy' : Real = 0.3723953238821935;
                                attribute Izz : Real = 0.12952318542842847;
                                attribute 'σ_Izz' : Real = 0.37017423652493897;
                                attribute Ixy : Real = 0.00564019582603183;
                                attribute 'σ_Ixy' : Real = 0.02351283871158888;
                                attribute Ixz : Real = -0.004769807480596106;
                                attribute 'σ_Ixz' : Real = 0.022566176940390956;
                                attribute Iyz : Real = 0.0022006033112167366;
                                attribute 'σ_Iyz' : Real = 0.02209918015384651;
                            }
                        }
                    }
                    part <'C.1.2.3.1.4'> 'Assembly 86' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.1.4.1'> 'Subassembly 295' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.4.1.1'> 'Part 1045' {
                                attribute POIconv : String = "+";
                                attribute Ipoint : Boolean = false;
                                attribute mass : Real = 0.8652523746620864;
                                attribute 'σ_mass' : Real = 0.28909372274994966;
                                attribute Cx : Real = -67.81035801395774;
                                attribute 'σ_Cx' : Real = 28.721044428837228;
                                attribute Cy : Real = 28.574663773179054;
                                attribute 'σ_Cy' : Real = 28.23690002309109;
                                attribute Cz : Real = 26.51412351988256;
                                attribute 'σ_Cz' : Real = 29.057750463592832;
                                attribute Ixx : Real = 0.9952737849813976;
                                attribute 'σ_Ixx' : Real = 0.37074144170588635;
                                attribute Iyy : Real = 0.9357890231830773;
                                attribute 'σ_Iyy' : Real = 0.3723953238821935;
                                attribute Izz : Real = 0.9740654577356895;
                                attribute 'σ_Izz' : Real = 0.37017423652493897;
                                attribute Ixy : Real = -0.07900628699054632;
                                attribute 'σ_Ixy' : Real = 0.02351283871158888;
                                attribute Ixz : Real = 0.07016981104621788;
                                attribute 'σ_Ixz' : Real = 0.022566176940390956;
                                attribute Iyz : Real = -0.061090488446185656;
                                attribute 'σ_Iyz' : Real = 0.02209918015384651;
                            }
                            part <'C.1.2.3.1.4.1.2'> 'Part 1046' {
                                attribute POIconv : String = "+";
                                attribute Ipoint : Boolean = false;
                                attribute mass : Real = 0.03140033738268539;
                                attribute 'σ_mass' : Real = 0.28909372274994966;
                                attribute Cx : Real = 89.0315999276936;
                                attribute 'σ_Cx' : Real = 28.721044428837228;
                                attribute Cy : Real = -89.93275687098503;
                                attribute 'σ_Cy' : Real = 28.23690002309109;
                                attribute Cz : Real = 65.84327514283359;
                                attribute 'σ_Cz' : Real = 29.057750463592832;
                                attribute Ixx : Real = 0.04006659707022646;
                                attribute 'σ_Ixx' : Real = 0.37074144170588635;
                                attribute Iyy : Real = 0.042851373811632544;
                                attribute 'σ_Iyy' : Real = 0.3723953238821935;
                                attribute Izz : Real = 0.041866582474210295;
                                attribute 'σ_Izz' : Real = 0.37017423652493897;
                                attribute Ixy : Real = -1.1134199603787096e-4;
                                attribute 'σ_Ixy' : Real = 0.02351283871158888;
                                attribute Ixz : Real = 1.9898372714573546e-4;
                                attribute 'σ_Ixz' : Real = 0.022566176940390956;
                                attribute Iyz : Real = 1.8332563179450815e-4;
                                attribute 'σ_Iyz' : Real = 0.02209918015384651;
                            }
                        }
                        part <'C.1.2.3.1.4.2'> 'Subassembly 296' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.4.2.1'> 'Part 1047' {
                                attribute POIconv : String = "+";
                                attribute Ipoint : Boolean = false;
                                attribute mass : Real = 0.2642831369091291;
                                attribute 'σ_mass' : Real = 0.28909372274994966;
                                attribute Cx : Real = 96.24938839115202;
                                attribute 'σ_Cx' : Real = 28.721044428837228;
                                attribute Cy : Real = -64.10846440121531;
                                attribute 'σ_Cy' : Real = 28.23690002309109;
                                attribute Cz : Real = 68.2395697105676;
                                attribute 'σ_Cz' : Real = 29.057750463592832;
                                attribute Ixx : Real = 0.3765125075978308;
                                attribute 'σ_Ixx' : Real = 0.37074144170588635;
                                attribute Iyy : Real = 0.3205503440554988;
                                attribute 'σ_Iyy' : Real = 0.3723953238821935;
                                attribute Izz : Real = 0.344764225930941;
                                attribute 'σ_Izz' : Real = 0.37017423652493897;
                                attribute Ixy : Real = -0.013281969353616255;
                                attribute 'σ_Ixy' : Real = 0.02351283871158888;
                                attribute Ixz : Real = -0.042489145372811676;
                                attribute 'σ_Ixz' : Real = 0.022566176940390956;
                                attribute Iyz : Real = -0.008543652033743514;
                                attribute 'σ_Iyz' : Real = 0.02209918015384651;
                            }
                            part <'C.1.2.3.1.4.2.2'> 'Part 1048' {
                                attribute POIconv : String = "-";
                                attribute Ipoint : Boolean = false;
                                attribute mass : Real = 0.999615342994919;
                                attribute 'σ_mass' : Real = 0.28909372274994966;
                                attribute Cx : Real = -51.21070072054863;
                                attribute 'σ_Cx' : Real = 28.721044428837228;
                                attribute Cy : Real = -89.31024805642664;
                                attribute 'σ_Cy' : Real = 28.23690002309109;
                                attribute Cz : Real = -62.562374444678426;
                                attribute 'σ_Cz' : Real = 29.057750463592832;
                                attribute Ixx : Real = 1.2056185845625573;
                                attribute 'σ_Ixx' : Real = 0.37074144170588635;
                                attribute Iyy : Real = 1.1665602386299811;
                                attribute 'σ_Iyy' : Real = 0.3723953238821935;
                                attribute Izz : Real = 1.2714362956349599;
                                attribute 'σ_Izz' : Real = 0.37017423652493897;
                                attribute Ixy : Real = 0.040719956767876625;
                                attribute 'σ_Ixy' : Real = 0.02351283871158888;
                                attribute Ixz : Real = -0.0028392401073712376;
                                attribute 'σ_Ixz' : Real = 0.022566176940390956;
                                attribute Iyz : Real = -0.0039137879003151715;
                                attribute 'σ_Iyz' : Real = 0.02209918015384651;
                            }
                            part <'C.1.2.3.1.4.2.3'> 'Part 1049' {
                                attribute POIconv : String = "+";
                                attribute Ipoint : Boolean = false;
                                attribute mass : Real = 0.12687110711215063;
                                attribute 'σ_mass' : Real = 0.28909372274994966;
                                attribute Cx : Real = -24.90128637291491;
                                attribute 'σ_Cx' : Real = 28.721044428837228;
                                attribute Cy : Real = -84.25761237740517;
                                attribute 'σ_Cy' : Real = 28.23690002309109;
                                attribute Cz : Real = -28.610008023679256;
                                attribute 'σ_Cz' : Real = 29.057750463592832;
                                attribute Ixx : Real = 0.14988434141791196;
                                attribute 'σ_Ixx' : Real = 0.37074144170588635;
                                attribute Iyy : Real = 0.14728455865374115;
                                attribute 'σ_Iyy' : Real = 0.3723953238821935;
                                attribute Izz : Real = 0.1630007169630277;
                                attribute 'σ_Izz' : Real = 0.37017423652493897;
                                attribute Ixy : Real = 0.0032933174822273974;
                                attribute 'σ_Ixy' : Real = 0.02351283871158888;
                                attribute Ixz : Real = 3.048478651590396e-4;
                                attribute 'σ_Ixz' : Real = 0.022566176940390956;
                                attribute Iyz : Real = 0.008232396454768759;
                                attribute 'σ_Iyz' : Real = 0.02209918015384651;
                            }
                            part <'C.1.2.3.1.4.2.4'> 'Part 1050' {
                                attribute POIconv : String = "+";
                                attribute Ipoint : Boolean = false;
                                attribute mass : Real = 0.12058695780276321;
                                attribute 'σ_mass' : Real = 0.28909372274994966;
                                attribute Cx : Real = 37.75184159167111;
                                attribute 'σ_Cx' : Real = 28.721044428837228;
                                attribute Cy : Real = -97.41140520200133;
                                attribute 'σ_Cy' : Real = 28.23690002309109;
                                attribute Cz : Real = -43.341012205928564;
                                attribute 'σ_Cz' : Real = 29.057750463592832;
                                attribute Ixx : Real = 0.16137069474304677;
                                attribute 'σ_Ixx' : Real = 0.37074144170588635;
                                attribute Iyy : Real = 0.17364600231446742;
                                attribute 'σ_Iyy' : Real = 0.3723953238821935;
                                attribute Izz : Real = 0.15561126203617454;
                                attribute 'σ_Izz' : Real = 0.37017423652493897;
                                attribute Ixy : Real = -0.019312389766490683;
                                attribute 'σ_Ixy' : Real = 0.02351283871158888;
                                attribute Ixz : Real = -5.302972116278399e-4;
                                attribute 'σ_Ixz' : Real = 0.022566176940390956;
                                attribute Iyz : Real = -0.004469059817591223;
                                attribute 'σ_Iyz' : Real = 0.02209918015384651;
                            }
                            part <'C.1.2.3.1.4.2.5'> 'Part 1051' {
                                attribute POIconv : String = "-";
                                attribute Ipoint : Boolean = false;
                                attribute mass : Real = 0.6414318931922317;
                                attribute 'σ_mass' : Real = 0.28909372274994966;
                                attribute Cx : Real = 81.41123573295772;
                                attribute 'σ_Cx' : Real = 28.721044428837228;
                                attribute Cy : Real = 44.24480153247714;
                                attribute 'σ_Cy' : Real = 28.23690002309109;
                                attribute Cz : Real = -27.285452745854855;
                                attribute 'σ_Cz' : Real = 29.057750463592832;
                                attribute Ixx : Real = 0.6513690223782906;
                                attribute 'σ_Ixx' : Real = 0.37074144170588635;
                                attribute Iyy : Real = 0.8085106982083033;
                                attribute 'σ_Iyy' : Real = 0.3723953238821935;
                                attribute Izz : Real = 0.8175795258224554;
                                attribute 'σ_Izz' : Real = 0.37017423652493897;
                                attribute Ixy : Real = 0.038210789931354565;
                                attribute 'σ_Ixy' : Real = 0.02351283871158888;
                                attribute Ixz : Real = 0.03261761625926242;
                                attribute 'σ_Ixz' : Real = 0.022566176940390956;
                                attribute Iyz : Real = 2.0372727072478797e-4;
                                attribute 'σ_Iyz' : Real = 0.02209918015384651;
                            }
                        }
                        part <'C.1.2.3.1.4.3'> 'Subassembly 297' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.4.3.1'> 'Part 1052' {
                                attribute POIconv : String = "+";
                                attribute Ipoint : Boolean = false;
                                attribute mass : Real = 0.16340611016773618;
                                attribute 'σ_mass' : Real = 0.28909372274994966;
                                attribute Cx : Real = -12.414421234279871;
                                attribute 'σ_Cx' : Real = 28.721044428837228;
                                attribute Cy : Real = 0.26108059100806713;
                                attribute 'σ_Cy' : Real = 28.23690002309109;
                                attribute Cz : Real = -35.56481748819351;
                                attribute 'σ_Cz' : Real = 29.057750463592832;
                                attribute Ixx : Real = 0.16654416391940294;
                                attribute 'σ_Ixx' : Real = 0.37074144170588635;
                                attribute Iyy : Real = 0.17144562127916171;
                                attribute 'σ_Iyy' : Real = 0.3723953238821935;
                                attribute Izz : Real = 0.1461097597527174;
                                attribute 'σ_Izz' : Real = 0.37017423652493897;
                                attribute Ixy : Real = -0.004029189984110122;
                                attribute 'σ_Ixy' : Real = 0.02351283871158888;
                                attribute Ixz : Real = 0.006847152148634688;
                                attribute 'σ_Ixz' : Real = 0.022566176940390956;
                                attribute Iyz : Real = -0.003419139572301038;
                                attribute 'σ_Iyz' : Real = 0.02209918015384651;
                            }
                            part <'C.1.2.3.1.4.3.2'> 'Part 1053' {
                                attribute POIconv : String = "-";
                                attribute Ipoint : Boolean = false;
                                attribute mass : Real = 0.3966979910978116;
                                attribute 'σ_mass' : Real = 0.28909372274994966;
                                attribute Cx : Real = -58.24294341728091;
                                attribute 'σ_Cx' : Real = 28.721044428837228;
                                attribute Cy : Real = -33.98464969359338;
                                attribute 'σ_Cy' : Real = 28.23690002309109;
                                attribute Cz : Real = -24.631404550746083;
                                attribute 'σ_Cz' : Real = 29.057750463592832;
                                attribute Ixx : Real = 0.37043131602739643;
                                attribute 'σ_Ixx' : Real = 0.37074144170588635;
                                attribute Iyy : Real = 0.37487626307375166;
                                attribute 'σ_Iyy' : Real = 0.3723953238821935;
                                attribute Izz : Real = 0.37484620368636934;
                                attribute 'σ_Izz' : Real = 0.37017423652493897;
                                attribute Ixy : Real = 0.011610541711058808;
                                attribute 'σ_Ixy' : Real = 0.02351283871158888;
                                attribute Ixz : Real = 0.01043426834880536;
                                attribute 'σ_Ixz' : Real = 0.022566176940390956;
                                attribute Iyz : Real = -0.007016248461573873;
                                attribute 'σ_Iyz' : Real = 0.02209918015384651;
                            }
                            part <'C.1.2.3.1.4.3.3'> 'Part 1054' {
                                attribute POIconv : String = "+";
                                attribute Ipoint : Boolean = false;
                                attribute mass : Real = 0.34402778986585325;
                                attribute 'σ_mass' : Real = 0.28909372274994966;
                                attribute Cx : Real = -40.55429487489164;
                                attribute 'σ_Cx' : Real = 28.721044428837228;
                                attribute Cy : Real = -88.74849979765713;
                                attribute 'σ_Cy' : Real = 28.23690002309109;
                                attribute Cz : Real = 86.19010825641453;
                                attribute 'σ_Cz' : Real = 29.057750463592832;
                                attribute Ixx : Real = 0.46355154857513636;
                                attribute 'σ_Ixx' : Real = 0.37074144170588635;
                                attribute Iyy : Real = 0.5196562143003289;
                                attribute 'σ_Iyy' : Real = 0.3723953238821935;
                                attribute Izz : Real = 0.4823439154859447;
                                attribute 'σ_Izz' : Real = 0.37017423652493897;
                                attribute Ixy : Real = -0.020006168681553842;
                                attribute 'σ_Ixy' : Real = 0.02351283871158888;
                                attribute Ixz : Real = -0.007743641368593271;
                                attribute 'σ_Ixz' : Real = 0.022566176940390956;
                                attribute Iyz : Real = 0.01510937372590955;
                                attribute 'σ_Iyz' : Real = 0.02209918015384651;
                            }
                            part <'C.1.2.3.1.4.3.4'> 'Part 1055' {
                                attribute POIconv : String = "+";
                                attribute Ipoint : Boolean = false;
                                attribute mass : Real = 0.36141186408232895;
                                attribute 'σ_mass' : Real = 0.28909372274994966;
                                attribute Cx : Real = 17.937244893983006;
                                attribute 'σ_Cx' : Real = 28.721044428837228;
                                attribute Cy : Real = 15.997829986736178;
                                attribute 'σ_Cy' : Real = 28.23690002309109;
                                attribute Cz : Real = 16.24582437798381;
                                attribute 'σ_Cz' : Real = 29.057750463592832;
                                attribute Ixx : Real = 0.3978110265653177;
                                attribute 'σ_Ixx' : Real = 0.37074144170588635;
                                attribute Iyy : Real = 0.3962637160353485;
                                attribute 'σ_Iyy' : Real = 0.3723953238821935;
                                attribute Izz : Real = 0.39378280426432843;
                                attribute 'σ_Izz' : Real = 0.37017423652493897;
                                attribute Ixy : Real = 0.010911645268354458;
                                attribute 'σ_Ixy' : Real = 0.02351283871158888;
                                attribute Ixz : Real = -0.0023715896487131703;
                                attribute 'σ_Ixz' : Real = 0.022566176940390956;
                                attribute Iyz : Real = 0.00512747725977481;
                                attribute 'σ_Iyz' : Real = 0.02209918015384651;
                            }
                        }
                        part <'C.1.2.3.1.4.4'> 'Subassembly 298' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.4.4.1'> 'Part 1056' {
                                attribute POIconv : String = "+";
                                attribute Ipoint : Boolean = false;
                                attribute mass : Real = 0.882149980786955;
                                attribute 'σ_mass' : Real = 0.28909372274994966;
                                attribute Cx : Real = 47.88799895904958;
                                attribute 'σ_Cx' : Real = 28.721044428837228;
                                attribute Cy : Real = -10.57063271291554;
                                attribute 'σ_Cy' : Real = 28.23690002309109;
                                attribute Cz : Real = 65.87203093804419;
                                attribute 'σ_Cz' : Real = 29.057750463592832;
                                attribute Ixx : Real = 1.1688060181363202;
                                attribute 'σ_Ixx' : Real = 0.37074144170588635;
                                attribute Iyy : Real = 1.1635226655013726;
                                attribute 'σ_Iyy' : Real = 0.3723953238821935;
                                attribute Izz : Real = 1.1479625672645903;
                                attribute 'σ_Izz' : Real = 0.37017423652493897;
                                attribute Ixy : Real = 0.01930441876696838;
                                attribute 'σ_Ixy' : Real = 0.02351283871158888;
                                attribute Ixz : Real = -0.011765484472756993;
                                attribute 'σ_Ixz' : Real = 0.022566176940390956;
                                attribute Iyz : Real = -0.015910416597707207;
                                attribute 'σ_Iyz' : Real = 0.02209918015384651;
                            }
                            part <'C.1.2.3.1.4.4.2'> 'Part 1057' {
                                attribute POIconv : String = "-";
                                attribute Ipoint : Boolean = false;
                                attribute mass : Real = 0.6235593824088573;
                                attribute 'σ_mass' : Real = 0.28909372274994966;
                                attribute Cx : Real = 7.771596126258373;
                                attribute 'σ_Cx' : Real = 28.721044428837228;
                                attribute Cy : Real = 2.2334241308271885;
                                attribute 'σ_Cy' : Real = 28.23690002309109;
                                attribute Cz : Real = 61.70614478178322;
                                attribute 'σ_Cz' : Real = 29.057750463592832;
                                attribute Ixx : Real = 0.8180365352892478;
                                attribute 'σ_Ixx' : Real = 0.37074144170588635;
                                attribute Iyy : Real = 0.7994194940059788;
                                attribute 'σ_Iyy' : Real = 0.3723953238821935;
                                attribute Izz : Real = 0.8366687939019364;
                                attribute 'σ_Izz' : Real = 0.37017423652493897;
                                attribute Ixy : Real = -0.02938419950643506;
                                attribute 'σ_Ixy' : Real = 0.02351283871158888;
                                attribute Ixz : Real = 0.01285629030817942;
                                attribute 'σ_Ixz' : Real = 0.022566176940390956;
                                attribute Iyz : Real = 0.007194026996384556;
                                attribute 'σ_Iyz' : Real = 0.02209918015384651;
                            }
                            part <'C.1.2.3.1.4.4.3'> 'Part 1058' {
                                attribute POIconv : String = "-";
                                attribute Ipoint : Boolean = false;
                                attribute mass : Real = 0.852130611640634;
                                attribute 'σ_mass' : Real = 0.28909372274994966;
                                attribute Cx : Real = -4.6923022251576185;
                                attribute 'σ_Cx' : Real = 28.721044428837228;
                                attribute Cy : Real = 42.065133107826114;
                                attribute 'σ_Cy' : Real = 28.23690002309109;
                                attribute Cz : Real = 30.690760351717472;
                                attribute 'σ_Cz' : Real = 29.057750463592832;
                                attribute Ixx : Real = 1.1105258109156457;
                                attribute 'σ_Ixx' : Real = 0.37074144170588635;
                                attribute Iyy : Real = 1.0355550546965706;
                                attribute 'σ_Iyy' : Real = 0.3723953238821935;
                                attribute Izz : Real = 1.0972395006960478;
                                attribute 'σ_Izz' : Real = 0.37017423652493897;
                                attribute Ixy : Real = -0.09355479906332526;
                                attribute 'σ_Ixy' : Real = 0.02351283871158888;
                                attribute Ixz : Real = -0.08673590560438557;
                                attribute 'σ_Ixz' : Real = 0.022566176940390956;
                                attribute Iyz : Real = -0.05994350970063276;
                                attribute 'σ_Iyz' : Real = 0.02209918015384651;
                            }
                        }
                        part <'C.1.2.3.1.4.5'> 'Subassembly 299' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.4.5.1'> 'Part 1059' {
                                attribute POIconv : String = "-";
                                attribute Ipoint : Boolean = false;
                                attribute mass : Real = 0.7318226899350994;
                                attribute 'σ_mass' : Real = 0.28909372274994966;
                                attribute Cx : Real = 97.58448014035821;
                                attribute 'σ_Cx' : Real = 28.721044428837228;
                                attribute Cy : Real = 39.462982304394245;
                                attribute 'σ_Cy' : Real = 28.23690002309109;
                                attribute Cz : Real = 87.18860587105155;
                                attribute 'σ_Cz' : Real = 29.057750463592832;
                                attribute Ixx : Real = 1.194259308780735;
                                attribute 'σ_Ixx' : Real = 0.37074144170588635;
                                attribute Iyy : Real = 1.164746794612592;
                                attribute 'σ_Iyy' : Real = 0.3723953238821935;
                                attribute Izz : Real = 1.1818874468366765;
                                attribute 'σ_Izz' : Real = 0.37017423652493897;
                                attribute Ixy : Real = 0.007191862197908598;
                                attribute 'σ_Ixy' : Real = 0.02351283871158888;
                                attribute Ixz : Real = 0.0042229771623906506;
                                attribute 'σ_Ixz' : Real = 0.022566176940390956;
                                attribute Iyz : Real = 0.004750707336135576;
                                attribute 'σ_Iyz' : Real = 0.02209918015384651;
                            }
                            part <'C.1.2.3.1.4.5.2'> 'Part 1060' {
                                attribute POIconv : String = "-";
                                attribute Ipoint : Boolean = false;
                                attribute mass : Real = 0.14777961387531832;
                                attribute 'σ_mass' : Real = 0.28909372274994966;
                                attribute Cx : Real = 11.671123607084155;
                                attribute 'σ_Cx' : Real = 28.721044428837228;
                                attribute Cy : Real = -61.40538356266916;
                                attribute 'σ_Cy' : Real = 28.23690002309109;
                                attribute Cz : Real = -93.36853586137295;
                                attribute 'σ_Cz' : Real = 29.057750463592832;
                                attribute Ixx : Real = 0.21730305139269704;
                                attribute 'σ_Ixx' : Real = 0.37074144170588635;
                                attribute Iyy : Real = 0.19940687540370183;
                                attribute 'σ_Iyy' : Real = 0.3723953238821935;
                                attribute Izz : Real = 0.19978219411696613;
                                attribute 'σ_Izz' : Real = 0.37017423652493897;
                                attribute Ixy : Real = 0.0016795468598082381;
                                attribute 'σ_Ixy' : Real = 0.02351283871158888;
                                attribute Ixz : Real = 0.004897994911134354;
                                attribute 'σ_Ixz' : Real = 0.022566176940390956;
                                attribute Iyz : Real = -3.125191342217973e-4;
                                attribute 'σ_Iyz' : Real = 0.02209918015384651;
                            }
                        }
                    }
                    part <'C.1.2.3.1.5'> 'Assembly 87' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.1.5.1'> 'Subassembly 300' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.5.1.1'> 'Part 1061' {
                                attribute POIconv : String = "-";
                                attribute Ipoint : Boolean = false;
                                attribute mass : Real = 0.13081390101742;
                                attribute 'σ_mass' : Real = 0.28909372274994966;
                                attribute Cx : Real = -19.102863036096096;
                                attribute 'σ_Cx' : Real = 28.721044428837228;
                                attribute Cy : Real = -94.51505299657583;
                                attribute 'σ_Cy' : Real = 28.23690002309109;
                                attribute Cz : Real = -30.995140364393592;
                                attribute 'σ_Cz' : Real = 29.057750463592832;
                                attribute Ixx : Real = 0.17326094199496697;
                                attribute 'σ_Ixx' : Real = 0.37074144170588635;
                                attribute Iyy : Real = 0.18656678027267268;
                                attribute 'σ_Iyy' : Real = 0.3723953238821935;
                                attribute Izz : Real = 0.18495806080878255;
                                attribute 'σ_Izz' : Real = 0.37017423652493897;
                                attribute Ixy : Real = -0.002505082775948407;
                                attribute 'σ_Ixy' : Real = 0.02351283871158888;
                                attribute Ixz : Real = -0.005244796713303929;
                                attribute 'σ_Ixz' : Real = 0.022566176940390956;
                                attribute Iyz : Real = -4.939127134549158e-4;
                                attribute 'σ_Iyz' : Real = 0.02209918015384651;
                            }
                            part <'C.1.2.3.1.5.1.2'> 'Part 1062' {
                                attribute POIconv : String = "-";
                                attribute Ipoint : Boolean = false;
                                attribute mass : Real = 0.5286573092150502;
                                attribute 'σ_mass' : Real = 0.28909372274994966;
                                attribute Cx : Real = 47.875435557216406;
                                attribute 'σ_Cx' : Real = 28.721044428837228;
                                attribute Cy : Real = -52.51263650134206;
                                attribute 'σ_Cy' : Real = 28.23690002309109;
                                attribute Cz : Real = -91.2951922044158;
                                attribute 'σ_Cz' : Real = 29.057750463592832;
                                attribute Ixx : Real = 0.6986659873372394;
                                attribute 'σ_Ixx' : Real = 0.37074144170588635;
                                attribute Iyy : Real = 0.7396714403046946;
                                attribute 'σ_Iyy' : Real = 0.3723953238821935;
                                attribute Izz : Real = 0.674014184708664;
                                attribute 'σ_Izz' : Real = 0.37017423652493897;
                                attribute Ixy : Real = -0.04783515283733443;
                                attribute 'σ_Ixy' : Real = 0.02351283871158888;
                                attribute Ixz : Real = 0.02057330101918691;
                                attribute 'σ_Ixz' : Real = 0.022566176940390956;
                                attribute Iyz : Real = -0.01870429998461142;
                                attribute 'σ_Iyz' : Real = 0.02209918015384651;
                            }
                            part <'C.1.2.3.1.5.1.3'> 'Part 1063' {
                                attribute POIconv : String = "+";
                                attribute Ipoint : Boolean = false;
                                attribute mass : Real = 0.85717995661241;
                                attribute 'σ_mass' : Real = 0.28909372274994966;
                                attribute Cx : Real = 57.68434344790876;
                                attribute 'σ_Cx' : Real = 28.721044428837228;
                                attribute Cy : Real = 99.41592700779438;
                                attribute 'σ_Cy' : Real = 28.23690002309109;
                                attribute Cz : Real = 81.6272471100092;
                                attribute 'σ_Cz' : Real = 29.057750463592832;
                                attribute Ixx : Real = 1.182030803572393;
                                attribute 'σ_Ixx' : Real = 0.37074144170588635;
                                attribute Iyy : Real = 1.1502833640526458;
                                attribute 'σ_Iyy' : Real = 0.3723953238821935;
                                attribute Izz : Real = 1.2221753209991009;
                                attribute 'σ_Izz' : Real = 0.37017423652493897;
                                attribute Ixy : Real = -0.10069200301187747;
                                attribute 'σ_Ixy' : Real = 0.02351283871158888;
                                attribute Ixz : Real = 0.12211406421555307;
                                attribute 'σ_Ixz' : Real = 0.022566176940390956;
                                attribute Iyz : Real = 0.10060626178265794;
                                attribute 'σ_Iyz' : Real = 0.02209918015384651;
                            }
                        }
                        part <'C.1.2.3.1.5.2'> 'Subassembly 301' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.5.2.1'> 'Part 1064' {
                                attribute POIconv : String = "+";
                                attribute Ipoint : Boolean = false;
                                attribute mass : Real = 0.08062984849116765;
                                attribute 'σ_mass' : Real = 0.28909372274994966;
                                attribute Cx : Real = 79.90733310580254;
                                attribute 'σ_Cx' : Real = 28.721044428837228;
                                attribute Cy : Real = -52.6643521618098;
                                attribute 'σ_Cy' : Real = 28.23690002309109;
                                attribute Cz : Real = 46.963507775217295;
                                attribute 'σ_Cz' : Real = 29.057750463592832;
                                attribute Ixx : Real = 0.10656009206662402;
                                attribute 'σ_Ixx' : Real = 0.37074144170588635;
                                attribute Iyy : Real = 0.10668314444170682;
                                attribute 'σ_Iyy' : Real = 0.3723953238821935;
                                attribute Izz : Real = 0.11445963451343098;
                                attribute 'σ_Izz' : Real = 0.37017423652493897;
                                attribute Ixy : Real = 5.375566486369059e-4;
                                attribute 'σ_Ixy' : Real = 0.02351283871158888;
                                attribute Ixz : Real = -3.5912182300382655e-4;
                                attribute 'σ_Ixz' : Real = 0.022566176940390956;
                                attribute Iyz : Real = 7.922446231387598e-5;
                                attribute 'σ_Iyz' : Real = 0.02209918015384651;
                            }
                            part <'C.1.2.3.1.5.2.2'> 'Part 1065' {
                                attribute POIconv : String = "-";
                                attribute Ipoint : Boolean = false;
                                attribute mass : Real = 0.8785589387393556;
                                attribute 'σ_mass' : Real = 0.28909372274994966;
                                attribute Cx : Real = -50.994906621053815;
                                attribute 'σ_Cx' : Real = 28.721044428837228;
                                attribute Cy : Real = 28.659749450162053;
                                attribute 'σ_Cy' : Real = 28.23690002309109;
                                attribute Cz : Real = 73.88611100614071;
                                attribute 'σ_Cz' : Real = 29.057750463592832;
                                attribute Ixx : Real = 1.0484490431043456;
                                attribute 'σ_Ixx' : Real = 0.37074144170588635;
                                attribute Iyy : Real = 0.9742583079671037;
                                attribute 'σ_Iyy' : Real = 0.3723953238821935;
                                attribute Izz : Real = 1.0068877350171561;
                                attribute 'σ_Izz' : Real = 0.37017423652493897;
                                attribute Ixy : Real = -0.024455286571313004;
                                attribute 'σ_Ixy' : Real = 0.02351283871158888;
                                attribute Ixz : Real = -0.06737624668913994;
                                attribute 'σ_Ixz' : Real = 0.022566176940390956;
                                attribute Iyz : Real = -0.0021416849567374055;
                                attribute 'σ_Iyz' : Real = 0.02209918015384651;
                            }
                            part <'C.1.2.3.1.5.2.3'> 'Part 1066' {
                                attribute POIconv : String = "+";
                                attribute Ipoint : Boolean = false;
                                attribute mass : Real = 0.7310225569473114;
                                attribute 'σ_mass' : Real = 0.28909372274994966;
                                attribute Cx : Real = 67.07863849587739;
                                attribute 'σ_Cx' : Real = 28.721044428837228;
                                attribute Cy : Real = -25.98369112238288;
                                attribute 'σ_Cy' : Real = 28.23690002309109;
                                attribute Cz : Real = -23.45006908290088;
                                attribute 'σ_Cz' : Real = 29.057750463592832;
                                attribute Ixx : Real = 1.109147505274529;
                                attribute 'σ_Ixx' : Real = 0.37074144170588635;
                                attribute Iyy : Real = 1.0759648119965606;
                                attribute 'σ_Iyy' : Real = 0.3723953238821935;
                                attribute Izz : Real = 1.103281754436055;
                                attribute 'σ_Izz' : Real = 0.37017423652493897;
                                attribute Ixy : Real = 0.01570963527677722;
                                attribute 'σ_Ixy' : Real = 0.02351283871158888;
                                attribute Ixz : Real = 0.0066060770728070504;
                                attribute 'σ_Ixz' : Real = 0.022566176940390956;
                                attribute Iyz : Real = 0.025445873328981;
                                attribute 'σ_Iyz' : Real = 0.02209918015384651;
                            }
                            part <'C.1.2.3.1.5.2.4'> 'Part 1067' {
                                attribute POIconv : String = "-";
                                attribute Ipoint : Boolean = false;
                                attribute mass : Real = 0.9189796810848638;
                                attribute 'σ_mass' : Real = 0.28909372274994966;
                                attribute Cx : Real = -88.89390137046576;
                                attribute 'σ_Cx' : Real = 28.721044428837228;
                                attribute Cy : Real = -59.95402755215764;
                                attribute 'σ_Cy' : Real = 28.23690002309109;
                                attribute Cz : Real = -16.915352595970035;
                                attribute 'σ_Cz' : Real = 29.057750463592832;
                                attribute Ixx : Real = 1.0891428888523997;
                                attribute 'σ_Ixx' : Real = 0.37074144170588635;
                                attribute Iyy : Real = 0.9480638612162594;
                                attribute 'σ_Iyy' : Real = 0.3723953238821935;
                                attribute Izz : Real = 1.0896619427952465;
                                attribute 'σ_Izz' : Real = 0.37017423652493897;
                                attribute Ixy : Real = -0.016774989020531705;
                                attribute 'σ_Ixy' : Real = 0.02351283871158888;
                                attribute Ixz : Real = -0.03668470294928386;
                                attribute 'σ_Ixz' : Real = 0.022566176940390956;
                                attribute Iyz : Real = -0.028651109157971887;
                                attribute 'σ_Iyz' : Real = 0.02209918015384651;
                            }
                            part <'C.1.2.3.1.5.2.5'> 'Part 1068' {
                                attribute POIconv : String = "+";
                                attribute Ipoint : Boolean = false;
                                attribute mass : Real = 0.7143612390323542;
                                attribute 'σ_mass' : Real = 0.28909372274994966;
                                attribute Cx : Real = -23.984279250726104;
                                attribute 'σ_Cx' : Real = 28.721044428837228;
                                attribute Cy : Real = -64.71602632664144;
                                attribute 'σ_Cy' : Real = 28.23690002309109;
                                attribute Cz : Real = -70.3919951338321;
                                attribute 'σ_Cz' : Real = 29.057750463592832;
                                attribute Ixx : Real = 0.8930441663136031;
                                attribute 'σ_Ixx' : Real = 0.37074144170588635;
                                attribute Iyy : Real = 0.8785900304424367;
                                attribute 'σ_Iyy' : Real = 0.3723953238821935;
                                attribute Izz : Real = 0.8533034238540819;
                                attribute 'σ_Izz' : Real = 0.37017423652493897;
                                attribute Ixy : Real = -2.4477902432202734e-4;
                                attribute 'σ_Ixy' : Real = 0.02351283871158888;
                                attribute Ixz : Real = -0.015456694583625643;
                                attribute 'σ_Ixz' : Real = 0.022566176940390956;
                                attribute Iyz : Real = -0.0012787325076341707;
                                attribute 'σ_Iyz' : Real = 0.02209918015384651;
                            }
                        }
                        part <'C.1.2.3.1.5.3'> 'Subassembly 302' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.5.3.1'> 'Part 1069' {
                                attribute POIconv : String = "-";
                                attribute Ipoint : Boolean = false;
                                attribute mass : Real = 0.8673915939605795;
                                attribute 'σ_mass' : Real = 0.28909372274994966;
                                attribute Cx : Real = -65.39055369794369;
                                attribute 'σ_Cx' : Real = 28.721044428837228;
                                attribute Cy : Real = 81.82338951155543;
                                attribute 'σ_Cy' : Real = 28.23690002309109;
                                attribute Cz : Real = 29.988151090219617;
                                attribute 'σ_Cz' : Real = 29.057750463592832;
                                attribute Ixx : Real = 1.034835911520058;
                                attribute 'σ_Ixx' : Real = 0.37074144170588635;
                                attribute Iyy : Real = 1.0146309044037214;
                                attribute 'σ_Iyy' : Real = 0.3723953238821935;
                                attribute Izz : Real = 1.0737685711147267;
                                attribute 'σ_Izz' : Real = 0.37017423652493897;
                                attribute Ixy : Real = 0.043130757775615654;
                                attribute 'σ_Ixy' : Real = 0.02351283871158888;
                                attribute Ixz : Real = 0.009992808796341953;
                                attribute 'σ_Ixz' : Real = 0.022566176940390956;
                                attribute Iyz : Real = -0.0029229533229066956;
                                attribute 'σ_Iyz' : Real = 0.02209918015384651;
                            }
                            part <'C.1.2.3.1.5.3.2'> 'Part 1070' {
                                attribute POIconv : String = "-";
                                attribute Ipoint : Boolean = false;
                                attribute mass : Real = 0.9694585117974784;
                                attribute 'σ_mass' : Real = 0.28909372274994966;
                                attribute Cx : Real = -24.787927605211735;
                                attribute 'σ_Cx' : Real = 28.721044428837228;
                                attribute Cy : Real = 70.91575739905238;
                                attribute 'σ_Cy' : Real = 28.23690002309109;
                                attribute Cz : Real = -76.74522497691214;
                                attribute 'σ_Cz' : Real = 29.057750463592832;
                                attribute Ixx : Real = 1.2813553158196134;
                                attribute 'σ_Ixx' : Real = 0.37074144170588635;
                                attribute Iyy : Real = 1.5410880811154988;
                                attribute 'σ_Iyy' : Real = 0.3723953238821935;
                                attribute Izz : Real = 1.334614558718345;
                                attribute 'σ_Izz' : Real = 0.37017423652493897;
                                attribute Ixy : Real = -0.0017469691574664215;
                                attribute 'σ_Ixy' : Real = 0.02351283871158888;
                                attribute Ixz : Real = -0.007961963272010188;
                                attribute 'σ_Ixz' : Real = 0.022566176940390956;
                                attribute Iyz : Real = 0.09502671921962388;
                                attribute 'σ_Iyz' : Real = 0.02209918015384651;
                            }
                            part <'C.1.2.3.1.5.3.3'> 'Part 1071' {
                                attribute POIconv : String = "+";
                                attribute Ipoint : Boolean = false;
                                attribute mass : Real = 0.6972554392570164;
                                attribute 'σ_mass' : Real = 0.28909372274994966;
                                attribute Cx : Real = 46.49368082173169;
                                attribute 'σ_Cx' : Real = 28.721044428837228;
                                attribute Cy : Real = -26.354542141780257;
                                attribute 'σ_Cy' : Real = 28.23690002309109;
                                attribute Cz : Real = -83.26301476918161;
                                attribute 'σ_Cz' : Real = 29.057750463592832;
                                attribute Ixx : Real = 0.8135661893211564;
                                attribute 'σ_Ixx' : Real = 0.37074144170588635;
                                attribute Iyy : Real = 0.9014552009155617;
                                attribute 'σ_Iyy' : Real = 0.3723953238821935;
                                attribute Izz : Real = 0.9240257779140032;
                                attribute 'σ_Izz' : Real = 0.37017423652493897;
                                attribute Ixy : Real = 0.05302263147365869;
                                attribute 'σ_Ixy' : Real = 0.02351283871158888;
                                attribute Ixz : Real = 0.03037337300464587;
                                attribute 'σ_Ixz' : Real = 0.022566176940390956;
                                attribute Iyz : Real = 0.0022654829686027055;
                                attribute 'σ_Iyz' : Real = 0.02209918015384651;
                            }
                            part <'C.1.2.3.1.5.3.4'> 'Part 1072' {
                                attribute POIconv : String = "-";
                                attribute Ipoint : Boolean = false;
                                attribute mass : Real = 0.41178440806129946;
                                attribute 'σ_mass' : Real = 0.28909372274994966;
                                attribute Cx : Real = -66.39845967292786;
                                attribute 'σ_Cx' : Real = 28.721044428837228;
                                attribute Cy : Real = -17.246408527716994;
                                attribute 'σ_Cy' : Real = 28.23690002309109;
                                attribute Cz : Real = 33.660761127248406;
                                attribute 'σ_Cz' : Real = 29.057750463592832;
                                attribute Ixx : Real = 0.41581779812420794;
                                attribute 'σ_Ixx' : Real = 0.37074144170588635;
                                attribute Iyy : Real = 0.41707775514054957;
                                attribute 'σ_Iyy' : Real = 0.3723953238821935;
                                attribute Izz : Real = 0.36798170276345094;
                                attribute 'σ_Izz' : Real = 0.37017423652493897;
                                attribute Ixy : Real = -0.008350212227890258;
                                attribute 'σ_Ixy' : Real = 0.02351283871158888;
                                attribute Ixz : Real = -0.004087352846995563;
                                attribute 'σ_Ixz' : Real = 0.022566176940390956;
                                attribute Iyz : Real = 0.007085325112769063;
                                attribute 'σ_Iyz' : Real = 0.02209918015384651;
                            }
                        }
                        part <'C.1.2.3.1.5.4'> 'Subassembly 303' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.1.5.4.1'> 'Part 1073' {
                                attribute POIconv : String = "+";
                                attribute Ipoint : Boolean = false;
                                attribute mass : Real = 0.2842550932301674;
                                attribute 'σ_mass' : Real = 0.28909372274994966;
                                attribute Cx : Real = 98.43460656702518;
                                attribute 'σ_Cx' : Real = 28.721044428837228;
                                attribute Cy : Real = -53.890949906781316;
                                attribute 'σ_Cy' : Real = 28.23690002309109;
                                attribute Cz : Real = 16.625373950228095;
                                attribute 'σ_Cz' : Real = 29.057750463592832;
                                attribute Ixx : Real = 0.36011565782792765;
                                attribute 'σ_Ixx' : Real = 0.37074144170588635;
                                attribute Iyy : Real = 0.3721605664139445;
                                attribute 'σ_Iyy' : Real = 0.3723953238821935;
                                attribute Izz : Real = 0.36010709330218926;
                                attribute 'σ_Izz' : Real = 0.37017423652493897;
                                attribute Ixy : Real = 0.010117331774858546;
                                attribute 'σ_Ixy' : Real = 0.02351283871158888;
                                attribute Ixz : Real = -0.004505712659662552;
                                attribute 'σ_Ixz' : Real = 0.022566176940390956;
                                attribute Iyz : Real = 0.014886826239469745;
                                attribute 'σ_Iyz' : Real = 0.02209918015384651;
                            }
                            part <'C.1.2.3.1.5.4.2'> 'Part 1074' {
                                attribute POIconv : String = "-";
                                attribute Ipoint : Boolean = false;
                                attribute mass : Real = 0.35028748105000707;
                                attribute 'σ_mass' : Real = 0.28909372274994966;
                                attribute Cx : Real = 17.263269098475575;
                                attribute 'σ_Cx' : Real = 28.721044428837228;
                                attribute Cy : Real = -30.141999665647745;
                                attribute 'σ_Cy' : Real = 28.23690002309109;
                                attribute Cz : Real = 79.03061797842383;
                                attribute 'σ_Cz' : Real = 29.057750463592832;
                                attribute Ixx : Real = 0.36139648477900693;
                                attribute 'σ_Ixx' : Real = 0.37074144170588635;
                                attribute Iyy : Real = 0.3669227309060699;
                                attribute 'σ_Iyy' : Real = 0.3723953238821935;
                                attribute Izz : Real = 0.3834589229076559;
                                attribute 'σ_Izz' : Real = 0.37017423652493897;
                                attribute Ixy : Real = -0.0035371725947279534;
                                attribute 'σ_Ixy' : Real = 0.02351283871158888;
                                attribute Ixz : Real = 0.016939714911895595;
                                attribute 'σ_Ixz' : Real = 0.022566176940390956;
                                attribute Iyz : Real = 0.0033033452734507317;
                                attribute 'σ_Iyz' : Real = 0.02209918015384651;
                            }
                        }
                    }
                }
                part <'C.1.2.3.2'> 'Subsystem 24' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.2.3.2.1'> 'Assembly 88' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.2.1.1'> 'Subassembly 304' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.1.1.1'> 'Part 1075' {
                                attribute POIconv : String = "-";
                                attribute Ipoint : Boolean = false;
                                attribute mass : Real = 0.09316603884263895;
                                attribute 'σ_mass' : Real = 0.28909372274994966;
                                attribute Cx : Real = 12.60268916375935;
                                attribute 'σ_Cx' : Real = 28.721044428837228;
                                attribute Cy : Real = 99.58324069157243;
                                attribute 'σ_Cy' : Real = 28.23690002309109;
                                attribute Cz : Real = 78.88803649693727;
                                attribute 'σ_Cz' : Real = 29.057750463592832;
                                attribute Ixx : Real = 0.09066852039309423;
                                attribute 'σ_Ixx' : Real = 0.37074144170588635;
                                attribute Iyy : Real = 0.08644172903608323;
                                attribute 'σ_Iyy' : Real = 0.3723953238821935;
                                attribute Izz : Real = 0.09541729913191384;
                                attribute 'σ_Izz' : Real = 0.37017423652493897;
                                attribute Ixy : Real = 0.007200924428477702;
                                attribute 'σ_Ixy' : Real = 0.02351283871158888;
                                attribute Ixz : Real = 0.0020119762557935204;
                                attribute 'σ_Ixz' : Real = 0.022566176940390956;
                                attribute Iyz : Real = -0.0038258231022511666;
                                attribute 'σ_Iyz' : Real = 0.02209918015384651;
                            }
                            part <'C.1.2.3.2.1.1.2'> 'Part 1076' {
                                attribute POIconv : String = "+";
                                attribute Ipoint : Boolean = false;
                                attribute mass : Real = 0.2929952875059098;
                                attribute 'σ_mass' : Real = 0.28909372274994966;
                                attribute Cx : Real = 35.99120490252972;
                                attribute 'σ_Cx' : Real = 28.721044428837228;
                                attribute Cy : Real = -17.41807605139911;
                                attribute 'σ_Cy' : Real = 28.23690002309109;
                                attribute Cz : Real = -47.60262714698911;
                                attribute 'σ_Cz' : Real = 29.057750463592832;
                                attribute Ixx : Real = 0.3111176327232721;
                                attribute 'σ_Ixx' : Real = 0.37074144170588635;
                                attribute Iyy : Real = 0.3095046432194984;
                                attribute 'σ_Iyy' : Real = 0.3723953238821935;
                                attribute Izz : Real = 0.31368155305549866;
                                attribute 'σ_Izz' : Real = 0.37017423652493897;
                                attribute Ixy : Real = 0.0012294486106757575;
                                attribute 'σ_Ixy' : Real = 0.02351283871158888;
                                attribute Ixz : Real = -3.635390425681407e-4;
                                attribute 'σ_Ixz' : Real = 0.022566176940390956;
                                attribute Iyz : Real = -0.00316724628804734;
                                attribute 'σ_Iyz' : Real = 0.02209918015384651;
                            }
                            part <'C.1.2.3.2.1.1.3'> 'Part 1077' {
                                attribute POIconv : String = "+";
                                attribute Ipoint : Boolean = false;
                                attribute mass : Real = 0.020711855444824324;
                                attribute 'σ_mass' : Real = 0.28909372274994966;
                                attribute Cx : Real = 7.059088023379445;
                                attribute 'σ_Cx' : Real = 28.721044428837228;
                                attribute Cy : Real = 36.22960192151368;
                                attribute 'σ_Cy' : Real = 28.23690002309109;
                                attribute Cz : Real = -0.7960488088428974;
                                attribute 'σ_Cz' : Real = 29.057750463592832;
                                attribute Ixx : Real = 0.03211247631308151;
                                attribute 'σ_Ixx' : Real = 0.37074144170588635;
                                attribute Iyy : Real = 0.03170252760446786;
                                attribute 'σ_Iyy' : Real = 0.3723953238821935;
                                attribute Izz : Real = 0.03201935618477567;
                                attribute 'σ_Izz' : Real = 0.37017423652493897;
                                attribute Ixy : Real = 6.483174484189957e-4;
                                attribute 'σ_Ixy' : Real = 0.02351283871158888;
                                attribute Ixz : Real = -3.1159791406084274e-4;
                                attribute 'σ_Ixz' : Real = 0.022566176940390956;
                                attribute Iyz : Real = -1.4705000092052589e-4;
                                attribute 'σ_Iyz' : Real = 0.02209918015384651;
                            }
                            part <'C.1.2.3.2.1.1.4'> 'Part 1078' {
                                attribute POIconv : String = "-";
                                attribute Ipoint : Boolean = false;
                                attribute mass : Real = 0.6407073800794315;
                                attribute 'σ_mass' : Real = 0.28909372274994966;
                                attribute Cx : Real = 89.19674125500023;
                                attribute 'σ_Cx' : Real = 28.721044428837228;
                                attribute Cy : Real = -11.363636190071702;
                                attribute 'σ_Cy' : Real = 28.23690002309109;
                                attribute Cz : Real = 10.201271995902061;
                                attribute 'σ_Cz' : Real = 29.057750463592832;
                                attribute Ixx : Real = 0.6378199053512029;
                                attribute 'σ_Ixx' : Real = 0.37074144170588635;
                                attribute Iyy : Real = 0.633743329509938;
                                attribute 'σ_Iyy' : Real = 0.3723953238821935;
                                attribute Izz : Real = 0.6317123394183661;
                                attribute 'σ_Izz' : Real = 0.37017423652493897;
                                attribute Ixy : Real = 0.001900299222432658;
                                attribute 'σ_Ixy' : Real = 0.02351283871158888;
                                attribute Ixz : Real = -0.0016071137086057386;
                                attribute 'σ_Ixz' : Real = 0.022566176940390956;
                                attribute Iyz : Real = 0.003453936252889564;
                                attribute 'σ_Iyz' : Real = 0.02209918015384651;
                            }
                        }
                        part <'C.1.2.3.2.1.2'> 'Subassembly 305' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.1.2.1'> 'Part 1079' {
                                attribute POIconv : String = "-";
                                attribute Ipoint : Boolean = false;
                                attribute mass : Real = 0.736369208443677;
                                attribute 'σ_mass' : Real = 0.28909372274994966;
                                attribute Cx : Real = 89.08713683485985;
                                attribute 'σ_Cx' : Real = 28.721044428837228;
                                attribute Cy : Real = -84.48967160657048;
                                attribute 'σ_Cy' : Real = 28.23690002309109;
                                attribute Cz : Real = 98.127674870193;
                                attribute 'σ_Cz' : Real = 29.057750463592832;
                                attribute Ixx : Real = 0.9074281887474119;
                                attribute 'σ_Ixx' : Real = 0.37074144170588635;
                                attribute Iyy : Real = 1.1312562714610315;
                                attribute 'σ_Iyy' : Real = 0.3723953238821935;
                                attribute Izz : Real = 0.8903214997645635;
                                attribute 'σ_Izz' : Real = 0.37017423652493897;
                                attribute Ixy : Real = -0.013089116061488274;
                                attribute 'σ_Ixy' : Real = 0.02351283871158888;
                                attribute Ixz : Real = -0.0454508459241012;
                                attribute 'σ_Ixz' : Real = 0.022566176940390956;
                                attribute Iyz : Real = -0.0175540541806187;
                                attribute 'σ_Iyz' : Real = 0.02209918015384651;
                            }
                            part <'C.1.2.3.2.1.2.2'> 'Part 1080' {
                                attribute POIconv : String = "-";
                                attribute Ipoint : Boolean = false;
                                attribute mass : Real = 0.136034482173156;
                                attribute 'σ_mass' : Real = 0.28909372274994966;
                                attribute Cx : Real = 33.401367627084255;
                                attribute 'σ_Cx' : Real = 28.721044428837228;
                                attribute Cy : Real = -35.36435957066715;
                                attribute 'σ_Cy' : Real = 28.23690002309109;
                                attribute Cz : Real = 23.781332932412624;
                                attribute 'σ_Cz' : Real = 29.057750463592832;
                                attribute Ixx : Real = 0.1898722227295391;
                                attribute 'σ_Ixx' : Real = 0.37074144170588635;
                                attribute Iyy : Real = 0.19031328235873918;
                                attribute 'σ_Iyy' : Real = 0.3723953238821935;
                                attribute Izz : Real = 0.1937970315547518;
                                attribute 'σ_Izz' : Real = 0.37017423652493897;
                                attribute Ixy : Real = 5.706782241701358e-5;
                                attribute 'σ_Ixy' : Real = 0.02351283871158888;
                                attribute Ixz : Real = -0.010390161027714846;
                                attribute 'σ_Ixz' : Real = 0.022566176940390956;
                                attribute Iyz : Real = 0.004074095579415841;
                                attribute 'σ_Iyz' : Real = 0.02209918015384651;
                            }
                            part <'C.1.2.3.2.1.2.3'> 'Part 1081' {
                                attribute POIconv : String = "-";
                                attribute Ipoint : Boolean = false;
                                attribute mass : Real = 0.5474059992129915;
                                attribute 'σ_mass' : Real = 0.28909372274994966;
                                attribute Cx : Real = -28.896778402850032;
                                attribute 'σ_Cx' : Real = 28.721044428837228;
                                attribute Cy : Real = 69.58198961801827;
                                attribute 'σ_Cy' : Real = 28.23690002309109;
                                attribute Cz : Real = 58.396795159205794;
                                attribute 'σ_Cz' : Real = 29.057750463592832;
                                attribute Ixx : Real = 0.7233941636655403;
                                attribute 'σ_Ixx' : Real = 0.37074144170588635;
                                attribute Iyy : Real = 0.8743873254364747;
                                attribute 'σ_Iyy' : Real = 0.3723953238821935;
                                attribute Izz : Real = 0.7255875116120409;
                                attribute 'σ_Izz' : Real = 0.37017423652493897;
                                attribute Ixy : Real = 0.018533668099388154;
                                attribute 'σ_Ixy' : Real = 0.02351283871158888;
                                attribute Ixz : Real = -0.003610646093416209;
                                attribute 'σ_Ixz' : Real = 0.022566176940390956;
                                attribute Iyz : Real = -0.028479450887521702;
                                attribute 'σ_Iyz' : Real = 0.02209918015384651;
                            }
                        }
                    }
                    part <'C.1.2.3.2.2'> 'Assembly 89' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.2.2.1'> 'Subassembly 306' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.2.1.1'> 'Part 1082' {
                                attribute POIconv : String = "+";
                                attribute Ipoint : Boolean = false;
                                attribute mass : Real = 0.2667583300252445;
                                attribute 'σ_mass' : Real = 0.28909372274994966;
                                attribute Cx : Real = 53.04571748711169;
                                attribute 'σ_Cx' : Real = 28.721044428837228;
                                attribute Cy : Real = 4.3095247354358435;
                                attribute 'σ_Cy' : Real = 28.23690002309109;
                                attribute Cz : Real = 10.195624688640237;
                                attribute 'σ_Cz' : Real = 29.057750463592832;
                                attribute Ixx : Real = 0.35496684195529155;
                                attribute 'σ_Ixx' : Real = 0.37074144170588635;
                                attribute Iyy : Real = 0.3423101052017469;
                                attribute 'σ_Iyy' : Real = 0.3723953238821935;
                                attribute Izz : Real = 0.32696397213086575;
                                attribute 'σ_Izz' : Real = 0.37017423652493897;
                                attribute Ixy : Real = 0.02616009064231773;
                                attribute 'σ_Ixy' : Real = 0.02351283871158888;
                                attribute Ixz : Real = -0.024513321047162917;
                                attribute 'σ_Ixz' : Real = 0.022566176940390956;
                                attribute Iyz : Real = 0.006453009990542897;
                                attribute 'σ_Iyz' : Real = 0.02209918015384651;
                            }
                            part <'C.1.2.3.2.2.1.2'> 'Part 1083' {
                                attribute POIconv : String = "-";
                                attribute Ipoint : Boolean = false;
                                attribute mass : Real = 0.7603096472376492;
                                attribute 'σ_mass' : Real = 0.28909372274994966;
                                attribute Cx : Real = 36.968472227454185;
                                attribute 'σ_Cx' : Real = 28.721044428837228;
                                attribute Cy : Real = 8.351876493543386;
                                attribute 'σ_Cy' : Real = 28.23690002309109;
                                attribute Cz : Real = -60.864388290792704;
                                attribute 'σ_Cz' : Real = 29.057750463592832;
                                attribute Ixx : Real = 0.9683795560205579;
                                attribute 'σ_Ixx' : Real = 0.37074144170588635;
                                attribute Iyy : Real = 0.683083289070925;
                                attribute 'σ_Iyy' : Real = 0.3723953238821935;
                                attribute Izz : Real = 0.9531789613066111;
                                attribute 'σ_Izz' : Real = 0.37017423652493897;
                                attribute Ixy : Real = 0.03052886075915511;
                                attribute 'σ_Ixy' : Real = 0.02351283871158888;
                                attribute Ixz : Real = -0.0027199163184193553;
                                attribute 'σ_Ixz' : Real = 0.022566176940390956;
                                attribute Iyz : Real = 0.0030415095379864097;
                                attribute 'σ_Iyz' : Real = 0.02209918015384651;
                            }
                            part <'C.1.2.3.2.2.1.3'> 'Part 1084' {
                                attribute POIconv : String = "+";
                                attribute Ipoint : Boolean = false;
                                attribute mass : Real = 0.5433033645558171;
                                attribute 'σ_mass' : Real = 0.28909372274994966;
                                attribute Cx : Real = 70.5368238966912;
                                attribute 'σ_Cx' : Real = 28.721044428837228;
                                attribute Cy : Real = -24.354524118825793;
                                attribute 'σ_Cy' : Real = 28.23690002309109;
                                attribute Cz : Real = -36.1916437279433;
                                attribute 'σ_Cz' : Real = 29.057750463592832;
                                attribute Ixx : Real = 0.7013746708070755;
                                attribute 'σ_Ixx' : Real = 0.37074144170588635;
                                attribute Iyy : Real = 0.6678097921525751;
                                attribute 'σ_Iyy' : Real = 0.3723953238821935;
                                attribute Izz : Real = 0.8236997681605733;
                                attribute 'σ_Izz' : Real = 0.37017423652493897;
                                attribute Ixy : Real = -0.008369130198001673;
                                attribute 'σ_Ixy' : Real = 0.02351283871158888;
                                attribute Ixz : Real = 0.008652304561179163;
                                attribute 'σ_Ixz' : Real = 0.022566176940390956;
                                attribute Iyz : Real = -0.0014998593408943365;
                                attribute 'σ_Iyz' : Real = 0.02209918015384651;
                            }
                            part <'C.1.2.3.2.2.1.4'> 'Part 1085' {
                                attribute POIconv : String = "-";
                                attribute Ipoint : Boolean = false;
                                attribute mass : Real = 0.8794356982854661;
                                attribute 'σ_mass' : Real = 0.28909372274994966;
                                attribute Cx : Real = -13.569234730675817;
                                attribute 'σ_Cx' : Real = 28.721044428837228;
                                attribute Cy : Real = 1.335459854453802;
                                attribute 'σ_Cy' : Real = 28.23690002309109;
                                attribute Cz : Real = 68.61111368052661;
                                attribute 'σ_Cz' : Real = 29.057750463592832;
                                attribute Ixx : Real = 1.1877927503193577;
                                attribute 'σ_Ixx' : Real = 0.37074144170588635;
                                attribute Iyy : Real = 1.2278454811245667;
                                attribute 'σ_Iyy' : Real = 0.3723953238821935;
                                attribute Izz : Real = 1.2778868521919615;
                                attribute 'σ_Izz' : Real = 0.37017423652493897;
                                attribute Ixy : Real = -0.0037696542450097363;
                                attribute 'σ_Ixy' : Real = 0.02351283871158888;
                                attribute Ixz : Real = 0.007588528370933295;
                                attribute 'σ_Ixz' : Real = 0.022566176940390956;
                                attribute Iyz : Real = -0.0035635831397830965;
                                attribute 'σ_Iyz' : Real = 0.02209918015384651;
                            }
                        }
                        part <'C.1.2.3.2.2.2'> 'Subassembly 307' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.2.2.1'> 'Part 1086' {
                                attribute POIconv : String = "+";
                                attribute Ipoint : Boolean = false;
                                attribute mass : Real = 0.5561327123520896;
                                attribute 'σ_mass' : Real = 0.28909372274994966;
                                attribute Cx : Real = -67.25634438917041;
                                attribute 'σ_Cx' : Real = 28.721044428837228;
                                attribute Cy : Real = 44.11402442492545;
                                attribute 'σ_Cy' : Real = 28.23690002309109;
                                attribute Cz : Real = -9.386031981557608;
                                attribute 'σ_Cz' : Real = 29.057750463592832;
                                attribute Ixx : Real = 0.6644465897368035;
                                attribute 'σ_Ixx' : Real = 0.37074144170588635;
                                attribute Iyy : Real = 0.6683513639241091;
                                attribute 'σ_Iyy' : Real = 0.3723953238821935;
                                attribute Izz : Real = 0.6803736349721548;
                                attribute 'σ_Izz' : Real = 0.37017423652493897;
                                attribute Ixy : Real = 0.015266620905208394;
                                attribute 'σ_Ixy' : Real = 0.02351283871158888;
                                attribute Ixz : Real = 0.057243504428252656;
                                attribute 'σ_Ixz' : Real = 0.022566176940390956;
                                attribute Iyz : Real = -0.0030015997111666392;
                                attribute 'σ_Iyz' : Real = 0.02209918015384651;
                            }
                            part <'C.1.2.3.2.2.2.2'> 'Part 1087' {
                                attribute POIconv : String = "+";
                                attribute Ipoint : Boolean = false;
                                attribute mass : Real = 0.8172284247637727;
                                attribute 'σ_mass' : Real = 0.28909372274994966;
                                attribute Cx : Real = 96.7974812258035;
                                attribute 'σ_Cx' : Real = 28.721044428837228;
                                attribute Cy : Real = -53.83351510390639;
                                attribute 'σ_Cy' : Real = 28.23690002309109;
                                attribute Cz : Real = 34.36636570841074;
                                attribute 'σ_Cz' : Real = 29.057750463592832;
                                attribute Ixx : Real = 1.0378063120688916;
                                attribute 'σ_Ixx' : Real = 0.37074144170588635;
                                attribute Iyy : Real = 0.8648887463909;
                                attribute 'σ_Iyy' : Real = 0.3723953238821935;
                                attribute Izz : Real = 0.9453361135450055;
                                attribute 'σ_Izz' : Real = 0.37017423652493897;
                                attribute Ixy : Real = -0.08299612091319185;
                                attribute 'σ_Ixy' : Real = 0.02351283871158888;
                                attribute Ixz : Real = -0.02758577712053387;
                                attribute 'σ_Ixz' : Real = 0.022566176940390956;
                                attribute Iyz : Real = 0.06066584038479146;
                                attribute 'σ_Iyz' : Real = 0.02209918015384651;
                            }
                            part <'C.1.2.3.2.2.2.3'> 'Part 1088' {
                                attribute POIconv : String = "+";
                                attribute Ipoint : Boolean = false;
                                attribute mass : Real = 0.5543945668123197;
                                attribute 'σ_mass' : Real = 0.28909372274994966;
                                attribute Cx : Real = 67.49224541708827;
                                attribute 'σ_Cx' : Real = 28.721044428837228;
                                attribute Cy : Real = -77.22733500413597;
                                attribute 'σ_Cy' : Real = 28.23690002309109;
                                attribute Cz : Real = -85.7072887942195;
                                attribute 'σ_Cz' : Real = 29.057750463592832;
                                attribute Ixx : Real = 0.6646762377603901;
                                attribute 'σ_Ixx' : Real = 0.37074144170588635;
                                attribute Iyy : Real = 0.7584581113637139;
                                attribute 'σ_Iyy' : Real = 0.3723953238821935;
                                attribute Izz : Real = 0.6745716401529638;
                                attribute 'σ_Izz' : Real = 0.37017423652493897;
                                attribute Ixy : Real = -0.0012254954982177484;
                                attribute 'σ_Ixy' : Real = 0.02351283871158888;
                                attribute Ixz : Real = -0.005532532777050148;
                                attribute 'σ_Ixz' : Real = 0.022566176940390956;
                                attribute Iyz : Real = -0.0446952174073174;
                                attribute 'σ_Iyz' : Real = 0.02209918015384651;
                            }
                            part <'C.1.2.3.2.2.2.4'> 'Part 1089' {
                                attribute POIconv : String = "+";
                                attribute Ipoint : Boolean = false;
                                attribute mass : Real = 0.1149001410761848;
                                attribute 'σ_mass' : Real = 0.28909372274994966;
                                attribute Cx : Real = -28.907833760604262;
                                attribute 'σ_Cx' : Real = 28.721044428837228;
                                attribute Cy : Real = 74.52406007796526;
                                attribute 'σ_Cy' : Real = 28.23690002309109;
                                attribute Cz : Real = 95.78590663149953;
                                attribute 'σ_Cz' : Real = 29.057750463592832;
                                attribute Ixx : Real = 0.1152588949388443;
                                attribute 'σ_Ixx' : Real = 0.37074144170588635;
                                attribute Iyy : Real = 0.13523930274537949;
                                attribute 'σ_Iyy' : Real = 0.3723953238821935;
                                attribute Izz : Real = 0.12827683824647135;
                                attribute 'σ_Izz' : Real = 0.37017423652493897;
                                attribute Ixy : Real = 0.005759024629091454;
                                attribute 'σ_Ixy' : Real = 0.02351283871158888;
                                attribute Ixz : Real = 5.342428656350633e-4;
                                attribute 'σ_Ixz' : Real = 0.022566176940390956;
                                attribute Iyz : Real = 0.008073754644159973;
                                attribute 'σ_Iyz' : Real = 0.02209918015384651;
                            }
                            part <'C.1.2.3.2.2.2.5'> 'Part 1090' {
                                attribute POIconv : String = "-";
                                attribute Ipoint : Boolean = false;
                                attribute mass : Real = 0.09878505051555111;
                                attribute 'σ_mass' : Real = 0.28909372274994966;
                                attribute Cx : Real = 72.98461738973856;
                                attribute 'σ_Cx' : Real = 28.721044428837228;
                                attribute Cy : Real = -56.09317580237985;
                                attribute 'σ_Cy' : Real = 28.23690002309109;
                                attribute Cz : Real = 43.05601269006729;
                                attribute 'σ_Cz' : Real = 29.057750463592832;
                                attribute Ixx : Real = 0.10518643948193843;
                                attribute 'σ_Ixx' : Real = 0.37074144170588635;
                                attribute Iyy : Real = 0.12900552991247027;
                                attribute 'σ_Iyy' : Real = 0.3723953238821935;
                                attribute Izz : Real = 0.12483903234966033;
                                attribute 'σ_Izz' : Real = 0.37017423652493897;
                                attribute Ixy : Real = 0.008310185808837344;
                                attribute 'σ_Ixy' : Real = 0.02351283871158888;
                                attribute Ixz : Real = 2.958743020453706e-5;
                                attribute 'σ_Ixz' : Real = 0.022566176940390956;
                                attribute Iyz : Real = 1.568144424204719e-5;
                                attribute 'σ_Iyz' : Real = 0.02209918015384651;
                            }
                        }
                    }
                    part <'C.1.2.3.2.3'> 'Assembly 90' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.2.3.1'> 'Subassembly 308' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.3.1.1'> 'Part 1091' {
                                attribute POIconv : String = "-";
                                attribute Ipoint : Boolean = false;
                                attribute mass : Real = 0.05497397221671418;
                                attribute 'σ_mass' : Real = 0.28909372274994966;
                                attribute Cx : Real = -37.98266397789121;
                                attribute 'σ_Cx' : Real = 28.721044428837228;
                                attribute Cy : Real = -92.95306913554668;
                                attribute 'σ_Cy' : Real = 28.23690002309109;
                                attribute Cz : Real = -94.83069661073387;
                                attribute 'σ_Cz' : Real = 29.057750463592832;
                                attribute Ixx : Real = 0.06966739586818131;
                                attribute 'σ_Ixx' : Real = 0.37074144170588635;
                                attribute Iyy : Real = 0.07700279554782437;
                                attribute 'σ_Iyy' : Real = 0.3723953238821935;
                                attribute Izz : Real = 0.08054261771822534;
                                attribute 'σ_Izz' : Real = 0.37017423652493897;
                                attribute Ixy : Real = -0.0014231119013099409;
                                attribute 'σ_Ixy' : Real = 0.02351283871158888;
                                attribute Ixz : Real = 6.900242581363717e-4;
                                attribute 'σ_Ixz' : Real = 0.022566176940390956;
                                attribute Iyz : Real = 0.0032138513078286053;
                                attribute 'σ_Iyz' : Real = 0.02209918015384651;
                            }
                            part <'C.1.2.3.2.3.1.2'> 'Part 1092' {
                                attribute POIconv : String = "+";
                                attribute Ipoint : Boolean = false;
                                attribute mass : Real = 0.34918252723268234;
                                attribute 'σ_mass' : Real = 0.28909372274994966;
                                attribute Cx : Real = -27.887688716873527;
                                attribute 'σ_Cx' : Real = 28.721044428837228;
                                attribute Cy : Real = -71.5850982349366;
                                attribute 'σ_Cy' : Real = 28.23690002309109;
                                attribute Cz : Real = 62.47166618704796;
                                attribute 'σ_Cz' : Real = 29.057750463592832;
                                attribute Ixx : Real = 0.372801418281261;
                                attribute 'σ_Ixx' : Real = 0.37074144170588635;
                                attribute Iyy : Real = 0.3798433680811546;
                                attribute 'σ_Iyy' : Real = 0.3723953238821935;
                                attribute Izz : Real = 0.36972095559979956;
                                attribute 'σ_Izz' : Real = 0.37017423652493897;
                                attribute Ixy : Real = 0.008647293681186243;
                                attribute 'σ_Ixy' : Real = 0.02351283871158888;
                                attribute Ixz : Real = -0.01976745999837262;
                                attribute 'σ_Ixz' : Real = 0.022566176940390956;
                                attribute Iyz : Real = -0.010441217251067579;
                                attribute 'σ_Iyz' : Real = 0.02209918015384651;
                            }
                            part <'C.1.2.3.2.3.1.3'> 'Part 1093' {
                                attribute POIconv : String = "+";
                                attribute Ipoint : Boolean = false;
                                attribute mass : Real = 0.15086264159809798;
                                attribute 'σ_mass' : Real = 0.28909372274994966;
                                attribute Cx : Real = 2.4376981891691685;
                                attribute 'σ_Cx' : Real = 28.721044428837228;
                                attribute Cy : Real = 49.69403180293739;
                                attribute 'σ_Cy' : Real = 28.23690002309109;
                                attribute Cz : Real = 46.903557144105434;
                                attribute 'σ_Cz' : Real = 29.057750463592832;
                                attribute Ixx : Real = 0.19931265931396447;
                                attribute 'σ_Ixx' : Real = 0.37074144170588635;
                                attribute Iyy : Real = 0.23335506539353873;
                                attribute 'σ_Iyy' : Real = 0.3723953238821935;
                                attribute Izz : Real = 0.20698063272790948;
                                attribute 'σ_Izz' : Real = 0.37017423652493897;
                                attribute Ixy : Real = 0.003925626952911989;
                                attribute 'σ_Ixy' : Real = 0.02351283871158888;
                                attribute Ixz : Real = 0.004855835772829;
                                attribute 'σ_Ixz' : Real = 0.022566176940390956;
                                attribute Iyz : Real = 3.237336856689135e-4;
                                attribute 'σ_Iyz' : Real = 0.02209918015384651;
                            }
                            part <'C.1.2.3.2.3.1.4'> 'Part 1094' {
                                attribute POIconv : String = "-";
                                attribute Ipoint : Boolean = false;
                                attribute mass : Real = 0.6912859861825127;
                                attribute 'σ_mass' : Real = 0.28909372274994966;
                                attribute Cx : Real = -83.1345091573894;
                                attribute 'σ_Cx' : Real = 28.721044428837228;
                                attribute Cy : Real = 66.90883254632354;
                                attribute 'σ_Cy' : Real = 28.23690002309109;
                                attribute Cz : Real = 63.120819022879004;
                                attribute 'σ_Cz' : Real = 29.057750463592832;
                                attribute Ixx : Real = 0.8003024047957623;
                                attribute 'σ_Ixx' : Real = 0.37074144170588635;
                                attribute Iyy : Real = 0.8259060592874118;
                                attribute 'σ_Iyy' : Real = 0.3723953238821935;
                                attribute Izz : Real = 1.025402684249924;
                                attribute 'σ_Izz' : Real = 0.37017423652493897;
                                attribute Ixy : Real = -0.02298066551182457;
                                attribute 'σ_Ixy' : Real = 0.02351283871158888;
                                attribute Ixz : Real = 2.835827405062617e-4;
                                attribute 'σ_Ixz' : Real = 0.022566176940390956;
                                attribute Iyz : Real = 0.02761624917420914;
                                attribute 'σ_Iyz' : Real = 0.02209918015384651;
                            }
                        }
                        part <'C.1.2.3.2.3.2'> 'Subassembly 309' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.3.2.1'> 'Part 1095' {
                                attribute POIconv : String = "+";
                                attribute Ipoint : Boolean = false;
                                attribute mass : Real = 0.5428474221359938;
                                attribute 'σ_mass' : Real = 0.28909372274994966;
                                attribute Cx : Real = 79.09870496951044;
                                attribute 'σ_Cx' : Real = 28.721044428837228;
                                attribute Cy : Real = 18.296489398926497;
                                attribute 'σ_Cy' : Real = 28.23690002309109;
                                attribute Cz : Real = 52.67065283842385;
                                attribute 'σ_Cz' : Real = 29.057750463592832;
                                attribute Ixx : Real = 0.6313717312322196;
                                attribute 'σ_Ixx' : Real = 0.37074144170588635;
                                attribute Iyy : Real = 0.6806577498054742;
                                attribute 'σ_Iyy' : Real = 0.3723953238821935;
                                attribute Izz : Real = 0.6605338827974486;
                                attribute 'σ_Izz' : Real = 0.37017423652493897;
                                attribute Ixy : Real = 0.038212751645309295;
                                attribute 'σ_Ixy' : Real = 0.02351283871158888;
                                attribute Ixz : Real = 0.010085192110511138;
                                attribute 'σ_Ixz' : Real = 0.022566176940390956;
                                attribute Iyz : Real = 0.05159292832745426;
                                attribute 'σ_Iyz' : Real = 0.02209918015384651;
                            }
                            part <'C.1.2.3.2.3.2.2'> 'Part 1096' {
                                attribute POIconv : String = "-";
                                attribute Ipoint : Boolean = false;
                                attribute mass : Real = 0.41461438029562125;
                                attribute 'σ_mass' : Real = 0.28909372274994966;
                                attribute Cx : Real = -37.03171834349632;
                                attribute 'σ_Cx' : Real = 28.721044428837228;
                                attribute Cy : Real = 93.54875925928354;
                                attribute 'σ_Cy' : Real = 28.23690002309109;
                                attribute Cz : Real = 41.99002832174301;
                                attribute 'σ_Cz' : Real = 29.057750463592832;
                                attribute Ixx : Real = 0.5766702800897564;
                                attribute 'σ_Ixx' : Real = 0.37074144170588635;
                                attribute Iyy : Real = 0.5602879990760286;
                                attribute 'σ_Iyy' : Real = 0.3723953238821935;
                                attribute Izz : Real = 0.54340643768561;
                                attribute 'σ_Izz' : Real = 0.37017423652493897;
                                attribute Ixy : Real = 0.0053229441757046405;
                                attribute 'σ_Ixy' : Real = 0.02351283871158888;
                                attribute Ixz : Real = -0.008756018723474852;
                                attribute 'σ_Ixz' : Real = 0.022566176940390956;
                                attribute Iyz : Real = 0.024595523787997054;
                                attribute 'σ_Iyz' : Real = 0.02209918015384651;
                            }
                            part <'C.1.2.3.2.3.2.3'> 'Part 1097' {
                                attribute POIconv : String = "+";
                                attribute Ipoint : Boolean = false;
                                attribute mass : Real = 0.4438376878462732;
                                attribute 'σ_mass' : Real = 0.28909372274994966;
                                attribute Cx : Real = -92.51174703240395;
                                attribute 'σ_Cx' : Real = 28.721044428837228;
                                attribute Cy : Real = 26.771060144528747;
                                attribute 'σ_Cy' : Real = 28.23690002309109;
                                attribute Cz : Real = -40.756921749562025;
                                attribute 'σ_Cz' : Real = 29.057750463592832;
                                attribute Ixx : Real = 0.6657342942508085;
                                attribute 'σ_Ixx' : Real = 0.37074144170588635;
                                attribute Iyy : Real = 0.5605041396293176;
                                attribute 'σ_Iyy' : Real = 0.3723953238821935;
                                attribute Izz : Real = 0.5571096079454422;
                                attribute 'σ_Izz' : Real = 0.37017423652493897;
                                attribute Ixy : Real = 0.033843872786422924;
                                attribute 'σ_Ixy' : Real = 0.02351283871158888;
                                attribute Ixz : Real = 7.748775845943994e-4;
                                attribute 'σ_Ixz' : Real = 0.022566176940390956;
                                attribute Iyz : Real = -0.011373311147057924;
                                attribute 'σ_Iyz' : Real = 0.02209918015384651;
                            }
                            part <'C.1.2.3.2.3.2.4'> 'Part 1098' {
                                attribute POIconv : String = "+";
                                attribute Ipoint : Boolean = false;
                                attribute mass : Real = 0.5225690558771603;
                                attribute 'σ_mass' : Real = 0.28909372274994966;
                                attribute Cx : Real = 66.79347674362361;
                                attribute 'σ_Cx' : Real = 28.721044428837228;
                                attribute Cy : Real = 24.51510149985552;
                                attribute 'σ_Cy' : Real = 28.23690002309109;
                                attribute Cz : Real = -54.75849821232259;
                                attribute 'σ_Cz' : Real = 29.057750463592832;
                                attribute Ixx : Real = 0.7172592588858192;
                                attribute 'σ_Ixx' : Real = 0.37074144170588635;
                                attribute Iyy : Real = 0.7693971489784205;
                                attribute 'σ_Iyy' : Real = 0.3723953238821935;
                                attribute Izz : Real = 0.6439328692741644;
                                attribute 'σ_Izz' : Real = 0.37017423652493897;
                                attribute Ixy : Real = -0.01948385557972983;
                                attribute 'σ_Ixy' : Real = 0.02351283871158888;
                                attribute Ixz : Real = -0.020205136169337494;
                                attribute 'σ_Ixz' : Real = 0.022566176940390956;
                                attribute Iyz : Real = -0.039895396171442526;
                                attribute 'σ_Iyz' : Real = 0.02209918015384651;
                            }
                        }
                    }
                    part <'C.1.2.3.2.4'> 'Assembly 91' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.2.4.1'> 'Subassembly 310' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.4.1.1'> 'Part 1099' {
                                attribute POIconv : String = "-";
                                attribute Ipoint : Boolean = false;
                                attribute mass : Real = 0.9355795071159955;
                                attribute 'σ_mass' : Real = 0.28909372274994966;
                                attribute Cx : Real = 5.548589210957289;
                                attribute 'σ_Cx' : Real = 28.721044428837228;
                                attribute Cy : Real = 56.769949151203036;
                                attribute 'σ_Cy' : Real = 28.23690002309109;
                                attribute Cz : Real = -86.13865557126701;
                                attribute 'σ_Cz' : Real = 29.057750463592832;
                                attribute Ixx : Real = 1.2637948732072388;
                                attribute 'σ_Ixx' : Real = 0.37074144170588635;
                                attribute Iyy : Real = 1.3494083538412773;
                                attribute 'σ_Iyy' : Real = 0.3723953238821935;
                                attribute Izz : Real = 1.3830498531416495;
                                attribute 'σ_Izz' : Real = 0.37017423652493897;
                                attribute Ixy : Real = 0.012519699709962303;
                                attribute 'σ_Ixy' : Real = 0.02351283871158888;
                                attribute Ixz : Real = -0.05939141884256449;
                                attribute 'σ_Ixz' : Real = 0.022566176940390956;
                                attribute Iyz : Real = -0.02278298144222341;
                                attribute 'σ_Iyz' : Real = 0.02209918015384651;
                            }
                            part <'C.1.2.3.2.4.1.2'> 'Part 1100' {
                                attribute POIconv : String = "-";
                                attribute Ipoint : Boolean = false;
                                attribute mass : Real = 0.15088262663478963;
                                attribute 'σ_mass' : Real = 0.28909372274994966;
                                attribute Cx : Real = -81.87416386790574;
                                attribute 'σ_Cx' : Real = 28.721044428837228;
                                attribute Cy : Real = -95.14246680773795;
                                attribute 'σ_Cy' : Real = 28.23690002309109;
                                attribute Cz : Real = -29.56867925822735;
                                attribute 'σ_Cz' : Real = 29.057750463592832;
                                attribute Ixx : Real = 0.1585559014803746;
                                attribute 'σ_Ixx' : Real = 0.37074144170588635;
                                attribute Iyy : Real = 0.14138737886412606;
                                attribute 'σ_Iyy' : Real = 0.3723953238821935;
                                attribute Izz : Real = 0.1652953054496566;
                                attribute 'σ_Izz' : Real = 0.37017423652493897;
                                attribute Ixy : Real = -1.4282638455323797e-4;
                                attribute 'σ_Ixy' : Real = 0.02351283871158888;
                                attribute Ixz : Real = -5.806910750280517e-6;
                                attribute 'σ_Ixz' : Real = 0.022566176940390956;
                                attribute Iyz : Real = 0.0034817968054934446;
                                attribute 'σ_Iyz' : Real = 0.02209918015384651;
                            }
                            part <'C.1.2.3.2.4.1.3'> 'Part 1101' {
                                attribute POIconv : String = "-";
                                attribute Ipoint : Boolean = false;
                                attribute mass : Real = 0.4954275927224662;
                                attribute 'σ_mass' : Real = 0.28909372274994966;
                                attribute Cx : Real = -26.655212603509426;
                                attribute 'σ_Cx' : Real = 28.721044428837228;
                                attribute Cy : Real = 1.1172140017151833;
                                attribute 'σ_Cy' : Real = 28.23690002309109;
                                attribute Cz : Real = 94.6926117874682;
                                attribute 'σ_Cz' : Real = 29.057750463592832;
                                attribute Ixx : Real = 0.6604474722485992;
                                attribute 'σ_Ixx' : Real = 0.37074144170588635;
                                attribute Iyy : Real = 0.6350152847021314;
                                attribute 'σ_Iyy' : Real = 0.3723953238821935;
                                attribute Izz : Real = 0.6833549157572724;
                                attribute 'σ_Izz' : Real = 0.37017423652493897;
                                attribute Ixy : Real = -0.005172712107083852;
                                attribute 'σ_Ixy' : Real = 0.02351283871158888;
                                attribute Ixz : Real = 0.006025208356714807;
                                attribute 'σ_Ixz' : Real = 0.022566176940390956;
                                attribute Iyz : Real = 0.011726085303259687;
                                attribute 'σ_Iyz' : Real = 0.02209918015384651;
                            }
                            part <'C.1.2.3.2.4.1.4'> 'Part 1102' {
                                attribute POIconv : String = "-";
                                attribute Ipoint : Boolean = false;
                                attribute mass : Real = 0.6521077641418669;
                                attribute 'σ_mass' : Real = 0.28909372274994966;
                                attribute Cx : Real = 17.113251471892;
                                attribute 'σ_Cx' : Real = 28.721044428837228;
                                attribute Cy : Real = 87.86846911534667;
                                attribute 'σ_Cy' : Real = 28.23690002309109;
                                attribute Cz : Real = -48.58629060909152;
                                attribute 'σ_Cz' : Real = 29.057750463592832;
                                attribute Ixx : Real = 0.9054042630024207;
                                attribute 'σ_Ixx' : Real = 0.37074144170588635;
                                attribute Iyy : Real = 0.9241841079190529;
                                attribute 'σ_Iyy' : Real = 0.3723953238821935;
                                attribute Izz : Real = 0.9496548367234031;
                                attribute 'σ_Izz' : Real = 0.37017423652493897;
                                attribute Ixy : Real = -0.0362169035073473;
                                attribute 'σ_Ixy' : Real = 0.02351283871158888;
                                attribute Ixz : Real = -0.03909162655610002;
                                attribute 'σ_Ixz' : Real = 0.022566176940390956;
                                attribute Iyz : Real = 0.034281708841578246;
                                attribute 'σ_Iyz' : Real = 0.02209918015384651;
                            }
                            part <'C.1.2.3.2.4.1.5'> 'Part 1103' {
                                attribute POIconv : String = "-";
                                attribute Ipoint : Boolean = false;
                                attribute mass : Real = 0.4436012440284248;
                                attribute 'σ_mass' : Real = 0.28909372274994966;
                                attribute Cx : Real = 97.9324808344245;
                                attribute 'σ_Cx' : Real = 28.721044428837228;
                                attribute Cy : Real = 1.7941991332918406;
                                attribute 'σ_Cy' : Real = 28.23690002309109;
                                attribute Cz : Real = 89.59850408136845;
                                attribute 'σ_Cz' : Real = 29.057750463592832;
                                attribute Ixx : Real = 0.5958068911074978;
                                attribute 'σ_Ixx' : Real = 0.37074144170588635;
                                attribute Iyy : Real = 0.4943680226960312;
                                attribute 'σ_Iyy' : Real = 0.3723953238821935;
                                attribute Izz : Real = 0.575398086083283;
                                attribute 'σ_Izz' : Real = 0.37017423652493897;
                                attribute Ixy : Real = 0.015589705510161738;
                                attribute 'σ_Ixy' : Real = 0.02351283871158888;
                                attribute Ixz : Real = -0.008923778699198723;
                                attribute 'σ_Ixz' : Real = 0.022566176940390956;
                                attribute Iyz : Real = 0.03533123349596242;
                                attribute 'σ_Iyz' : Real = 0.02209918015384651;
                            }
                        }
                        part <'C.1.2.3.2.4.2'> 'Subassembly 311' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.4.2.1'> 'Part 1104' {
                                attribute POIconv : String = "-";
                                attribute Ipoint : Boolean = false;
                                attribute mass : Real = 0.7227953992483672;
                                attribute 'σ_mass' : Real = 0.28909372274994966;
                                attribute Cx : Real = -13.830693904310465;
                                attribute 'σ_Cx' : Real = 28.721044428837228;
                                attribute Cy : Real = 77.28517251089215;
                                attribute 'σ_Cy' : Real = 28.23690002309109;
                                attribute Cz : Real = 21.19648582302034;
                                attribute 'σ_Cz' : Real = 29.057750463592832;
                                attribute Ixx : Real = 0.74744148432908;
                                attribute 'σ_Ixx' : Real = 0.37074144170588635;
                                attribute Iyy : Real = 0.7233700979355331;
                                attribute 'σ_Iyy' : Real = 0.3723953238821935;
                                attribute Izz : Real = 0.6408198576755768;
                                attribute 'σ_Izz' : Real = 0.37017423652493897;
                                attribute Ixy : Real = 0.0023911687933561966;
                                attribute 'σ_Ixy' : Real = 0.02351283871158888;
                                attribute Ixz : Real = -0.005298585512449525;
                                attribute 'σ_Ixz' : Real = 0.022566176940390956;
                                attribute Iyz : Real = 0.05094650401846454;
                                attribute 'σ_Iyz' : Real = 0.02209918015384651;
                            }
                            part <'C.1.2.3.2.4.2.2'> 'Part 1105' {
                                attribute POIconv : String = "+";
                                attribute Ipoint : Boolean = false;
                                attribute mass : Real = 0.9516128267524764;
                                attribute 'σ_mass' : Real = 0.28909372274994966;
                                attribute Cx : Real = 7.7100086491554976;
                                attribute 'σ_Cx' : Real = 28.721044428837228;
                                attribute Cy : Real = -88.23011899366975;
                                attribute 'σ_Cy' : Real = 28.23690002309109;
                                attribute Cz : Real = 15.422165859490633;
                                attribute 'σ_Cz' : Real = 29.057750463592832;
                                attribute Ixx : Real = 1.262666097491278;
                                attribute 'σ_Ixx' : Real = 0.37074144170588635;
                                attribute Iyy : Real = 1.2518975744882963;
                                attribute 'σ_Iyy' : Real = 0.3723953238821935;
                                attribute Izz : Real = 1.222591874616785;
                                attribute 'σ_Izz' : Real = 0.37017423652493897;
                                attribute Ixy : Real = -0.11010656102204461;
                                attribute 'σ_Ixy' : Real = 0.02351283871158888;
                                attribute Ixz : Real = -0.08322898012810283;
                                attribute 'σ_Ixz' : Real = 0.022566176940390956;
                                attribute Iyz : Real = -0.10003250362266354;
                                attribute 'σ_Iyz' : Real = 0.02209918015384651;
                            }
                        }
                        part <'C.1.2.3.2.4.3'> 'Subassembly 312' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.4.3.1'> 'Part 1106' {
                                attribute POIconv : String = "-";
                                attribute Ipoint : Boolean = false;
                                attribute mass : Real = 0.15245172869018278;
                                attribute 'σ_mass' : Real = 0.28909372274994966;
                                attribute Cx : Real = 82.1294114459306;
                                attribute 'σ_Cx' : Real = 28.721044428837228;
                                attribute Cy : Real = -78.09897377155721;
                                attribute 'σ_Cy' : Real = 28.23690002309109;
                                attribute Cz : Real = 17.741036973893642;
                                attribute 'σ_Cz' : Real = 29.057750463592832;
                                attribute Ixx : Real = 0.21717095508092787;
                                attribute 'σ_Ixx' : Real = 0.37074144170588635;
                                attribute Iyy : Real = 0.1971670500317219;
                                attribute 'σ_Iyy' : Real = 0.3723953238821935;
                                attribute Izz : Real = 0.1836865595422051;
                                attribute 'σ_Izz' : Real = 0.37017423652493897;
                                attribute Ixy : Real = 0.004674645632627362;
                                attribute 'σ_Ixy' : Real = 0.02351283871158888;
                                attribute Ixz : Real = 0.006608017622239318;
                                attribute 'σ_Ixz' : Real = 0.022566176940390956;
                                attribute Iyz : Real = -0.013550468386228223;
                                attribute 'σ_Iyz' : Real = 0.02209918015384651;
                            }
                            part <'C.1.2.3.2.4.3.2'> 'Part 1107' {
                                attribute POIconv : String = "+";
                                attribute Ipoint : Boolean = false;
                                attribute mass : Real = 0.330234752579825;
                                attribute 'σ_mass' : Real = 0.28909372274994966;
                                attribute Cx : Real = 81.547816330567;
                                attribute 'σ_Cx' : Real = 28.721044428837228;
                                attribute Cy : Real = 52.62661101296544;
                                attribute 'σ_Cy' : Real = 28.23690002309109;
                                attribute Cz : Real = 40.2078771032393;
                                attribute 'σ_Cz' : Real = 29.057750463592832;
                                attribute Ixx : Real = 0.5183635413897415;
                                attribute 'σ_Ixx' : Real = 0.37074144170588635;
                                attribute Iyy : Real = 0.5115284083294579;
                                attribute 'σ_Iyy' : Real = 0.3723953238821935;
                                attribute Izz : Real = 0.5123840850324586;
                                attribute 'σ_Izz' : Real = 0.37017423652493897;
                                attribute Ixy : Real = -0.011018954783511593;
                                attribute 'σ_Ixy' : Real = 0.02351283871158888;
                                attribute Ixz : Real = 0.012584871386786916;
                                attribute 'σ_Ixz' : Real = 0.022566176940390956;
                                attribute Iyz : Real = 2.449865937105925e-4;
                                attribute 'σ_Iyz' : Real = 0.02209918015384651;
                            }
                        }
                        part <'C.1.2.3.2.4.4'> 'Subassembly 313' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.4.4.1'> 'Part 1108' {
                                attribute POIconv : String = "+";
                                attribute Ipoint : Boolean = false;
                                attribute mass : Real = 0.016121685769874602;
                                attribute 'σ_mass' : Real = 0.28909372274994966;
                                attribute Cx : Real = 90.47938068397343;
                                attribute 'σ_Cx' : Real = 28.721044428837228;
                                attribute Cy : Real = -27.619647048413754;
                                attribute 'σ_Cy' : Real = 28.23690002309109;
                                attribute Cz : Real = -1.5015270560979843;
                                attribute 'σ_Cz' : Real = 29.057750463592832;
                                attribute Ixx : Real = 0.01946039445245955;
                                attribute 'σ_Ixx' : Real = 0.37074144170588635;
                                attribute Iyy : Real = 0.018841092155858132;
                                attribute 'σ_Iyy' : Real = 0.3723953238821935;
                                attribute Izz : Real = 0.020817150149981548;
                                attribute 'σ_Izz' : Real = 0.37017423652493897;
                                attribute Ixy : Real = 2.673951490214987e-4;
                                attribute 'σ_Ixy' : Real = 0.02351283871158888;
                                attribute Ixz : Real = -0.0012171115318801724;
                                attribute 'σ_Ixz' : Real = 0.022566176940390956;
                                attribute Iyz : Real = 0.0012571686809779033;
                                attribute 'σ_Iyz' : Real = 0.02209918015384651;
                            }
                            part <'C.1.2.3.2.4.4.2'> 'Part 1109' {
                                attribute POIconv : String = "-";
                                attribute Ipoint : Boolean = false;
                                attribute mass : Real = 0.6192007512964774;
                                attribute 'σ_mass' : Real = 0.28909372274994966;
                                attribute Cx : Real = -50.13936059549451;
                                attribute 'σ_Cx' : Real = 28.721044428837228;
                                attribute Cy : Real = 90.9339573699981;
                                attribute 'σ_Cy' : Real = 28.23690002309109;
                                attribute Cz : Real = -5.758166639134288;
                                attribute 'σ_Cz' : Real = 29.057750463592832;
                                attribute Ixx : Real = 0.7544162856581335;
                                attribute 'σ_Ixx' : Real = 0.37074144170588635;
                                attribute Iyy : Real = 0.7844172004587067;
                                attribute 'σ_Iyy' : Real = 0.3723953238821935;
                                attribute Izz : Real = 0.8893412959485172;
                                attribute 'σ_Izz' : Real = 0.37017423652493897;
                                attribute Ixy : Real = -0.001520068948336354;
                                attribute 'σ_Ixy' : Real = 0.02351283871158888;
                                attribute Ixz : Real = -0.013119333252952375;
                                attribute 'σ_Ixz' : Real = 0.022566176940390956;
                                attribute Iyz : Real = 0.00919834567052532;
                                attribute 'σ_Iyz' : Real = 0.02209918015384651;
                            }
                            part <'C.1.2.3.2.4.4.3'> 'Part 1110' {
                                attribute POIconv : String = "-";
                                attribute Ipoint : Boolean = false;
                                attribute mass : Real = 0.8519235519045033;
                                attribute 'σ_mass' : Real = 0.28909372274994966;
                                attribute Cx : Real = 10.888919606804848;
                                attribute 'σ_Cx' : Real = 28.721044428837228;
                                attribute Cy : Real = 29.18862784281373;
                                attribute 'σ_Cy' : Real = 28.23690002309109;
                                attribute Cz : Real = 75.17644455656409;
                                attribute 'σ_Cz' : Real = 29.057750463592832;
                                attribute Ixx : Real = 1.1747274995723958;
                                attribute 'σ_Ixx' : Real = 0.37074144170588635;
                                attribute Iyy : Real = 1.177720886597631;
                                attribute 'σ_Iyy' : Real = 0.3723953238821935;
                                attribute Izz : Real = 1.193344147244268;
                                attribute 'σ_Izz' : Real = 0.37017423652493897;
                                attribute Ixy : Real = -0.012833828777611748;
                                attribute 'σ_Ixy' : Real = 0.02351283871158888;
                                attribute Ixz : Real = -0.013564274028886339;
                                attribute 'σ_Ixz' : Real = 0.022566176940390956;
                                attribute Iyz : Real = -7.884820807096713e-4;
                                attribute 'σ_Iyz' : Real = 0.02209918015384651;
                            }
                            part <'C.1.2.3.2.4.4.4'> 'Part 1111' {
                                attribute POIconv : String = "-";
                                attribute Ipoint : Boolean = false;
                                attribute mass : Real = 0.6062849436367397;
                                attribute 'σ_mass' : Real = 0.28909372274994966;
                                attribute Cx : Real = -5.354289570823312;
                                attribute 'σ_Cx' : Real = 28.721044428837228;
                                attribute Cy : Real = -54.34263232164085;
                                attribute 'σ_Cy' : Real = 28.23690002309109;
                                attribute Cz : Real = 26.216398319229484;
                                attribute 'σ_Cz' : Real = 29.057750463592832;
                                attribute Ixx : Real = 0.8110678129408333;
                                attribute 'σ_Ixx' : Real = 0.37074144170588635;
                                attribute Iyy : Real = 0.8159399987915779;
                                attribute 'σ_Iyy' : Real = 0.3723953238821935;
                                attribute Izz : Real = 0.658226395386454;
                                attribute 'σ_Izz' : Real = 0.37017423652493897;
                                attribute Ixy : Real = 0.005608632892637671;
                                attribute 'σ_Ixy' : Real = 0.02351283871158888;
                                attribute Ixz : Real = -0.0013624788414457003;
                                attribute 'σ_Ixz' : Real = 0.022566176940390956;
                                attribute Iyz : Real = -0.027304984492302252;
                                attribute 'σ_Iyz' : Real = 0.02209918015384651;
                            }
                            part <'C.1.2.3.2.4.4.5'> 'Part 1112' {
                                attribute POIconv : String = "+";
                                attribute Ipoint : Boolean = false;
                                attribute mass : Real = 0.39371819819277154;
                                attribute 'σ_mass' : Real = 0.28909372274994966;
                                attribute Cx : Real = -22.040423471480608;
                                attribute 'σ_Cx' : Real = 28.721044428837228;
                                attribute Cy : Real = 19.392980774864554;
                                attribute 'σ_Cy' : Real = 28.23690002309109;
                                attribute Cz : Real = 64.12140158936381;
                                attribute 'σ_Cz' : Real = 29.057750463592832;
                                attribute Ixx : Real = 0.4509935414856381;
                                attribute 'σ_Ixx' : Real = 0.37074144170588635;
                                attribute Iyy : Real = 0.49325683095698586;
                                attribute 'σ_Iyy' : Real = 0.3723953238821935;
                                attribute Izz : Real = 0.4317900286245668;
                                attribute 'σ_Izz' : Real = 0.37017423652493897;
                                attribute Ixy : Real = -0.027477813882965565;
                                attribute 'σ_Ixy' : Real = 0.02351283871158888;
                                attribute Ixz : Real = -0.013513574981236835;
                                attribute 'σ_Ixz' : Real = 0.022566176940390956;
                                attribute Iyz : Real = 0.012169320648142341;
                                attribute 'σ_Iyz' : Real = 0.02209918015384651;
                            }
                        }
                        part <'C.1.2.3.2.4.5'> 'Subassembly 314' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.4.5.1'> 'Part 1113' {
                                attribute POIconv : String = "+";
                                attribute Ipoint : Boolean = false;
                                attribute mass : Real = 0.7066141671736259;
                                attribute 'σ_mass' : Real = 0.28909372274994966;
                                attribute Cx : Real = 89.06655050814152;
                                attribute 'σ_Cx' : Real = 28.721044428837228;
                                attribute Cy : Real = -31.84382147155702;
                                attribute 'σ_Cy' : Real = 28.23690002309109;
                                attribute Cz : Real = -96.88437008298934;
                                attribute 'σ_Cz' : Real = 29.057750463592832;
                                attribute Ixx : Real = 0.74219272866924;
                                attribute 'σ_Ixx' : Real = 0.37074144170588635;
                                attribute Iyy : Real = 0.7310644097280373;
                                attribute 'σ_Iyy' : Real = 0.3723953238821935;
                                attribute Izz : Real = 0.7316206503994653;
                                attribute 'σ_Izz' : Real = 0.37017423652493897;
                                attribute Ixy : Real = 0.0025341132894404006;
                                attribute 'σ_Ixy' : Real = 0.02351283871158888;
                                attribute Ixz : Real = 0.001922566306612992;
                                attribute 'σ_Ixz' : Real = 0.022566176940390956;
                                attribute Iyz : Real = 2.4552321915932155e-5;
                                attribute 'σ_Iyz' : Real = 0.02209918015384651;
                            }
                            part <'C.1.2.3.2.4.5.2'> 'Part 1114' {
                                attribute POIconv : String = "+";
                                attribute Ipoint : Boolean = false;
                                attribute mass : Real = 0.41636258010845634;
                                attribute 'σ_mass' : Real = 0.28909372274994966;
                                attribute Cx : Real = -11.276261461898685;
                                attribute 'σ_Cx' : Real = 28.721044428837228;
                                attribute Cy : Real = 29.970974940806627;
                                attribute 'σ_Cy' : Real = 28.23690002309109;
                                attribute Cz : Real = 87.68960488960147;
                                attribute 'σ_Cz' : Real = 29.057750463592832;
                                attribute Ixx : Real = 0.5636588883307363;
                                attribute 'σ_Ixx' : Real = 0.37074144170588635;
                                attribute Iyy : Real = 0.5590741487674599;
                                attribute 'σ_Iyy' : Real = 0.3723953238821935;
                                attribute Izz : Real = 0.6030087155458527;
                                attribute 'σ_Izz' : Real = 0.37017423652493897;
                                attribute Ixy : Real = 0.010506020988205859;
                                attribute 'σ_Ixy' : Real = 0.02351283871158888;
                                attribute Ixz : Real = -0.038231433474013754;
                                attribute 'σ_Ixz' : Real = 0.022566176940390956;
                                attribute Iyz : Real = -0.029167939537512066;
                                attribute 'σ_Iyz' : Real = 0.02209918015384651;
                            }
                            part <'C.1.2.3.2.4.5.3'> 'Part 1115' {
                                attribute POIconv : String = "+";
                                attribute Ipoint : Boolean = false;
                                attribute mass : Real = 0.5816145352178719;
                                attribute 'σ_mass' : Real = 0.28909372274994966;
                                attribute Cx : Real = 83.29264703206718;
                                attribute 'σ_Cx' : Real = 28.721044428837228;
                                attribute Cy : Real = 50.73892958462238;
                                attribute 'σ_Cy' : Real = 28.23690002309109;
                                attribute Cz : Real = 85.10421188548207;
                                attribute 'σ_Cz' : Real = 29.057750463592832;
                                attribute Ixx : Real = 0.8211560207005684;
                                attribute 'σ_Ixx' : Real = 0.37074144170588635;
                                attribute Iyy : Real = 0.7493723798815796;
                                attribute 'σ_Iyy' : Real = 0.3723953238821935;
                                attribute Izz : Real = 0.7222445548861581;
                                attribute 'σ_Izz' : Real = 0.37017423652493897;
                                attribute Ixy : Real = 0.05420213167923642;
                                attribute 'σ_Ixy' : Real = 0.02351283871158888;
                                attribute Ixz : Real = -0.008305300103981457;
                                attribute 'σ_Ixz' : Real = 0.022566176940390956;
                                attribute Iyz : Real = 0.002751495075160395;
                                attribute 'σ_Iyz' : Real = 0.02209918015384651;
                            }
                            part <'C.1.2.3.2.4.5.4'> 'Part 1116' {
                                attribute POIconv : String = "+";
                                attribute Ipoint : Boolean = false;
                                attribute mass : Real = 0.09126331778988242;
                                attribute 'σ_mass' : Real = 0.28909372274994966;
                                attribute Cx : Real = 24.23046096228063;
                                attribute 'σ_Cx' : Real = 28.721044428837228;
                                attribute Cy : Real = 98.20293877273798;
                                attribute 'σ_Cy' : Real = 28.23690002309109;
                                attribute Cz : Real = -98.84484428912401;
                                attribute 'σ_Cz' : Real = 29.057750463592832;
                                attribute Ixx : Real = 0.11036362834762625;
                                attribute 'σ_Ixx' : Real = 0.37074144170588635;
                                attribute Iyy : Real = 0.12282192603579145;
                                attribute 'σ_Iyy' : Real = 0.3723953238821935;
                                attribute Izz : Real = 0.10383856477144217;
                                attribute 'σ_Izz' : Real = 0.37017423652493897;
                                attribute Ixy : Real = 0.0075857185307616065;
                                attribute 'σ_Ixy' : Real = 0.02351283871158888;
                                attribute Ixz : Real = 6.377065400574866e-4;
                                attribute 'σ_Ixz' : Real = 0.022566176940390956;
                                attribute Iyz : Real = 0.005336207085140968;
                                attribute 'σ_Iyz' : Real = 0.02209918015384651;
                            }
                        }
                    }
                    part <'C.1.2.3.2.5'> 'Assembly 92' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.2.5.1'> 'Subassembly 315' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.5.1.1'> 'Part 1117' {
                                attribute POIconv : String = "+";
                                attribute Ipoint : Boolean = false;
                                attribute mass : Real = 0.47044576397631316;
                                attribute 'σ_mass' : Real = 0.28909372274994966;
                                attribute Cx : Real = 2.569628646597266;
                                attribute 'σ_Cx' : Real = 28.721044428837228;
                                attribute Cy : Real = -32.78453899547458;
                                attribute 'σ_Cy' : Real = 28.23690002309109;
                                attribute Cz : Real = 6.346535868942738;
                                attribute 'σ_Cz' : Real = 29.057750463592832;
                                attribute Ixx : Real = 0.6435109223521447;
                                attribute 'σ_Ixx' : Real = 0.37074144170588635;
                                attribute Iyy : Real = 0.6319281439582822;
                                attribute 'σ_Iyy' : Real = 0.3723953238821935;
                                attribute Izz : Real = 0.635749727032682;
                                attribute 'σ_Izz' : Real = 0.37017423652493897;
                                attribute Ixy : Real = -0.009649223272934833;
                                attribute 'σ_Ixy' : Real = 0.02351283871158888;
                                attribute Ixz : Real = -0.004767302061863253;
                                attribute 'σ_Ixz' : Real = 0.022566176940390956;
                                attribute Iyz : Real = 0.006933716334258468;
                                attribute 'σ_Iyz' : Real = 0.02209918015384651;
                            }
                            part <'C.1.2.3.2.5.1.2'> 'Part 1118' {
                                attribute POIconv : String = "-";
                                attribute Ipoint : Boolean = false;
                                attribute mass : Real = 0.37974785833922214;
                                attribute 'σ_mass' : Real = 0.28909372274994966;
                                attribute Cx : Real = -85.01557409763336;
                                attribute 'σ_Cx' : Real = 28.721044428837228;
                                attribute Cy : Real = 62.093520956113935;
                                attribute 'σ_Cy' : Real = 28.23690002309109;
                                attribute Cz : Real = -54.929202469065785;
                                attribute 'σ_Cz' : Real = 29.057750463592832;
                                attribute Ixx : Real = 0.5849535482464808;
                                attribute 'σ_Ixx' : Real = 0.37074144170588635;
                                attribute Iyy : Real = 0.5346327766143826;
                                attribute 'σ_Iyy' : Real = 0.3723953238821935;
                                attribute Izz : Real = 0.5736480168125648;
                                attribute 'σ_Izz' : Real = 0.37017423652493897;
                                attribute Ixy : Real = 0.00890710336288442;
                                attribute 'σ_Ixy' : Real = 0.02351283871158888;
                                attribute Ixz : Real = 0.004345863693145809;
                                attribute 'σ_Ixz' : Real = 0.022566176940390956;
                                attribute Iyz : Real = -0.004018970593441017;
                                attribute 'σ_Iyz' : Real = 0.02209918015384651;
                            }
                            part <'C.1.2.3.2.5.1.3'> 'Part 1119' {
                                attribute POIconv : String = "-";
                                attribute Ipoint : Boolean = false;
                                attribute mass : Real = 0.14067737479438075;
                                attribute 'σ_mass' : Real = 0.28909372274994966;
                                attribute Cx : Real = 32.7779624145478;
                                attribute 'σ_Cx' : Real = 28.721044428837228;
                                attribute Cy : Real = 75.29446827247739;
                                attribute 'σ_Cy' : Real = 28.23690002309109;
                                attribute Cz : Real = -11.46841049194336;
                                attribute 'σ_Cz' : Real = 29.057750463592832;
                                attribute Ixx : Real = 0.15892723039233403;
                                attribute 'σ_Ixx' : Real = 0.37074144170588635;
                                attribute Iyy : Real = 0.1678808983553926;
                                attribute 'σ_Iyy' : Real = 0.3723953238821935;
                                attribute Izz : Real = 0.17775567616954238;
                                attribute 'σ_Izz' : Real = 0.37017423652493897;
                                attribute Ixy : Real = 0.0018071040092204952;
                                attribute 'σ_Ixy' : Real = 0.02351283871158888;
                                attribute Ixz : Real = -0.001680649506816778;
                                attribute 'σ_Ixz' : Real = 0.022566176940390956;
                                attribute Iyz : Real = -0.014830472293822429;
                                attribute 'σ_Iyz' : Real = 0.02209918015384651;
                            }
                            part <'C.1.2.3.2.5.1.4'> 'Part 1120' {
                                attribute POIconv : String = "+";
                                attribute Ipoint : Boolean = false;
                                attribute mass : Real = 0.034414559416007254;
                                attribute 'σ_mass' : Real = 0.28909372274994966;
                                attribute Cx : Real = -97.60396899655461;
                                attribute 'σ_Cx' : Real = 28.721044428837228;
                                attribute Cy : Real = -68.05190462619066;
                                attribute 'σ_Cy' : Real = 28.23690002309109;
                                attribute Cz : Real = 75.59148604050279;
                                attribute 'σ_Cz' : Real = 29.057750463592832;
                                attribute Ixx : Real = 0.038059115816056935;
                                attribute 'σ_Ixx' : Real = 0.37074144170588635;
                                attribute Iyy : Real = 0.044014803362034095;
                                attribute 'σ_Iyy' : Real = 0.3723953238821935;
                                attribute Izz : Real = 0.042160093414771393;
                                attribute 'σ_Izz' : Real = 0.37017423652493897;
                                attribute Ixy : Real = 0.0013617379503700182;
                                attribute 'σ_Ixy' : Real = 0.02351283871158888;
                                attribute Ixz : Real = 2.04852444372326e-4;
                                attribute 'σ_Ixz' : Real = 0.022566176940390956;
                                attribute Iyz : Real = -0.0035621184285471457;
                                attribute 'σ_Iyz' : Real = 0.02209918015384651;
                            }
                        }
                        part <'C.1.2.3.2.5.2'> 'Subassembly 316' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.2.5.2.1'> 'Part 1121' {
                                attribute POIconv : String = "+";
                                attribute Ipoint : Boolean = false;
                                attribute mass : Real = 0.8136336002105381;
                                attribute 'σ_mass' : Real = 0.28909372274994966;
                                attribute Cx : Real = 18.792902631685138;
                                attribute 'σ_Cx' : Real = 28.721044428837228;
                                attribute Cy : Real = -84.80450455099344;
                                attribute 'σ_Cy' : Real = 28.23690002309109;
                                attribute Cz : Real = -25.386005640029907;
                                attribute 'σ_Cz' : Real = 29.057750463592832;
                                attribute Ixx : Real = 0.9875334638584475;
                                attribute 'σ_Ixx' : Real = 0.37074144170588635;
                                attribute Iyy : Real = 0.8492803765609918;
                                attribute 'σ_Iyy' : Real = 0.3723953238821935;
                                attribute Izz : Real = 0.9176661921602746;
                                attribute 'σ_Izz' : Real = 0.37017423652493897;
                                attribute Ixy : Real = -0.02184093446547435;
                                attribute 'σ_Ixy' : Real = 0.02351283871158888;
                                attribute Ixz : Real = -0.011531735642302495;
                                attribute 'σ_Ixz' : Real = 0.022566176940390956;
                                attribute Iyz : Real = -0.006885765518491183;
                                attribute 'σ_Iyz' : Real = 0.02209918015384651;
                            }
                            part <'C.1.2.3.2.5.2.2'> 'Part 1122' {
                                attribute POIconv : String = "+";
                                attribute Ipoint : Boolean = false;
                                attribute mass : Real = 0.19911163453245537;
                                attribute 'σ_mass' : Real = 0.28909372274994966;
                                attribute Cx : Real = 3.27370073646307;
                                attribute 'σ_Cx' : Real = 28.721044428837228;
                                attribute Cy : Real = -48.36344122886658;
                                attribute 'σ_Cy' : Real = 28.23690002309109;
                                attribute Cz : Real = -23.354453407227993;
                                attribute 'σ_Cz' : Real = 29.057750463592832;
                                attribute Ixx : Real = 0.23449143385256138;
                                attribute 'σ_Ixx' : Real = 0.37074144170588635;
                                attribute Iyy : Real = 0.22483809930691548;
                                attribute 'σ_Iyy' : Real = 0.3723953238821935;
                                attribute Izz : Real = 0.2247627247990798;
                                attribute 'σ_Izz' : Real = 0.37017423652493897;
                                attribute Ixy : Real = 0.016296491388182663;
                                attribute 'σ_Ixy' : Real = 0.02351283871158888;
                                attribute Ixz : Real = -0.027969523137785075;
                                attribute 'σ_Ixz' : Real = 0.022566176940390956;
                                attribute Iyz : Real = -0.020955658093139956;
                                attribute 'σ_Iyz' : Real = 0.02209918015384651;
                            }
                        }
                    }
                }
                part <'C.1.2.3.3'> 'Subsystem 25' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.2.3.3.1'> 'Assembly 93' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.3.1.1'> 'Subassembly 317' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.1.1.1'> 'Part 1123' {
                                attribute POIconv : String = "-";
                                attribute Ipoint : Boolean = false;
                                attribute mass : Real = 0.7402315276924055;
                                attribute 'σ_mass' : Real = 0.28909372274994966;
                                attribute Cx : Real = -90.6176423188299;
                                attribute 'σ_Cx' : Real = 28.721044428837228;
                                attribute Cy : Real = 91.29746346734464;
                                attribute 'σ_Cy' : Real = 28.23690002309109;
                                attribute Cz : Real = 54.458841728046536;
                                attribute 'σ_Cz' : Real = 29.057750463592832;
                                attribute Ixx : Real = 1.0179245101354817;
                                attribute 'σ_Ixx' : Real = 0.37074144170588635;
                                attribute Iyy : Real = 0.9064378212625557;
                                attribute 'σ_Iyy' : Real = 0.3723953238821935;
                                attribute Izz : Real = 0.9961967172515375;
                                attribute 'σ_Izz' : Real = 0.37017423652493897;
                                attribute Ixy : Real = -0.04097862941807292;
                                attribute 'σ_Ixy' : Real = 0.02351283871158888;
                                attribute Ixz : Real = 0.011574126188077617;
                                attribute 'σ_Ixz' : Real = 0.022566176940390956;
                                attribute Iyz : Real = -0.050948997775442643;
                                attribute 'σ_Iyz' : Real = 0.02209918015384651;
                            }
                            part <'C.1.2.3.3.1.1.2'> 'Part 1124' {
                                attribute POIconv : String = "-";
                                attribute Ipoint : Boolean = false;
                                attribute mass : Real = 0.5629994987144601;
                                attribute 'σ_mass' : Real = 0.28909372274994966;
                                attribute Cx : Real = -1.9051856361329556;
                                attribute 'σ_Cx' : Real = 28.721044428837228;
                                attribute Cy : Real = -12.37833690829575;
                                attribute 'σ_Cy' : Real = 28.23690002309109;
                                attribute Cz : Real = 16.911207512021065;
                                attribute 'σ_Cz' : Real = 29.057750463592832;
                                attribute Ixx : Real = 0.7131628517514028;
                                attribute 'σ_Ixx' : Real = 0.37074144170588635;
                                attribute Iyy : Real = 0.666251029176459;
                                attribute 'σ_Iyy' : Real = 0.3723953238821935;
                                attribute Izz : Real = 0.6518860524368141;
                                attribute 'σ_Izz' : Real = 0.37017423652493897;
                                attribute Ixy : Real = -0.02391320703225242;
                                attribute 'σ_Ixy' : Real = 0.02351283871158888;
                                attribute Ixz : Real = 0.013281885385761378;
                                attribute 'σ_Ixz' : Real = 0.022566176940390956;
                                attribute Iyz : Real = 0.06423244867076075;
                                attribute 'σ_Iyz' : Real = 0.02209918015384651;
                            }
                        }
                        part <'C.1.2.3.3.1.2'> 'Subassembly 318' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.1.2.1'> 'Part 1125' {
                                attribute POIconv : String = "+";
                                attribute Ipoint : Boolean = false;
                                attribute mass : Real = 0.9771186153339222;
                                attribute 'σ_mass' : Real = 0.28909372274994966;
                                attribute Cx : Real = 56.416200241073966;
                                attribute 'σ_Cx' : Real = 28.721044428837228;
                                attribute Cy : Real = 57.22544393502176;
                                attribute 'σ_Cy' : Real = 28.23690002309109;
                                attribute Cz : Real = -37.21758299507201;
                                attribute 'σ_Cz' : Real = 29.057750463592832;
                                attribute Ixx : Real = 1.2044085430831106;
                                attribute 'σ_Ixx' : Real = 0.37074144170588635;
                                attribute Iyy : Real = 0.9881488738740569;
                                attribute 'σ_Iyy' : Real = 0.3723953238821935;
                                attribute Izz : Real = 1.1867021157945699;
                                attribute 'σ_Izz' : Real = 0.37017423652493897;
                                attribute Ixy : Real = -0.06383660530983334;
                                attribute 'σ_Ixy' : Real = 0.02351283871158888;
                                attribute Ixz : Real = -0.02092339044913391;
                                attribute 'σ_Ixz' : Real = 0.022566176940390956;
                                attribute Iyz : Real = 0.04866868527405713;
                                attribute 'σ_Iyz' : Real = 0.02209918015384651;
                            }
                            part <'C.1.2.3.3.1.2.2'> 'Part 1126' {
                                attribute POIconv : String = "-";
                                attribute Ipoint : Boolean = false;
                                attribute mass : Real = 0.3694087115677539;
                                attribute 'σ_mass' : Real = 0.28909372274994966;
                                attribute Cx : Real = 10.647061048075557;
                                attribute 'σ_Cx' : Real = 28.721044428837228;
                                attribute Cy : Real = 52.2939610760659;
                                attribute 'σ_Cy' : Real = 28.23690002309109;
                                attribute Cz : Real = -58.04320606403053;
                                attribute 'σ_Cz' : Real = 29.057750463592832;
                                attribute Ixx : Real = 0.5275253429735705;
                                attribute 'σ_Ixx' : Real = 0.37074144170588635;
                                attribute Iyy : Real = 0.5194531474684527;
                                attribute 'σ_Iyy' : Real = 0.3723953238821935;
                                attribute Izz : Real = 0.4912565970207912;
                                attribute 'σ_Izz' : Real = 0.37017423652493897;
                                attribute Ixy : Real = -0.015045108692227315;
                                attribute 'σ_Ixy' : Real = 0.02351283871158888;
                                attribute Ixz : Real = 0.007796659230711382;
                                attribute 'σ_Ixz' : Real = 0.022566176940390956;
                                attribute Iyz : Real = 0.004199626118750391;
                                attribute 'σ_Iyz' : Real = 0.02209918015384651;
                            }
                            part <'C.1.2.3.3.1.2.3'> 'Part 1127' {
                                attribute POIconv : String = "+";
                                attribute Ipoint : Boolean = false;
                                attribute mass : Real = 0.3638120953426696;
                                attribute 'σ_mass' : Real = 0.28909372274994966;
                                attribute Cx : Real = 34.06212884001434;
                                attribute 'σ_Cx' : Real = 28.721044428837228;
                                attribute Cy : Real = -94.89191491156816;
                                attribute 'σ_Cy' : Real = 28.23690002309109;
                                attribute Cz : Real = -57.52921896055341;
                                attribute 'σ_Cz' : Real = 29.057750463592832;
                                attribute Ixx : Real = 0.4424417369904654;
                                attribute 'σ_Ixx' : Real = 0.37074144170588635;
                                attribute Iyy : Real = 0.3844101733738442;
                                attribute 'σ_Iyy' : Real = 0.3723953238821935;
                                attribute Izz : Real = 0.41688282310939734;
                                attribute 'σ_Izz' : Real = 0.37017423652493897;
                                attribute Ixy : Real = -0.016384025792099875;
                                attribute 'σ_Ixy' : Real = 0.02351283871158888;
                                attribute Ixz : Real = -0.032584746128578854;
                                attribute 'σ_Ixz' : Real = 0.022566176940390956;
                                attribute Iyz : Real = 0.0012805385570121056;
                                attribute 'σ_Iyz' : Real = 0.02209918015384651;
                            }
                        }
                    }
                    part <'C.1.2.3.3.2'> 'Assembly 94' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.3.2.1'> 'Subassembly 319' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.2.1.1'> 'Part 1128' {
                                attribute POIconv : String = "+";
                                attribute Ipoint : Boolean = false;
                                attribute mass : Real = 0.300287495268276;
                                attribute 'σ_mass' : Real = 0.28909372274994966;
                                attribute Cx : Real = 68.32964611239731;
                                attribute 'σ_Cx' : Real = 28.721044428837228;
                                attribute Cy : Real = 3.152820374816656;
                                attribute 'σ_Cy' : Real = 28.23690002309109;
                                attribute Cz : Real = -66.47687186487019;
                                attribute 'σ_Cz' : Real = 29.057750463592832;
                                attribute Ixx : Real = 0.36934015848696866;
                                attribute 'σ_Ixx' : Real = 0.37074144170588635;
                                attribute Iyy : Real = 0.33326036779988943;
                                attribute 'σ_Iyy' : Real = 0.3723953238821935;
                                attribute Izz : Real = 0.4384724295112993;
                                attribute 'σ_Izz' : Real = 0.37017423652493897;
                                attribute Ixy : Real = -0.005957327785694725;
                                attribute 'σ_Ixy' : Real = 0.02351283871158888;
                                attribute Ixz : Real = -0.005763712398440347;
                                attribute 'σ_Ixz' : Real = 0.022566176940390956;
                                attribute Iyz : Real = 0.02152417654744623;
                                attribute 'σ_Iyz' : Real = 0.02209918015384651;
                            }
                            part <'C.1.2.3.3.2.1.2'> 'Part 1129' {
                                attribute POIconv : String = "+";
                                attribute Ipoint : Boolean = false;
                                attribute mass : Real = 0.6313118730988353;
                                attribute 'σ_mass' : Real = 0.28909372274994966;
                                attribute Cx : Real = -65.77382539398968;
                                attribute 'σ_Cx' : Real = 28.721044428837228;
                                attribute Cy : Real = 92.49089434742928;
                                attribute 'σ_Cy' : Real = 28.23690002309109;
                                attribute Cz : Real = -93.92624609172344;
                                attribute 'σ_Cz' : Real = 29.057750463592832;
                                attribute Ixx : Real = 0.9052151271990161;
                                attribute 'σ_Ixx' : Real = 0.37074144170588635;
                                attribute Iyy : Real = 0.9188131205196788;
                                attribute 'σ_Iyy' : Real = 0.3723953238821935;
                                attribute Izz : Real = 0.8429030930681655;
                                attribute 'σ_Izz' : Real = 0.37017423652493897;
                                attribute Ixy : Real = 0.0577147169741431;
                                attribute 'σ_Ixy' : Real = 0.02351283871158888;
                                attribute Ixz : Real = -0.0010377715377740677;
                                attribute 'σ_Ixz' : Real = 0.022566176940390956;
                                attribute Iyz : Real = 5.588881213690777e-4;
                                attribute 'σ_Iyz' : Real = 0.02209918015384651;
                            }
                            part <'C.1.2.3.3.2.1.3'> 'Part 1130' {
                                attribute POIconv : String = "+";
                                attribute Ipoint : Boolean = false;
                                attribute mass : Real = 0.3436191369073931;
                                attribute 'σ_mass' : Real = 0.28909372274994966;
                                attribute Cx : Real = 95.01519436016679;
                                attribute 'σ_Cx' : Real = 28.721044428837228;
                                attribute Cy : Real = -47.71872563287616;
                                attribute 'σ_Cy' : Real = 28.23690002309109;
                                attribute Cz : Real = -45.841980539262295;
                                attribute 'σ_Cz' : Real = 29.057750463592832;
                                attribute Ixx : Real = 0.42306059961619746;
                                attribute 'σ_Ixx' : Real = 0.37074144170588635;
                                attribute Iyy : Real = 0.43898016803194384;
                                attribute 'σ_Iyy' : Real = 0.3723953238821935;
                                attribute Izz : Real = 0.45376610250614074;
                                attribute 'σ_Izz' : Real = 0.37017423652493897;
                                attribute Ixy : Real = 0.050977190340680364;
                                attribute 'σ_Ixy' : Real = 0.02351283871158888;
                                attribute Ixz : Real = 0.01048526169886384;
                                attribute 'σ_Ixz' : Real = 0.022566176940390956;
                                attribute Iyz : Real = -0.01761748347598234;
                                attribute 'σ_Iyz' : Real = 0.02209918015384651;
                            }
                            part <'C.1.2.3.3.2.1.4'> 'Part 1131' {
                                attribute POIconv : String = "-";
                                attribute Ipoint : Boolean = false;
                                attribute mass : Real = 0.26585083035216667;
                                attribute 'σ_mass' : Real = 0.28909372274994966;
                                attribute Cx : Real = -6.060240929946303;
                                attribute 'σ_Cx' : Real = 28.721044428837228;
                                attribute Cy : Real = -77.85823168233037;
                                attribute 'σ_Cy' : Real = 28.23690002309109;
                                attribute Cz : Real = 43.523722840473056;
                                attribute 'σ_Cz' : Real = 29.057750463592832;
                                attribute Ixx : Real = 0.4129818329488012;
                                attribute 'σ_Ixx' : Real = 0.37074144170588635;
                                attribute Iyy : Real = 0.36396376179780493;
                                attribute 'σ_Iyy' : Real = 0.3723953238821935;
                                attribute Izz : Real = 0.35550458844387295;
                                attribute 'σ_Izz' : Real = 0.37017423652493897;
                                attribute Ixy : Real = -0.0211706853257008;
                                attribute 'σ_Ixy' : Real = 0.02351283871158888;
                                attribute Ixz : Real = -0.007904168998703706;
                                attribute 'σ_Ixz' : Real = 0.022566176940390956;
                                attribute Iyz : Real = -1.0739461788334439e-4;
                                attribute 'σ_Iyz' : Real = 0.02209918015384651;
                            }
                            part <'C.1.2.3.3.2.1.5'> 'Part 1132' {
                                attribute POIconv : String = "-";
                                attribute Ipoint : Boolean = false;
                                attribute mass : Real = 0.21106479846220463;
                                attribute 'σ_mass' : Real = 0.28909372274994966;
                                attribute Cx : Real = -44.2881076131016;
                                attribute 'σ_Cx' : Real = 28.721044428837228;
                                attribute Cy : Real = 82.73152085021138;
                                attribute 'σ_Cy' : Real = 28.23690002309109;
                                attribute Cz : Real = -22.1117430832237;
                                attribute 'σ_Cz' : Real = 29.057750463592832;
                                attribute Ixx : Real = 0.25086121241928727;
                                attribute 'σ_Ixx' : Real = 0.37074144170588635;
                                attribute Iyy : Real = 0.2923312086306453;
                                attribute 'σ_Iyy' : Real = 0.3723953238821935;
                                attribute Izz : Real = 0.2690899894141246;
                                attribute 'σ_Izz' : Real = 0.37017423652493897;
                                attribute Ixy : Real = 0.014416957482808924;
                                attribute 'σ_Ixy' : Real = 0.02351283871158888;
                                attribute Ixz : Real = 0.010783202443186918;
                                attribute 'σ_Ixz' : Real = 0.022566176940390956;
                                attribute Iyz : Real = 0.008936610454802823;
                                attribute 'σ_Iyz' : Real = 0.02209918015384651;
                            }
                        }
                        part <'C.1.2.3.3.2.2'> 'Subassembly 320' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.2.2.1'> 'Part 1133' {
                                attribute POIconv : String = "+";
                                attribute Ipoint : Boolean = false;
                                attribute mass : Real = 0.16530295626493172;
                                attribute 'σ_mass' : Real = 0.28909372274994966;
                                attribute Cx : Real = 16.369473561644554;
                                attribute 'σ_Cx' : Real = 28.721044428837228;
                                attribute Cy : Real = -34.88249834626913;
                                attribute 'σ_Cy' : Real = 28.23690002309109;
                                attribute Cz : Real = -38.14453766681254;
                                attribute 'σ_Cz' : Real = 29.057750463592832;
                                attribute Ixx : Real = 0.25503409827761864;
                                attribute 'σ_Ixx' : Real = 0.37074144170588635;
                                attribute Iyy : Real = 0.2508321338514727;
                                attribute 'σ_Iyy' : Real = 0.3723953238821935;
                                attribute Izz : Real = 0.2349600814221059;
                                attribute 'σ_Izz' : Real = 0.37017423652493897;
                                attribute Ixy : Real = -0.001871789487561103;
                                attribute 'σ_Ixy' : Real = 0.02351283871158888;
                                attribute Ixz : Real = 4.500984796894639e-5;
                                attribute 'σ_Ixz' : Real = 0.022566176940390956;
                                attribute Iyz : Real = -0.003602639942466051;
                                attribute 'σ_Iyz' : Real = 0.02209918015384651;
                            }
                            part <'C.1.2.3.3.2.2.2'> 'Part 1134' {
                                attribute POIconv : String = "+";
                                attribute Ipoint : Boolean = false;
                                attribute mass : Real = 0.21987718947092072;
                                attribute 'σ_mass' : Real = 0.28909372274994966;
                                attribute Cx : Real = -65.31264008954167;
                                attribute 'σ_Cx' : Real = 28.721044428837228;
                                attribute Cy : Real = -4.255700530484319;
                                attribute 'σ_Cy' : Real = 28.23690002309109;
                                attribute Cz : Real = -86.48242908529937;
                                attribute 'σ_Cz' : Real = 29.057750463592832;
                                attribute Ixx : Real = 0.29381339334264334;
                                attribute 'σ_Ixx' : Real = 0.37074144170588635;
                                attribute Iyy : Real = 0.31808276140654207;
                                attribute 'σ_Iyy' : Real = 0.3723953238821935;
                                attribute Izz : Real = 0.28945871052345834;
                                attribute 'σ_Izz' : Real = 0.37017423652493897;
                                attribute Ixy : Real = 0.017812997157717874;
                                attribute 'σ_Ixy' : Real = 0.02351283871158888;
                                attribute Ixz : Real = 2.0626148078625102e-4;
                                attribute 'σ_Ixz' : Real = 0.022566176940390956;
                                attribute Iyz : Real = -8.951390882603949e-5;
                                attribute 'σ_Iyz' : Real = 0.02209918015384651;
                            }
                            part <'C.1.2.3.3.2.2.3'> 'Part 1135' {
                                attribute POIconv : String = "-";
                                attribute Ipoint : Boolean = false;
                                attribute mass : Real = 0.15249473765399307;
                                attribute 'σ_mass' : Real = 0.28909372274994966;
                                attribute Cx : Real = -75.27537047863007;
                                attribute 'σ_Cx' : Real = 28.721044428837228;
                                attribute Cy : Real = -76.74542139284313;
                                attribute 'σ_Cy' : Real = 28.23690002309109;
                                attribute Cz : Real = 96.29762298427522;
                                attribute 'σ_Cz' : Real = 29.057750463592832;
                                attribute Ixx : Real = 0.1452462579879769;
                                attribute 'σ_Ixx' : Real = 0.37074144170588635;
                                attribute Iyy : Real = 0.15108497357480608;
                                attribute 'σ_Iyy' : Real = 0.3723953238821935;
                                attribute Izz : Real = 0.15837791424322542;
                                attribute 'σ_Izz' : Real = 0.37017423652493897;
                                attribute Ixy : Real = -0.0024451108444513954;
                                attribute 'σ_Ixy' : Real = 0.02351283871158888;
                                attribute Ixz : Real = 0.0011055171266655043;
                                attribute 'σ_Ixz' : Real = 0.022566176940390956;
                                attribute Iyz : Real = -0.0052871407602917775;
                                attribute 'σ_Iyz' : Real = 0.02209918015384651;
                            }
                        }
                        part <'C.1.2.3.3.2.3'> 'Subassembly 321' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.2.3.1'> 'Part 1136' {
                                attribute POIconv : String = "-";
                                attribute Ipoint : Boolean = false;
                                attribute mass : Real = 0.4949692073278129;
                                attribute 'σ_mass' : Real = 0.28909372274994966;
                                attribute Cx : Real = 51.751705491915345;
                                attribute 'σ_Cx' : Real = 28.721044428837228;
                                attribute Cy : Real = -82.3002414777875;
                                attribute 'σ_Cy' : Real = 28.23690002309109;
                                attribute Cz : Real = -73.04290840402246;
                                attribute 'σ_Cz' : Real = 29.057750463592832;
                                attribute Ixx : Real = 0.5468992172889806;
                                attribute 'σ_Ixx' : Real = 0.37074144170588635;
                                attribute Iyy : Real = 0.6270105274079575;
                                attribute 'σ_Iyy' : Real = 0.3723953238821935;
                                attribute Izz : Real = 0.6243832705769022;
                                attribute 'σ_Izz' : Real = 0.37017423652493897;
                                attribute Ixy : Real = 0.07254116357168534;
                                attribute 'σ_Ixy' : Real = 0.02351283871158888;
                                attribute Ixz : Real = -0.017785245093049407;
                                attribute 'σ_Ixz' : Real = 0.022566176940390956;
                                attribute Iyz : Real = 0.013614617102668588;
                                attribute 'σ_Iyz' : Real = 0.02209918015384651;
                            }
                            part <'C.1.2.3.3.2.3.2'> 'Part 1137' {
                                attribute POIconv : String = "-";
                                attribute Ipoint : Boolean = false;
                                attribute mass : Real = 0.026876852105138824;
                                attribute 'σ_mass' : Real = 0.28909372274994966;
                                attribute Cx : Real = 98.31936792470515;
                                attribute 'σ_Cx' : Real = 28.721044428837228;
                                attribute Cy : Real = 98.197972914204;
                                attribute 'σ_Cy' : Real = 28.23690002309109;
                                attribute Cz : Real = -24.136184295639396;
                                attribute 'σ_Cz' : Real = 29.057750463592832;
                                attribute Ixx : Real = 0.033284602015161126;
                                attribute 'σ_Ixx' : Real = 0.37074144170588635;
                                attribute Iyy : Real = 0.03463491734367418;
                                attribute 'σ_Iyy' : Real = 0.3723953238821935;
                                attribute Izz : Real = 0.03223346391066476;
                                attribute 'σ_Izz' : Real = 0.37017423652493897;
                                attribute Ixy : Real = -0.0019857378748306224;
                                attribute 'σ_Ixy' : Real = 0.02351283871158888;
                                attribute Ixz : Real = -6.402604989273093e-4;
                                attribute 'σ_Ixz' : Real = 0.022566176940390956;
                                attribute Iyz : Real = 0.0017428941593680498;
                                attribute 'σ_Iyz' : Real = 0.02209918015384651;
                            }
                            part <'C.1.2.3.3.2.3.3'> 'Part 1138' {
                                attribute POIconv : String = "-";
                                attribute Ipoint : Boolean = false;
                                attribute mass : Real = 0.8601742880437523;
                                attribute 'σ_mass' : Real = 0.28909372274994966;
                                attribute Cx : Real = 95.5351846292615;
                                attribute 'σ_Cx' : Real = 28.721044428837228;
                                attribute Cy : Real = 93.52711904793978;
                                attribute 'σ_Cy' : Real = 28.23690002309109;
                                attribute Cz : Real = 92.00677648186684;
                                attribute 'σ_Cz' : Real = 29.057750463592832;
                                attribute Ixx : Real = 1.0219546514477373;
                                attribute 'σ_Ixx' : Real = 0.37074144170588635;
                                attribute Iyy : Real = 1.077712092840212;
                                attribute 'σ_Iyy' : Real = 0.3723953238821935;
                                attribute Izz : Real = 1.1627805137826237;
                                attribute 'σ_Izz' : Real = 0.37017423652493897;
                                attribute Ixy : Real = -0.053868656566637044;
                                attribute 'σ_Ixy' : Real = 0.02351283871158888;
                                attribute Ixz : Real = -0.015212325251310648;
                                attribute 'σ_Ixz' : Real = 0.022566176940390956;
                                attribute Iyz : Real = -0.03678154830821617;
                                attribute 'σ_Iyz' : Real = 0.02209918015384651;
                            }
                            part <'C.1.2.3.3.2.3.4'> 'Part 1139' {
                                attribute POIconv : String = "-";
                                attribute Ipoint : Boolean = false;
                                attribute mass : Real = 0.06272422112897039;
                                attribute 'σ_mass' : Real = 0.28909372274994966;
                                attribute Cx : Real = 87.95182816684246;
                                attribute 'σ_Cx' : Real = 28.721044428837228;
                                attribute Cy : Real = -91.79763020947576;
                                attribute 'σ_Cy' : Real = 28.23690002309109;
                                attribute Cz : Real = -31.500987708568573;
                                attribute 'σ_Cz' : Real = 29.057750463592832;
                                attribute Ixx : Real = 0.08802745265021128;
                                attribute 'σ_Ixx' : Real = 0.37074144170588635;
                                attribute Iyy : Real = 0.07853123469248825;
                                attribute 'σ_Iyy' : Real = 0.3723953238821935;
                                attribute Izz : Real = 0.08959774559323586;
                                attribute 'σ_Izz' : Real = 0.37017423652493897;
                                attribute Ixy : Real = -5.522474371692713e-4;
                                attribute 'σ_Ixy' : Real = 0.02351283871158888;
                                attribute Ixz : Real = -3.955644618723155e-4;
                                attribute 'σ_Ixz' : Real = 0.022566176940390956;
                                attribute Iyz : Real = 0.004539404301995009;
                                attribute 'σ_Iyz' : Real = 0.02209918015384651;
                            }
                        }
                        part <'C.1.2.3.3.2.4'> 'Subassembly 322' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.2.4.1'> 'Part 1140' {
                                attribute POIconv : String = "-";
                                attribute Ipoint : Boolean = false;
                                attribute mass : Real = 0.8029978942512535;
                                attribute 'σ_mass' : Real = 0.28909372274994966;
                                attribute Cx : Real = -58.86550433933735;
                                attribute 'σ_Cx' : Real = 28.721044428837228;
                                attribute Cy : Real = -78.26017765328288;
                                attribute 'σ_Cy' : Real = 28.23690002309109;
                                attribute Cz : Real = 81.46493663080037;
                                attribute 'σ_Cz' : Real = 29.057750463592832;
                                attribute Ixx : Real = 0.8267211510723803;
                                attribute 'σ_Ixx' : Real = 0.37074144170588635;
                                attribute Iyy : Real = 0.9706107330115894;
                                attribute 'σ_Iyy' : Real = 0.3723953238821935;
                                attribute Izz : Real = 0.9742928874226946;
                                attribute 'σ_Izz' : Real = 0.37017423652493897;
                                attribute Ixy : Real = -0.01726447560138701;
                                attribute 'σ_Ixy' : Real = 0.02351283871158888;
                                attribute Ixz : Real = -0.07927684323198714;
                                attribute 'σ_Ixz' : Real = 0.022566176940390956;
                                attribute Iyz : Real = -0.022719756170377147;
                                attribute 'σ_Iyz' : Real = 0.02209918015384651;
                            }
                            part <'C.1.2.3.3.2.4.2'> 'Part 1141' {
                                attribute POIconv : String = "+";
                                attribute Ipoint : Boolean = false;
                                attribute mass : Real = 0.1681197369468864;
                                attribute 'σ_mass' : Real = 0.28909372274994966;
                                attribute Cx : Real = -3.885092632845044;
                                attribute 'σ_Cx' : Real = 28.721044428837228;
                                attribute Cy : Real = -38.47290319390595;
                                attribute 'σ_Cy' : Real = 28.23690002309109;
                                attribute Cz : Real = -21.66428449563682;
                                attribute 'σ_Cz' : Real = 29.057750463592832;
                                attribute Ixx : Real = 0.15253122724865734;
                                attribute 'σ_Ixx' : Real = 0.37074144170588635;
                                attribute Iyy : Real = 0.21085548556488662;
                                attribute 'σ_Iyy' : Real = 0.3723953238821935;
                                attribute Izz : Real = 0.20495983175999954;
                                attribute 'σ_Izz' : Real = 0.37017423652493897;
                                attribute Ixy : Real = 0.002656356006204293;
                                attribute 'σ_Ixy' : Real = 0.02351283871158888;
                                attribute Ixz : Real = -0.016617772613760014;
                                attribute 'σ_Ixz' : Real = 0.022566176940390956;
                                attribute Iyz : Real = -6.72715475454482e-4;
                                attribute 'σ_Iyz' : Real = 0.02209918015384651;
                            }
                            part <'C.1.2.3.3.2.4.3'> 'Part 1142' {
                                attribute POIconv : String = "-";
                                attribute Ipoint : Boolean = false;
                                attribute mass : Real = 0.9485609727189876;
                                attribute 'σ_mass' : Real = 0.28909372274994966;
                                attribute Cx : Real = 89.16624281555414;
                                attribute 'σ_Cx' : Real = 28.721044428837228;
                                attribute Cy : Real = -45.19746410660446;
                                attribute 'σ_Cy' : Real = 28.23690002309109;
                                attribute Cz : Real = 92.63938828371465;
                                attribute 'σ_Cz' : Real = 29.057750463592832;
                                attribute Ixx : Real = 1.1946055548062644;
                                attribute 'σ_Ixx' : Real = 0.37074144170588635;
                                attribute Iyy : Real = 1.1394912112408166;
                                attribute 'σ_Iyy' : Real = 0.3723953238821935;
                                attribute Izz : Real = 1.3186808812918016;
                                attribute 'σ_Izz' : Real = 0.37017423652493897;
                                attribute Ixy : Real = 0.012486014293346243;
                                attribute 'σ_Ixy' : Real = 0.02351283871158888;
                                attribute Ixz : Real = 0.032547914619737287;
                                attribute 'σ_Ixz' : Real = 0.022566176940390956;
                                attribute Iyz : Real = 0.025581138763356902;
                                attribute 'σ_Iyz' : Real = 0.02209918015384651;
                            }
                        }
                        part <'C.1.2.3.3.2.5'> 'Subassembly 323' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.2.5.1'> 'Part 1143' {
                                attribute POIconv : String = "-";
                                attribute Ipoint : Boolean = false;
                                attribute mass : Real = 0.5021571628896054;
                                attribute 'σ_mass' : Real = 0.28909372274994966;
                                attribute Cx : Real = 55.76005382463336;
                                attribute 'σ_Cx' : Real = 28.721044428837228;
                                attribute Cy : Real = 24.068352906033397;
                                attribute 'σ_Cy' : Real = 28.23690002309109;
                                attribute Cz : Real = 78.04477061145008;
                                attribute 'σ_Cz' : Real = 29.057750463592832;
                                attribute Ixx : Real = 0.6887006593860255;
                                attribute 'σ_Ixx' : Real = 0.37074144170588635;
                                attribute Iyy : Real = 0.6239165450929819;
                                attribute 'σ_Iyy' : Real = 0.3723953238821935;
                                attribute Izz : Real = 0.6141958518624007;
                                attribute 'σ_Izz' : Real = 0.37017423652493897;
                                attribute Ixy : Real = -0.0017188169770789915;
                                attribute 'σ_Ixy' : Real = 0.02351283871158888;
                                attribute Ixz : Real = -0.01357297004062851;
                                attribute 'σ_Ixz' : Real = 0.022566176940390956;
                                attribute Iyz : Real = 0.01199002590248726;
                                attribute 'σ_Iyz' : Real = 0.02209918015384651;
                            }
                            part <'C.1.2.3.3.2.5.2'> 'Part 1144' {
                                attribute POIconv : String = "+";
                                attribute Ipoint : Boolean = false;
                                attribute mass : Real = 0.21873833777871915;
                                attribute 'σ_mass' : Real = 0.28909372274994966;
                                attribute Cx : Real = -12.425463367253542;
                                attribute 'σ_Cx' : Real = 28.721044428837228;
                                attribute Cy : Real = 89.16734554804862;
                                attribute 'σ_Cy' : Real = 28.23690002309109;
                                attribute Cz : Real = 17.37482170574367;
                                attribute 'σ_Cz' : Real = 29.057750463592832;
                                attribute Ixx : Real = 0.24191406270711754;
                                attribute 'σ_Ixx' : Real = 0.37074144170588635;
                                attribute Iyy : Real = 0.26038520895876244;
                                attribute 'σ_Iyy' : Real = 0.3723953238821935;
                                attribute Izz : Real = 0.27093524158392573;
                                attribute 'σ_Izz' : Real = 0.37017423652493897;
                                attribute Ixy : Real = -0.016800119541176384;
                                attribute 'σ_Ixy' : Real = 0.02351283871158888;
                                attribute Ixz : Real = 0.003935348243412233;
                                attribute 'σ_Ixz' : Real = 0.022566176940390956;
                                attribute Iyz : Real = -6.682418489651988e-5;
                                attribute 'σ_Iyz' : Real = 0.02209918015384651;
                            }
                            part <'C.1.2.3.3.2.5.3'> 'Part 1145' {
                                attribute POIconv : String = "+";
                                attribute Ipoint : Boolean = false;
                                attribute mass : Real = 0.6188820525184273;
                                attribute 'σ_mass' : Real = 0.28909372274994966;
                                attribute Cx : Real = 6.707015540450811;
                                attribute 'σ_Cx' : Real = 28.721044428837228;
                                attribute Cy : Real = 12.880825670436025;
                                attribute 'σ_Cy' : Real = 28.23690002309109;
                                attribute Cz : Real = 97.8761161211878;
                                attribute 'σ_Cz' : Real = 29.057750463592832;
                                attribute Ixx : Real = 0.67995172395457;
                                attribute 'σ_Ixx' : Real = 0.37074144170588635;
                                attribute Iyy : Real = 0.7421351777093977;
                                attribute 'σ_Iyy' : Real = 0.3723953238821935;
                                attribute Izz : Real = 0.7592668371108575;
                                attribute 'σ_Izz' : Real = 0.37017423652493897;
                                attribute Ixy : Real = -0.0018951162093840594;
                                attribute 'σ_Ixy' : Real = 0.02351283871158888;
                                attribute Ixz : Real = 0.0021266837447037317;
                                attribute 'σ_Ixz' : Real = 0.022566176940390956;
                                attribute Iyz : Real = 5.1422105507893095e-5;
                                attribute 'σ_Iyz' : Real = 0.02209918015384651;
                            }
                        }
                    }
                    part <'C.1.2.3.3.3'> 'Assembly 95' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.3.3.1'> 'Subassembly 324' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.3.1.1'> 'Part 1146' {
                                attribute POIconv : String = "+";
                                attribute Ipoint : Boolean = false;
                                attribute mass : Real = 0.2156393684996292;
                                attribute 'σ_mass' : Real = 0.28909372274994966;
                                attribute Cx : Real = -25.546913500875235;
                                attribute 'σ_Cx' : Real = 28.721044428837228;
                                attribute Cy : Real = 64.04562308453023;
                                attribute 'σ_Cy' : Real = 28.23690002309109;
                                attribute Cz : Real = -11.25999167561531;
                                attribute 'σ_Cz' : Real = 29.057750463592832;
                                attribute Ixx : Real = 0.3504775645228141;
                                attribute 'σ_Ixx' : Real = 0.37074144170588635;
                                attribute Iyy : Real = 0.3529738240126634;
                                attribute 'σ_Iyy' : Real = 0.3723953238821935;
                                attribute Izz : Real = 0.353111997049998;
                                attribute 'σ_Izz' : Real = 0.37017423652493897;
                                attribute Ixy : Real = -0.001986159206998698;
                                attribute 'σ_Ixy' : Real = 0.02351283871158888;
                                attribute Ixz : Real = 0.002316887143696578;
                                attribute 'σ_Ixz' : Real = 0.022566176940390956;
                                attribute Iyz : Real = 0.0035287232705087644;
                                attribute 'σ_Iyz' : Real = 0.02209918015384651;
                            }
                            part <'C.1.2.3.3.3.1.2'> 'Part 1147' {
                                attribute POIconv : String = "-";
                                attribute Ipoint : Boolean = false;
                                attribute mass : Real = 0.1411246996978298;
                                attribute 'σ_mass' : Real = 0.28909372274994966;
                                attribute Cx : Real = 7.613337878137827;
                                attribute 'σ_Cx' : Real = 28.721044428837228;
                                attribute Cy : Real = -79.27542165853083;
                                attribute 'σ_Cy' : Real = 28.23690002309109;
                                attribute Cz : Real = 61.54035753570497;
                                attribute 'σ_Cz' : Real = 29.057750463592832;
                                attribute Ixx : Real = 0.15280759801090632;
                                attribute 'σ_Ixx' : Real = 0.37074144170588635;
                                attribute Iyy : Real = 0.16187744197611764;
                                attribute 'σ_Iyy' : Real = 0.3723953238821935;
                                attribute Izz : Real = 0.16767715003623793;
                                attribute 'σ_Izz' : Real = 0.37017423652493897;
                                attribute Ixy : Real = -0.007258785712568836;
                                attribute 'σ_Ixy' : Real = 0.02351283871158888;
                                attribute Ixz : Real = 0.005728057405915468;
                                attribute 'σ_Ixz' : Real = 0.022566176940390956;
                                attribute Iyz : Real = 0.00791151460835075;
                                attribute 'σ_Iyz' : Real = 0.02209918015384651;
                            }
                            part <'C.1.2.3.3.3.1.3'> 'Part 1148' {
                                attribute POIconv : String = "-";
                                attribute Ipoint : Boolean = false;
                                attribute mass : Real = 0.8722493939355481;
                                attribute 'σ_mass' : Real = 0.28909372274994966;
                                attribute Cx : Real = 97.95725173316896;
                                attribute 'σ_Cx' : Real = 28.721044428837228;
                                attribute Cy : Real = -28.61468056216836;
                                attribute 'σ_Cy' : Real = 28.23690002309109;
                                attribute Cz : Real = -36.694128485396504;
                                attribute 'σ_Cz' : Real = 29.057750463592832;
                                attribute Ixx : Real = 1.0627096534643206;
                                attribute 'σ_Ixx' : Real = 0.37074144170588635;
                                attribute Iyy : Real = 1.049730785370024;
                                attribute 'σ_Iyy' : Real = 0.3723953238821935;
                                attribute Izz : Real = 1.0029827838491847;
                                attribute 'σ_Izz' : Real = 0.37017423652493897;
                                attribute Ixy : Real = -0.024224760306871644;
                                attribute 'σ_Ixy' : Real = 0.02351283871158888;
                                attribute Ixz : Real = 0.007282904332993631;
                                attribute 'σ_Ixz' : Real = 0.022566176940390956;
                                attribute Iyz : Real = 0.029223677472345867;
                                attribute 'σ_Iyz' : Real = 0.02209918015384651;
                            }
                        }
                        part <'C.1.2.3.3.3.2'> 'Subassembly 325' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.3.2.1'> 'Part 1149' {
                                attribute POIconv : String = "+";
                                attribute Ipoint : Boolean = false;
                                attribute mass : Real = 0.2208638272935059;
                                attribute 'σ_mass' : Real = 0.28909372274994966;
                                attribute Cx : Real = 10.632020700722933;
                                attribute 'σ_Cx' : Real = 28.721044428837228;
                                attribute Cy : Real = -2.555057918652892;
                                attribute 'σ_Cy' : Real = 28.23690002309109;
                                attribute Cz : Real = -15.34853633493185;
                                attribute 'σ_Cz' : Real = 29.057750463592832;
                                attribute Ixx : Real = 0.25623472940078057;
                                attribute 'σ_Ixx' : Real = 0.37074144170588635;
                                attribute Iyy : Real = 0.2543089934267736;
                                attribute 'σ_Iyy' : Real = 0.3723953238821935;
                                attribute Izz : Real = 0.24507464835246398;
                                attribute 'σ_Izz' : Real = 0.37017423652493897;
                                attribute Ixy : Real = -0.027254775978169252;
                                attribute 'σ_Ixy' : Real = 0.02351283871158888;
                                attribute Ixz : Real = -0.006873905333996289;
                                attribute 'σ_Ixz' : Real = 0.022566176940390956;
                                attribute Iyz : Real = -0.006240300320748112;
                                attribute 'σ_Iyz' : Real = 0.02209918015384651;
                            }
                            part <'C.1.2.3.3.3.2.2'> 'Part 1150' {
                                attribute POIconv : String = "+";
                                attribute Ipoint : Boolean = false;
                                attribute mass : Real = 0.6474646133370697;
                                attribute 'σ_mass' : Real = 0.28909372274994966;
                                attribute Cx : Real = 83.74939523637295;
                                attribute 'σ_Cx' : Real = 28.721044428837228;
                                attribute Cy : Real = 96.9920726493001;
                                attribute 'σ_Cy' : Real = 28.23690002309109;
                                attribute Cz : Real = 64.95299804955721;
                                attribute 'σ_Cz' : Real = 29.057750463592832;
                                attribute Ixx : Real = 0.8254922846231016;
                                attribute 'σ_Ixx' : Real = 0.37074144170588635;
                                attribute Iyy : Real = 0.844809395980925;
                                attribute 'σ_Iyy' : Real = 0.3723953238821935;
                                attribute Izz : Real = 0.8651825925619495;
                                attribute 'σ_Izz' : Real = 0.37017423652493897;
                                attribute Ixy : Real = 0.041356265963219965;
                                attribute 'σ_Ixy' : Real = 0.02351283871158888;
                                attribute Ixz : Real = 0.06679462070738779;
                                attribute 'σ_Ixz' : Real = 0.022566176940390956;
                                attribute Iyz : Real = 0.052902791199776526;
                                attribute 'σ_Iyz' : Real = 0.02209918015384651;
                            }
                            part <'C.1.2.3.3.3.2.3'> 'Part 1151' {
                                attribute POIconv : String = "-";
                                attribute Ipoint : Boolean = false;
                                attribute mass : Real = 0.1998935781386681;
                                attribute 'σ_mass' : Real = 0.28909372274994966;
                                attribute Cx : Real = 9.909604350104928;
                                attribute 'σ_Cx' : Real = 28.721044428837228;
                                attribute Cy : Real = 44.56796427257359;
                                attribute 'σ_Cy' : Real = 28.23690002309109;
                                attribute Cz : Real = 5.330644641071558;
                                attribute 'σ_Cz' : Real = 29.057750463592832;
                                attribute Ixx : Real = 0.2784193769521985;
                                attribute 'σ_Ixx' : Real = 0.37074144170588635;
                                attribute Iyy : Real = 0.2864733155826442;
                                attribute 'σ_Iyy' : Real = 0.3723953238821935;
                                attribute Izz : Real = 0.27962031369374757;
                                attribute 'σ_Izz' : Real = 0.37017423652493897;
                                attribute Ixy : Real = 0.00672002298558945;
                                attribute 'σ_Ixy' : Real = 0.02351283871158888;
                                attribute Ixz : Real = -0.011263582239797319;
                                attribute 'σ_Ixz' : Real = 0.022566176940390956;
                                attribute Iyz : Real = 0.006480353309416801;
                                attribute 'σ_Iyz' : Real = 0.02209918015384651;
                            }
                            part <'C.1.2.3.3.3.2.4'> 'Part 1152' {
                                attribute POIconv : String = "+";
                                attribute Ipoint : Boolean = false;
                                attribute mass : Real = 0.23416880179732108;
                                attribute 'σ_mass' : Real = 0.28909372274994966;
                                attribute Cx : Real = 80.09221772663295;
                                attribute 'σ_Cx' : Real = 28.721044428837228;
                                attribute Cy : Real = 35.235527670010924;
                                attribute 'σ_Cy' : Real = 28.23690002309109;
                                attribute Cz : Real = -23.74124568887055;
                                attribute 'σ_Cz' : Real = 29.057750463592832;
                                attribute Ixx : Real = 0.37557168249293454;
                                attribute 'σ_Ixx' : Real = 0.37074144170588635;
                                attribute Iyy : Real = 0.37467670613590154;
                                attribute 'σ_Iyy' : Real = 0.3723953238821935;
                                attribute Izz : Real = 0.37519557994687097;
                                attribute 'σ_Izz' : Real = 0.37017423652493897;
                                attribute Ixy : Real = 8.422927412459983e-4;
                                attribute 'σ_Ixy' : Real = 0.02351283871158888;
                                attribute Ixz : Real = -1.1031047906846924e-4;
                                attribute 'σ_Ixz' : Real = 0.022566176940390956;
                                attribute Iyz : Real = -3.1105646999059666e-4;
                                attribute 'σ_Iyz' : Real = 0.02209918015384651;
                            }
                        }
                        part <'C.1.2.3.3.3.3'> 'Subassembly 326' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.3.3.1'> 'Part 1153' {
                                attribute POIconv : String = "+";
                                attribute Ipoint : Boolean = false;
                                attribute mass : Real = 0.4025493644969538;
                                attribute 'σ_mass' : Real = 0.28909372274994966;
                                attribute Cx : Real = 30.95246935263276;
                                attribute 'σ_Cx' : Real = 28.721044428837228;
                                attribute Cy : Real = -10.21992419846356;
                                attribute 'σ_Cy' : Real = 28.23690002309109;
                                attribute Cz : Real = 46.769953705370426;
                                attribute 'σ_Cz' : Real = 29.057750463592832;
                                attribute Ixx : Real = 0.4129329869864466;
                                attribute 'σ_Ixx' : Real = 0.37074144170588635;
                                attribute Iyy : Real = 0.40887155054383484;
                                attribute 'σ_Iyy' : Real = 0.3723953238821935;
                                attribute Izz : Real = 0.39672464860963186;
                                attribute 'σ_Izz' : Real = 0.37017423652493897;
                                attribute Ixy : Real = 0.008848099438941714;
                                attribute 'σ_Ixy' : Real = 0.02351283871158888;
                                attribute Ixz : Real = 0.023886103246154596;
                                attribute 'σ_Ixz' : Real = 0.022566176940390956;
                                attribute Iyz : Real = -0.019296782793598533;
                                attribute 'σ_Iyz' : Real = 0.02209918015384651;
                            }
                            part <'C.1.2.3.3.3.3.2'> 'Part 1154' {
                                attribute POIconv : String = "+";
                                attribute Ipoint : Boolean = false;
                                attribute mass : Real = 0.6444155635028146;
                                attribute 'σ_mass' : Real = 0.28909372274994966;
                                attribute Cx : Real = -65.22628706879914;
                                attribute 'σ_Cx' : Real = 28.721044428837228;
                                attribute Cy : Real = -8.016453357413411;
                                attribute 'σ_Cy' : Real = 28.23690002309109;
                                attribute Cz : Real = -90.29602380469441;
                                attribute 'σ_Cz' : Real = 29.057750463592832;
                                attribute Ixx : Real = 0.8251840899371466;
                                attribute 'σ_Ixx' : Real = 0.37074144170588635;
                                attribute Iyy : Real = 0.9534690390312993;
                                attribute 'σ_Iyy' : Real = 0.3723953238821935;
                                attribute Izz : Real = 0.7699277230808921;
                                attribute 'σ_Izz' : Real = 0.37017423652493897;
                                attribute Ixy : Real = 0.02730906174678948;
                                attribute 'σ_Ixy' : Real = 0.02351283871158888;
                                attribute Ixz : Real = -0.005660801200392538;
                                attribute 'σ_Ixz' : Real = 0.022566176940390956;
                                attribute Iyz : Real = 0.004511270369298027;
                                attribute 'σ_Iyz' : Real = 0.02209918015384651;
                            }
                            part <'C.1.2.3.3.3.3.3'> 'Part 1155' {
                                attribute POIconv : String = "+";
                                attribute Ipoint : Boolean = false;
                                attribute mass : Real = 0.0731430235800799;
                                attribute 'σ_mass' : Real = 0.28909372274994966;
                                attribute Cx : Real = -94.84316180460155;
                                attribute 'σ_Cx' : Real = 28.721044428837228;
                                attribute Cy : Real = 7.328130584210157;
                                attribute 'σ_Cy' : Real = 28.23690002309109;
                                attribute Cz : Real = -50.15052342787385;
                                attribute 'σ_Cz' : Real = 29.057750463592832;
                                attribute Ixx : Real = 0.08578797256175501;
                                attribute 'σ_Ixx' : Real = 0.37074144170588635;
                                attribute Iyy : Real = 0.09915849316591722;
                                attribute 'σ_Iyy' : Real = 0.3723953238821935;
                                attribute Izz : Real = 0.09915812951115507;
                                attribute 'σ_Izz' : Real = 0.37017423652493897;
                                attribute Ixy : Real = -0.0029198146100436594;
                                attribute 'σ_Ixy' : Real = 0.02351283871158888;
                                attribute Ixz : Real = -0.0036633529689337526;
                                attribute 'σ_Ixz' : Real = 0.022566176940390956;
                                attribute Iyz : Real = 0.001764986456764725;
                                attribute 'σ_Iyz' : Real = 0.02209918015384651;
                            }
                            part <'C.1.2.3.3.3.3.4'> 'Part 1156' {
                                attribute POIconv : String = "+";
                                attribute Ipoint : Boolean = false;
                                attribute mass : Real = 0.37710506710154007;
                                attribute 'σ_mass' : Real = 0.28909372274994966;
                                attribute Cx : Real = 70.37533391267061;
                                attribute 'σ_Cx' : Real = 28.721044428837228;
                                attribute Cy : Real = 30.54864020086825;
                                attribute 'σ_Cy' : Real = 28.23690002309109;
                                attribute Cz : Real = 32.25529328919947;
                                attribute 'σ_Cz' : Real = 29.057750463592832;
                                attribute Ixx : Real = 0.4694288870777152;
                                attribute 'σ_Ixx' : Real = 0.37074144170588635;
                                attribute Iyy : Real = 0.45596739470019015;
                                attribute 'σ_Iyy' : Real = 0.3723953238821935;
                                attribute Izz : Real = 0.46008329267883685;
                                attribute 'σ_Izz' : Real = 0.37017423652493897;
                                attribute Ixy : Real = -0.005547784278024838;
                                attribute 'σ_Ixy' : Real = 0.02351283871158888;
                                attribute Ixz : Real = 0.007970367492713386;
                                attribute 'σ_Ixz' : Real = 0.022566176940390956;
                                attribute Iyz : Real = 5.981835115231405e-4;
                                attribute 'σ_Iyz' : Real = 0.02209918015384651;
                            }
                        }
                        part <'C.1.2.3.3.3.4'> 'Subassembly 327' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.3.4.1'> 'Part 1157' {
                                attribute POIconv : String = "+";
                                attribute Ipoint : Boolean = false;
                                attribute mass : Real = 0.7336926386537962;
                                attribute 'σ_mass' : Real = 0.28909372274994966;
                                attribute Cx : Real = -95.35790062509477;
                                attribute 'σ_Cx' : Real = 28.721044428837228;
                                attribute Cy : Real = 39.57259049639106;
                                attribute 'σ_Cy' : Real = 28.23690002309109;
                                attribute Cz : Real = 7.135393423959613;
                                attribute 'σ_Cz' : Real = 29.057750463592832;
                                attribute Ixx : Real = 1.0673947738414644;
                                attribute 'σ_Ixx' : Real = 0.37074144170588635;
                                attribute Iyy : Real = 1.0609109595985258;
                                attribute 'σ_Iyy' : Real = 0.3723953238821935;
                                attribute Izz : Real = 0.9952948768670735;
                                attribute 'σ_Izz' : Real = 0.37017423652493897;
                                attribute Ixy : Real = -0.021407425297408487;
                                attribute 'σ_Ixy' : Real = 0.02351283871158888;
                                attribute Ixz : Real = -0.029490043312835112;
                                attribute 'σ_Ixz' : Real = 0.022566176940390956;
                                attribute Iyz : Real = 0.05181015072487731;
                                attribute 'σ_Iyz' : Real = 0.02209918015384651;
                            }
                            part <'C.1.2.3.3.3.4.2'> 'Part 1158' {
                                attribute POIconv : String = "+";
                                attribute Ipoint : Boolean = false;
                                attribute mass : Real = 0.5384773509327788;
                                attribute 'σ_mass' : Real = 0.28909372274994966;
                                attribute Cx : Real = 90.86621846072376;
                                attribute 'σ_Cx' : Real = 28.721044428837228;
                                attribute Cy : Real = 51.9076039083302;
                                attribute 'σ_Cy' : Real = 28.23690002309109;
                                attribute Cz : Real = -94.49823279865086;
                                attribute 'σ_Cz' : Real = 29.057750463592832;
                                attribute Ixx : Real = 0.6645092720163112;
                                attribute 'σ_Ixx' : Real = 0.37074144170588635;
                                attribute Iyy : Real = 0.5894203247511687;
                                attribute 'σ_Iyy' : Real = 0.3723953238821935;
                                attribute Izz : Real = 0.6602577003094309;
                                attribute 'σ_Izz' : Real = 0.37017423652493897;
                                attribute Ixy : Real = 0.007554306511462643;
                                attribute 'σ_Ixy' : Real = 0.02351283871158888;
                                attribute Ixz : Real = -0.061888916998248805;
                                attribute 'σ_Ixz' : Real = 0.022566176940390956;
                                attribute Iyz : Real = -0.01522748216680998;
                                attribute 'σ_Iyz' : Real = 0.02209918015384651;
                            }
                        }
                    }
                    part <'C.1.2.3.3.4'> 'Assembly 96' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.3.4.1'> 'Subassembly 328' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.4.1.1'> 'Part 1159' {
                                attribute POIconv : String = "+";
                                attribute Ipoint : Boolean = false;
                                attribute mass : Real = 0.7400061334336642;
                                attribute 'σ_mass' : Real = 0.28909372274994966;
                                attribute Cx : Real = -12.040049163624644;
                                attribute 'σ_Cx' : Real = 28.721044428837228;
                                attribute Cy : Real = -20.87032371200621;
                                attribute 'σ_Cy' : Real = 28.23690002309109;
                                attribute Cz : Real = 9.516456397250295;
                                attribute 'σ_Cz' : Real = 29.057750463592832;
                                attribute Ixx : Real = 0.8736980676978113;
                                attribute 'σ_Ixx' : Real = 0.37074144170588635;
                                attribute Iyy : Real = 0.8984059541864781;
                                attribute 'σ_Iyy' : Real = 0.3723953238821935;
                                attribute Izz : Real = 0.8272458262687516;
                                attribute 'σ_Izz' : Real = 0.37017423652493897;
                                attribute Ixy : Real = 0.05261144903563116;
                                attribute 'σ_Ixy' : Real = 0.02351283871158888;
                                attribute Ixz : Real = -0.042462779152416655;
                                attribute 'σ_Ixz' : Real = 0.022566176940390956;
                                attribute Iyz : Real = 0.03292772291785614;
                                attribute 'σ_Iyz' : Real = 0.02209918015384651;
                            }
                            part <'C.1.2.3.3.4.1.2'> 'Part 1160' {
                                attribute POIconv : String = "-";
                                attribute Ipoint : Boolean = false;
                                attribute mass : Real = 0.6371451087531168;
                                attribute 'σ_mass' : Real = 0.28909372274994966;
                                attribute Cx : Real = 76.25436382368207;
                                attribute 'σ_Cx' : Real = 28.721044428837228;
                                attribute Cy : Real = 6.33819280192256;
                                attribute 'σ_Cy' : Real = 28.23690002309109;
                                attribute Cz : Real = -33.47769808024168;
                                attribute 'σ_Cz' : Real = 29.057750463592832;
                                attribute Ixx : Real = 0.9194108974451034;
                                attribute 'σ_Ixx' : Real = 0.37074144170588635;
                                attribute Iyy : Real = 0.8882589578714308;
                                attribute 'σ_Iyy' : Real = 0.3723953238821935;
                                attribute Izz : Real = 0.8272522240211637;
                                attribute 'σ_Izz' : Real = 0.37017423652493897;
                                attribute Ixy : Real = 0.014605514666435369;
                                attribute 'σ_Ixy' : Real = 0.02351283871158888;
                                attribute Ixz : Real = 0.004397523652002532;
                                attribute 'σ_Ixz' : Real = 0.022566176940390956;
                                attribute Iyz : Real = 0.04619760827854258;
                                attribute 'σ_Iyz' : Real = 0.02209918015384651;
                            }
                            part <'C.1.2.3.3.4.1.3'> 'Part 1161' {
                                attribute POIconv : String = "+";
                                attribute Ipoint : Boolean = false;
                                attribute mass : Real = 0.9055529230181127;
                                attribute 'σ_mass' : Real = 0.28909372274994966;
                                attribute Cx : Real = -20.364547381177545;
                                attribute 'σ_Cx' : Real = 28.721044428837228;
                                attribute Cy : Real = -10.368261765688658;
                                attribute 'σ_Cy' : Real = 28.23690002309109;
                                attribute Cz : Real = 45.30077567324042;
                                attribute 'σ_Cz' : Real = 29.057750463592832;
                                attribute Ixx : Real = 1.1377331000815702;
                                attribute 'σ_Ixx' : Real = 0.37074144170588635;
                                attribute Iyy : Real = 1.0836667815234615;
                                attribute 'σ_Iyy' : Real = 0.3723953238821935;
                                attribute Izz : Real = 1.1487037806721623;
                                attribute 'σ_Izz' : Real = 0.37017423652493897;
                                attribute Ixy : Real = -0.04242739765160772;
                                attribute 'σ_Ixy' : Real = 0.02351283871158888;
                                attribute Ixz : Real = 0.05616368806906573;
                                attribute 'σ_Ixz' : Real = 0.022566176940390956;
                                attribute Iyz : Real = 0.05112533860318922;
                                attribute 'σ_Iyz' : Real = 0.02209918015384651;
                            }
                            part <'C.1.2.3.3.4.1.4'> 'Part 1162' {
                                attribute POIconv : String = "-";
                                attribute Ipoint : Boolean = false;
                                attribute mass : Real = 0.07659709179936908;
                                attribute 'σ_mass' : Real = 0.28909372274994966;
                                attribute Cx : Real = 54.52306047081947;
                                attribute 'σ_Cx' : Real = 28.721044428837228;
                                attribute Cy : Real = -88.03657772950828;
                                attribute 'σ_Cy' : Real = 28.23690002309109;
                                attribute Cz : Real = -90.6695815268904;
                                attribute 'σ_Cz' : Real = 29.057750463592832;
                                attribute Ixx : Real = 0.10147572257623734;
                                attribute 'σ_Ixx' : Real = 0.37074144170588635;
                                attribute Iyy : Real = 0.09890702791589893;
                                attribute 'σ_Iyy' : Real = 0.3723953238821935;
                                attribute Izz : Real = 0.09662101080797235;
                                attribute 'σ_Izz' : Real = 0.37017423652493897;
                                attribute Ixy : Real = -0.003850059811865432;
                                attribute 'σ_Ixy' : Real = 0.02351283871158888;
                                attribute Ixz : Real = -0.004894159244334374;
                                attribute 'σ_Ixz' : Real = 0.022566176940390956;
                                attribute Iyz : Real = -0.00534731897596152;
                                attribute 'σ_Iyz' : Real = 0.02209918015384651;
                            }
                        }
                        part <'C.1.2.3.3.4.2'> 'Subassembly 329' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.4.2.1'> 'Part 1163' {
                                attribute POIconv : String = "+";
                                attribute Ipoint : Boolean = false;
                                attribute mass : Real = 0.21082770662684924;
                                attribute 'σ_mass' : Real = 0.28909372274994966;
                                attribute Cx : Real = 69.8582960292697;
                                attribute 'σ_Cx' : Real = 28.721044428837228;
                                attribute Cy : Real = 56.49674846790731;
                                attribute 'σ_Cy' : Real = 28.23690002309109;
                                attribute Cz : Real = -76.12224486656487;
                                attribute 'σ_Cz' : Real = 29.057750463592832;
                                attribute Ixx : Real = 0.2256526384627233;
                                attribute 'σ_Ixx' : Real = 0.37074144170588635;
                                attribute Iyy : Real = 0.21901422902787354;
                                attribute 'σ_Iyy' : Real = 0.3723953238821935;
                                attribute Izz : Real = 0.22196618404322313;
                                attribute 'σ_Izz' : Real = 0.37017423652493897;
                                attribute Ixy : Real = -5.243276115298734e-4;
                                attribute 'σ_Ixy' : Real = 0.02351283871158888;
                                attribute Ixz : Real = 0.002808377481176116;
                                attribute 'σ_Ixz' : Real = 0.022566176940390956;
                                attribute Iyz : Real = -0.010564354526211142;
                                attribute 'σ_Iyz' : Real = 0.02209918015384651;
                            }
                            part <'C.1.2.3.3.4.2.2'> 'Part 1164' {
                                attribute POIconv : String = "+";
                                attribute Ipoint : Boolean = false;
                                attribute mass : Real = 0.20865075647411868;
                                attribute 'σ_mass' : Real = 0.28909372274994966;
                                attribute Cx : Real = 67.55500230938196;
                                attribute 'σ_Cx' : Real = 28.721044428837228;
                                attribute Cy : Real = 35.14960375614464;
                                attribute 'σ_Cy' : Real = 28.23690002309109;
                                attribute Cz : Real = -12.420725729316473;
                                attribute 'σ_Cz' : Real = 29.057750463592832;
                                attribute Ixx : Real = 0.2883609895685834;
                                attribute 'σ_Ixx' : Real = 0.37074144170588635;
                                attribute Iyy : Real = 0.2668000915645318;
                                attribute 'σ_Iyy' : Real = 0.3723953238821935;
                                attribute Izz : Real = 0.2836593105032307;
                                attribute 'σ_Izz' : Real = 0.37017423652493897;
                                attribute Ixy : Real = -0.00617069731588449;
                                attribute 'σ_Ixy' : Real = 0.02351283871158888;
                                attribute Ixz : Real = 0.0058078828912204485;
                                attribute 'σ_Ixz' : Real = 0.022566176940390956;
                                attribute Iyz : Real = -0.0025366101542495935;
                                attribute 'σ_Iyz' : Real = 0.02209918015384651;
                            }
                            part <'C.1.2.3.3.4.2.3'> 'Part 1165' {
                                attribute POIconv : String = "+";
                                attribute Ipoint : Boolean = false;
                                attribute mass : Real = 0.9036840868147555;
                                attribute 'σ_mass' : Real = 0.28909372274994966;
                                attribute Cx : Real = -37.714927503839135;
                                attribute 'σ_Cx' : Real = 28.721044428837228;
                                attribute Cy : Real = 33.008114295080304;
                                attribute 'σ_Cy' : Real = 28.23690002309109;
                                attribute Cz : Real = -45.969417644664645;
                                attribute 'σ_Cz' : Real = 29.057750463592832;
                                attribute Ixx : Real = 1.0490112578914066;
                                attribute 'σ_Ixx' : Real = 0.37074144170588635;
                                attribute Iyy : Real = 1.1896105585334824;
                                attribute 'σ_Iyy' : Real = 0.3723953238821935;
                                attribute Izz : Real = 1.0395761789049052;
                                attribute 'σ_Izz' : Real = 0.37017423652493897;
                                attribute Ixy : Real = 0.03880308333734295;
                                attribute 'σ_Ixy' : Real = 0.02351283871158888;
                                attribute Ixz : Real = -0.0034240903381612246;
                                attribute 'σ_Ixz' : Real = 0.022566176940390956;
                                attribute Iyz : Real = 0.005282077233799953;
                                attribute 'σ_Iyz' : Real = 0.02209918015384651;
                            }
                            part <'C.1.2.3.3.4.2.4'> 'Part 1166' {
                                attribute POIconv : String = "-";
                                attribute Ipoint : Boolean = false;
                                attribute mass : Real = 0.8923097606853116;
                                attribute 'σ_mass' : Real = 0.28909372274994966;
                                attribute Cx : Real = -71.1104148067534;
                                attribute 'σ_Cx' : Real = 28.721044428837228;
                                attribute Cy : Real = -64.32791547849774;
                                attribute 'σ_Cy' : Real = 28.23690002309109;
                                attribute Cz : Real = -35.727845365181565;
                                attribute 'σ_Cz' : Real = 29.057750463592832;
                                attribute Ixx : Real = 1.0978955725900148;
                                attribute 'σ_Ixx' : Real = 0.37074144170588635;
                                attribute Iyy : Real = 1.4156295401370689;
                                attribute 'σ_Iyy' : Real = 0.3723953238821935;
                                attribute Izz : Real = 1.1581046131238177;
                                attribute 'σ_Izz' : Real = 0.37017423652493897;
                                attribute Ixy : Real = -0.012990731430555928;
                                attribute 'σ_Ixy' : Real = 0.02351283871158888;
                                attribute Ixz : Real = -0.013012539246183279;
                                attribute 'σ_Ixz' : Real = 0.022566176940390956;
                                attribute Iyz : Real = 0.0701197318106209;
                                attribute 'σ_Iyz' : Real = 0.02209918015384651;
                            }
                            part <'C.1.2.3.3.4.2.5'> 'Part 1167' {
                                attribute POIconv : String = "+";
                                attribute Ipoint : Boolean = false;
                                attribute mass : Real = 0.2877445728383027;
                                attribute 'σ_mass' : Real = 0.28909372274994966;
                                attribute Cx : Real = 91.59461706876755;
                                attribute 'σ_Cx' : Real = 28.721044428837228;
                                attribute Cy : Real = 43.10703664086759;
                                attribute 'σ_Cy' : Real = 28.23690002309109;
                                attribute Cz : Real = 99.95293864049017;
                                attribute 'σ_Cz' : Real = 29.057750463592832;
                                attribute Ixx : Real = 0.3308934551706392;
                                attribute 'σ_Ixx' : Real = 0.37074144170588635;
                                attribute Iyy : Real = 0.31470614438608446;
                                attribute 'σ_Iyy' : Real = 0.3723953238821935;
                                attribute Izz : Real = 0.31290358849449484;
                                attribute 'σ_Izz' : Real = 0.37017423652493897;
                                attribute Ixy : Real = -0.024504422291383124;
                                attribute 'σ_Ixy' : Real = 0.02351283871158888;
                                attribute Ixz : Real = 9.465158771882105e-4;
                                attribute 'σ_Ixz' : Real = 0.022566176940390956;
                                attribute Iyz : Real = -0.003915303088483573;
                                attribute 'σ_Iyz' : Real = 0.02209918015384651;
                            }
                        }
                        part <'C.1.2.3.3.4.3'> 'Subassembly 330' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.4.3.1'> 'Part 1168' {
                                attribute POIconv : String = "+";
                                attribute Ipoint : Boolean = false;
                                attribute mass : Real = 0.5087709793595131;
                                attribute 'σ_mass' : Real = 0.28909372274994966;
                                attribute Cx : Real = 75.06642527878284;
                                attribute 'σ_Cx' : Real = 28.721044428837228;
                                attribute Cy : Real = 44.61297080852091;
                                attribute 'σ_Cy' : Real = 28.23690002309109;
                                attribute Cz : Real = -5.477722082287073;
                                attribute 'σ_Cz' : Real = 29.057750463592832;
                                attribute Ixx : Real = 0.6321992396457022;
                                attribute 'σ_Ixx' : Real = 0.37074144170588635;
                                attribute Iyy : Real = 0.6624704425798316;
                                attribute 'σ_Iyy' : Real = 0.3723953238821935;
                                attribute Izz : Real = 0.5840726066876287;
                                attribute 'σ_Izz' : Real = 0.37017423652493897;
                                attribute Ixy : Real = -0.0065827568759038195;
                                attribute 'σ_Ixy' : Real = 0.02351283871158888;
                                attribute Ixz : Real = -0.05471269287272852;
                                attribute 'σ_Ixz' : Real = 0.022566176940390956;
                                attribute Iyz : Real = 0.009373431557905815;
                                attribute 'σ_Iyz' : Real = 0.02209918015384651;
                            }
                            part <'C.1.2.3.3.4.3.2'> 'Part 1169' {
                                attribute POIconv : String = "-";
                                attribute Ipoint : Boolean = false;
                                attribute mass : Real = 0.10343382902443408;
                                attribute 'σ_mass' : Real = 0.28909372274994966;
                                attribute Cx : Real = -11.829330306500196;
                                attribute 'σ_Cx' : Real = 28.721044428837228;
                                attribute Cy : Real = 13.006323808804154;
                                attribute 'σ_Cy' : Real = 28.23690002309109;
                                attribute Cz : Real = -78.77780334092677;
                                attribute 'σ_Cz' : Real = 29.057750463592832;
                                attribute Ixx : Real = 0.12379197400861093;
                                attribute 'σ_Ixx' : Real = 0.37074144170588635;
                                attribute Iyy : Real = 0.11439372826237404;
                                attribute 'σ_Iyy' : Real = 0.3723953238821935;
                                attribute Izz : Real = 0.10929187094039318;
                                attribute 'σ_Izz' : Real = 0.37017423652493897;
                                attribute Ixy : Real = 8.44096566023753e-4;
                                attribute 'σ_Ixy' : Real = 0.02351283871158888;
                                attribute Ixz : Real = 0.006447223098256013;
                                attribute 'σ_Ixz' : Real = 0.022566176940390956;
                                attribute Iyz : Real = 0.01421954460641909;
                                attribute 'σ_Iyz' : Real = 0.02209918015384651;
                            }
                            part <'C.1.2.3.3.4.3.3'> 'Part 1170' {
                                attribute POIconv : String = "+";
                                attribute Ipoint : Boolean = false;
                                attribute mass : Real = 0.746471662517637;
                                attribute 'σ_mass' : Real = 0.28909372274994966;
                                attribute Cx : Real = -28.250183491036296;
                                attribute 'σ_Cx' : Real = 28.721044428837228;
                                attribute Cy : Real = -64.31631813757122;
                                attribute 'σ_Cy' : Real = 28.23690002309109;
                                attribute Cz : Real = 18.015751475468278;
                                attribute 'σ_Cz' : Real = 29.057750463592832;
                                attribute Ixx : Real = 0.6543642174225006;
                                attribute 'σ_Ixx' : Real = 0.37074144170588635;
                                attribute Iyy : Real = 0.7278075294922773;
                                attribute 'σ_Iyy' : Real = 0.3723953238821935;
                                attribute Izz : Real = 0.7380626975517567;
                                attribute 'σ_Izz' : Real = 0.37017423652493897;
                                attribute Ixy : Real = -0.011720419639288425;
                                attribute 'σ_Ixy' : Real = 0.02351283871158888;
                                attribute Ixz : Real = -0.020278479770480987;
                                attribute 'σ_Ixz' : Real = 0.022566176940390956;
                                attribute Iyz : Real = 0.00627879447604285;
                                attribute 'σ_Iyz' : Real = 0.02209918015384651;
                            }
                        }
                        part <'C.1.2.3.3.4.4'> 'Subassembly 331' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.4.4.1'> 'Part 1171' {
                                attribute POIconv : String = "+";
                                attribute Ipoint : Boolean = false;
                                attribute mass : Real = 0.9181259398835245;
                                attribute 'σ_mass' : Real = 0.28909372274994966;
                                attribute Cx : Real = 25.845273584127426;
                                attribute 'σ_Cx' : Real = 28.721044428837228;
                                attribute Cy : Real = 31.96282321587205;
                                attribute 'σ_Cy' : Real = 28.23690002309109;
                                attribute Cz : Real = -15.334486961364746;
                                attribute 'σ_Cz' : Real = 29.057750463592832;
                                attribute Ixx : Real = 1.225434669928097;
                                attribute 'σ_Ixx' : Real = 0.37074144170588635;
                                attribute Iyy : Real = 1.1688951140896207;
                                attribute 'σ_Iyy' : Real = 0.3723953238821935;
                                attribute Izz : Real = 1.2376403923758996;
                                attribute 'σ_Izz' : Real = 0.37017423652493897;
                                attribute Ixy : Real = -0.03155637926558796;
                                attribute 'σ_Ixy' : Real = 0.02351283871158888;
                                attribute Ixz : Real = -0.009375586480591754;
                                attribute 'σ_Ixz' : Real = 0.022566176940390956;
                                attribute Iyz : Real = 0.018458549869264082;
                                attribute 'σ_Iyz' : Real = 0.02209918015384651;
                            }
                            part <'C.1.2.3.3.4.4.2'> 'Part 1172' {
                                attribute POIconv : String = "-";
                                attribute Ipoint : Boolean = false;
                                attribute mass : Real = 0.22444754692935384;
                                attribute 'σ_mass' : Real = 0.28909372274994966;
                                attribute Cx : Real = 45.471458695828915;
                                attribute 'σ_Cx' : Real = 28.721044428837228;
                                attribute Cy : Real = 74.63137721642852;
                                attribute 'σ_Cy' : Real = 28.23690002309109;
                                attribute Cz : Real = 80.03235114738345;
                                attribute 'σ_Cz' : Real = 29.057750463592832;
                                attribute Ixx : Real = 0.33360246910305097;
                                attribute 'σ_Ixx' : Real = 0.37074144170588635;
                                attribute Iyy : Real = 0.3370219269586817;
                                attribute 'σ_Iyy' : Real = 0.3723953238821935;
                                attribute Izz : Real = 0.3402139006344269;
                                attribute 'σ_Izz' : Real = 0.37017423652493897;
                                attribute Ixy : Real = 0.0046649779491889;
                                attribute 'σ_Ixy' : Real = 0.02351283871158888;
                                attribute Ixz : Real = 0.012722194545028018;
                                attribute 'σ_Ixz' : Real = 0.022566176940390956;
                                attribute Iyz : Real = 0.001366865877167227;
                                attribute 'σ_Iyz' : Real = 0.02209918015384651;
                            }
                        }
                        part <'C.1.2.3.3.4.5'> 'Subassembly 332' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.4.5.1'> 'Part 1173' {
                                attribute POIconv : String = "-";
                                attribute Ipoint : Boolean = false;
                                attribute mass : Real = 0.955625822631875;
                                attribute 'σ_mass' : Real = 0.28909372274994966;
                                attribute Cx : Real = -80.15746069140732;
                                attribute 'σ_Cx' : Real = 28.721044428837228;
                                attribute Cy : Real = -30.156374536454678;
                                attribute 'σ_Cy' : Real = 28.23690002309109;
                                attribute Cz : Real = -12.001685472205281;
                                attribute 'σ_Cz' : Real = 29.057750463592832;
                                attribute Ixx : Real = 1.1106261429312312;
                                attribute 'σ_Ixx' : Real = 0.37074144170588635;
                                attribute Iyy : Real = 1.2485890954920487;
                                attribute 'σ_Iyy' : Real = 0.3723953238821935;
                                attribute Izz : Real = 1.2531707961635905;
                                attribute 'σ_Izz' : Real = 0.37017423652493897;
                                attribute Ixy : Real = 0.021882301753942776;
                                attribute 'σ_Ixy' : Real = 0.02351283871158888;
                                attribute Ixz : Real = -0.14712071527640036;
                                attribute 'σ_Ixz' : Real = 0.022566176940390956;
                                attribute Iyz : Real = -0.044431654822483346;
                                attribute 'σ_Iyz' : Real = 0.02209918015384651;
                            }
                            part <'C.1.2.3.3.4.5.2'> 'Part 1174' {
                                attribute POIconv : String = "+";
                                attribute Ipoint : Boolean = false;
                                attribute mass : Real = 0.545603597829584;
                                attribute 'σ_mass' : Real = 0.28909372274994966;
                                attribute Cx : Real = -86.98755013756454;
                                attribute 'σ_Cx' : Real = 28.721044428837228;
                                attribute Cy : Real = -53.339227847754955;
                                attribute 'σ_Cy' : Real = 28.23690002309109;
                                attribute Cz : Real = 56.995693407952785;
                                attribute 'σ_Cz' : Real = 29.057750463592832;
                                attribute Ixx : Real = 0.7432740273983538;
                                attribute 'σ_Ixx' : Real = 0.37074144170588635;
                                attribute Iyy : Real = 0.6576012643915549;
                                attribute 'σ_Iyy' : Real = 0.3723953238821935;
                                attribute Izz : Real = 0.7477311569063766;
                                attribute 'σ_Izz' : Real = 0.37017423652493897;
                                attribute Ixy : Real = -0.021645632840158198;
                                attribute 'σ_Ixy' : Real = 0.02351283871158888;
                                attribute Ixz : Real = 0.00549467540041061;
                                attribute 'σ_Ixz' : Real = 0.022566176940390956;
                                attribute Iyz : Real = -0.019009048199629362;
                                attribute 'σ_Iyz' : Real = 0.02209918015384651;
                            }
                            part <'C.1.2.3.3.4.5.3'> 'Part 1175' {
                                attribute POIconv : String = "+";
                                attribute Ipoint : Boolean = false;
                                attribute mass : Real = 0.15502261463995093;
                                attribute 'σ_mass' : Real = 0.28909372274994966;
                                attribute Cx : Real = 42.17293206602335;
                                attribute 'σ_Cx' : Real = 28.721044428837228;
                                attribute Cy : Real = 99.18043753132224;
                                attribute 'σ_Cy' : Real = 28.23690002309109;
                                attribute Cz : Real = 98.11067711561918;
                                attribute 'σ_Cz' : Real = 29.057750463592832;
                                attribute Ixx : Real = 0.16351896922744752;
                                attribute 'σ_Ixx' : Real = 0.37074144170588635;
                                attribute Iyy : Real = 0.15392284576391796;
                                attribute 'σ_Iyy' : Real = 0.3723953238821935;
                                attribute Izz : Real = 0.15985165412760657;
                                attribute 'σ_Izz' : Real = 0.37017423652493897;
                                attribute Ixy : Real = -4.269991105755182e-4;
                                attribute 'σ_Ixy' : Real = 0.02351283871158888;
                                attribute Ixz : Real = 3.3465252152815243e-4;
                                attribute 'σ_Ixz' : Real = 0.022566176940390956;
                                attribute Iyz : Real = -0.004964485338095095;
                                attribute 'σ_Iyz' : Real = 0.02209918015384651;
                            }
                            part <'C.1.2.3.3.4.5.4'> 'Part 1176' {
                                attribute POIconv : String = "-";
                                attribute Ipoint : Boolean = false;
                                attribute mass : Real = 0.2544909297064878;
                                attribute 'σ_mass' : Real = 0.28909372274994966;
                                attribute Cx : Real = 8.527061203494668;
                                attribute 'σ_Cx' : Real = 28.721044428837228;
                                attribute Cy : Real = -20.128681743517518;
                                attribute 'σ_Cy' : Real = 28.23690002309109;
                                attribute Cz : Real = -3.8641369435936213;
                                attribute 'σ_Cz' : Real = 29.057750463592832;
                                attribute Ixx : Real = 0.32669400680453;
                                attribute 'σ_Ixx' : Real = 0.37074144170588635;
                                attribute Iyy : Real = 0.34179922899878074;
                                attribute 'σ_Iyy' : Real = 0.3723953238821935;
                                attribute Izz : Real = 0.2769346032467346;
                                attribute 'σ_Izz' : Real = 0.37017423652493897;
                                attribute Ixy : Real = 0.01472239043269392;
                                attribute 'σ_Ixy' : Real = 0.02351283871158888;
                                attribute Ixz : Real = 0.0013145797617428556;
                                attribute 'σ_Ixz' : Real = 0.022566176940390956;
                                attribute Iyz : Real = 0.0013911618466437097;
                                attribute 'σ_Iyz' : Real = 0.02209918015384651;
                            }
                            part <'C.1.2.3.3.4.5.5'> 'Part 1177' {
                                attribute POIconv : String = "-";
                                attribute Ipoint : Boolean = false;
                                attribute mass : Real = 0.5460476461276412;
                                attribute 'σ_mass' : Real = 0.28909372274994966;
                                attribute Cx : Real = -64.96254815720022;
                                attribute 'σ_Cx' : Real = 28.721044428837228;
                                attribute Cy : Real = -57.990443939343095;
                                attribute 'σ_Cy' : Real = 28.23690002309109;
                                attribute Cz : Real = -4.131144564598799;
                                attribute 'σ_Cz' : Real = 29.057750463592832;
                                attribute Ixx : Real = 0.6982731914652558;
                                attribute 'σ_Ixx' : Real = 0.37074144170588635;
                                attribute Iyy : Real = 0.7108185963025712;
                                attribute 'σ_Iyy' : Real = 0.3723953238821935;
                                attribute Izz : Real = 0.7289567208157977;
                                attribute 'σ_Izz' : Real = 0.37017423652493897;
                                attribute Ixy : Real = -0.07980760082283507;
                                attribute 'σ_Ixy' : Real = 0.02351283871158888;
                                attribute Ixz : Real = -0.012689021004058278;
                                attribute 'σ_Ixz' : Real = 0.022566176940390956;
                                attribute Iyz : Real = 0.02523158009672751;
                                attribute 'σ_Iyz' : Real = 0.02209918015384651;
                            }
                        }
                    }
                    part <'C.1.2.3.3.5'> 'Assembly 97' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.3.5.1'> 'Subassembly 333' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.5.1.1'> 'Part 1178' {
                                attribute POIconv : String = "-";
                                attribute Ipoint : Boolean = false;
                                attribute mass : Real = 0.30423817377421075;
                                attribute 'σ_mass' : Real = 0.28909372274994966;
                                attribute Cx : Real = -91.44046362489462;
                                attribute 'σ_Cx' : Real = 28.721044428837228;
                                attribute Cy : Real = -2.6556380093097687;
                                attribute 'σ_Cy' : Real = 28.23690002309109;
                                attribute Cz : Real = 87.31230134144425;
                                attribute 'σ_Cz' : Real = 29.057750463592832;
                                attribute Ixx : Real = 0.38242099653739703;
                                attribute 'σ_Ixx' : Real = 0.37074144170588635;
                                attribute Iyy : Real = 0.386561360595014;
                                attribute 'σ_Iyy' : Real = 0.3723953238821935;
                                attribute Izz : Real = 0.37932622101010294;
                                attribute 'σ_Izz' : Real = 0.37017423652493897;
                                attribute Ixy : Real = 0.0027441751408110006;
                                attribute 'σ_Ixy' : Real = 0.02351283871158888;
                                attribute Ixz : Real = 8.645390658974968e-5;
                                attribute 'σ_Ixz' : Real = 0.022566176940390956;
                                attribute Iyz : Real = -5.326007681602408e-4;
                                attribute 'σ_Iyz' : Real = 0.02209918015384651;
                            }
                            part <'C.1.2.3.3.5.1.2'> 'Part 1179' {
                                attribute POIconv : String = "+";
                                attribute Ipoint : Boolean = false;
                                attribute mass : Real = 0.7205004568770528;
                                attribute 'σ_mass' : Real = 0.28909372274994966;
                                attribute Cx : Real = 66.49376801215112;
                                attribute 'σ_Cx' : Real = 28.721044428837228;
                                attribute Cy : Real = 8.3178854547441;
                                attribute 'σ_Cy' : Real = 28.23690002309109;
                                attribute Cz : Real = 8.983286190778017;
                                attribute 'σ_Cz' : Real = 29.057750463592832;
                                attribute Ixx : Real = 0.8260469850896712;
                                attribute 'σ_Ixx' : Real = 0.37074144170588635;
                                attribute Iyy : Real = 0.8517171435029138;
                                attribute 'σ_Iyy' : Real = 0.3723953238821935;
                                attribute Izz : Real = 0.7998987885800434;
                                attribute 'σ_Izz' : Real = 0.37017423652493897;
                                attribute Ixy : Real = -0.0025502495830517016;
                                attribute 'σ_Ixy' : Real = 0.02351283871158888;
                                attribute Ixz : Real = 0.018614973087416508;
                                attribute 'σ_Ixz' : Real = 0.022566176940390956;
                                attribute Iyz : Real = 0.007728726179584821;
                                attribute 'σ_Iyz' : Real = 0.02209918015384651;
                            }
                        }
                        part <'C.1.2.3.3.5.2'> 'Subassembly 334' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.5.2.1'> 'Part 1180' {
                                attribute POIconv : String = "+";
                                attribute Ipoint : Boolean = false;
                                attribute mass : Real = 0.43127991567412394;
                                attribute 'σ_mass' : Real = 0.28909372274994966;
                                attribute Cx : Real = -94.51196920126677;
                                attribute 'σ_Cx' : Real = 28.721044428837228;
                                attribute Cy : Real = -67.62745664454997;
                                attribute 'σ_Cy' : Real = 28.23690002309109;
                                attribute Cz : Real = -52.49585825949907;
                                attribute 'σ_Cz' : Real = 29.057750463592832;
                                attribute Ixx : Real = 0.5089482644993374;
                                attribute 'σ_Ixx' : Real = 0.37074144170588635;
                                attribute Iyy : Real = 0.5345940656523156;
                                attribute 'σ_Iyy' : Real = 0.3723953238821935;
                                attribute Izz : Real = 0.43371980639452906;
                                attribute 'σ_Izz' : Real = 0.37017423652493897;
                                attribute Ixy : Real = -0.011467873274092637;
                                attribute 'σ_Ixy' : Real = 0.02351283871158888;
                                attribute Ixz : Real = -0.0385133403477958;
                                attribute 'σ_Ixz' : Real = 0.022566176940390956;
                                attribute Iyz : Real = 0.019367090648829827;
                                attribute 'σ_Iyz' : Real = 0.02209918015384651;
                            }
                            part <'C.1.2.3.3.5.2.2'> 'Part 1181' {
                                attribute POIconv : String = "+";
                                attribute Ipoint : Boolean = false;
                                attribute mass : Real = 0.6705418300102465;
                                attribute 'σ_mass' : Real = 0.28909372274994966;
                                attribute Cx : Real = -52.5651712436229;
                                attribute 'σ_Cx' : Real = 28.721044428837228;
                                attribute Cy : Real = -16.648359829559922;
                                attribute 'σ_Cy' : Real = 28.23690002309109;
                                attribute Cz : Real = 10.222343821078539;
                                attribute 'σ_Cz' : Real = 29.057750463592832;
                                attribute Ixx : Real = 0.6882377407463639;
                                attribute 'σ_Ixx' : Real = 0.37074144170588635;
                                attribute Iyy : Real = 0.8130383945547924;
                                attribute 'σ_Iyy' : Real = 0.3723953238821935;
                                attribute Izz : Real = 0.8044460212722317;
                                attribute 'σ_Izz' : Real = 0.37017423652493897;
                                attribute Ixy : Real = -0.06758205507190732;
                                attribute 'σ_Ixy' : Real = 0.02351283871158888;
                                attribute Ixz : Real = 0.00948048436581599;
                                attribute 'σ_Ixz' : Real = 0.022566176940390956;
                                attribute Iyz : Real = -0.002577373244791746;
                                attribute 'σ_Iyz' : Real = 0.02209918015384651;
                            }
                            part <'C.1.2.3.3.5.2.3'> 'Part 1182' {
                                attribute POIconv : String = "-";
                                attribute Ipoint : Boolean = false;
                                attribute mass : Real = 0.7963612662160303;
                                attribute 'σ_mass' : Real = 0.28909372274994966;
                                attribute Cx : Real = 50.945586524903774;
                                attribute 'σ_Cx' : Real = 28.721044428837228;
                                attribute Cy : Real = 28.867764305323362;
                                attribute 'σ_Cy' : Real = 28.23690002309109;
                                attribute Cz : Real = -10.997195355594158;
                                attribute 'σ_Cz' : Real = 29.057750463592832;
                                attribute Ixx : Real = 0.9934271238119846;
                                attribute 'σ_Ixx' : Real = 0.37074144170588635;
                                attribute Iyy : Real = 0.9628380905975602;
                                attribute 'σ_Iyy' : Real = 0.3723953238821935;
                                attribute Izz : Real = 0.9137027178047246;
                                attribute 'σ_Izz' : Real = 0.37017423652493897;
                                attribute Ixy : Real = -0.027606016120134646;
                                attribute 'σ_Ixy' : Real = 0.02351283871158888;
                                attribute Ixz : Real = -0.009663652927892464;
                                attribute 'σ_Ixz' : Real = 0.022566176940390956;
                                attribute Iyz : Real = -0.018688522023214114;
                                attribute 'σ_Iyz' : Real = 0.02209918015384651;
                            }
                        }
                        part <'C.1.2.3.3.5.3'> 'Subassembly 335' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.5.3.1'> 'Part 1183' {
                                attribute POIconv : String = "-";
                                attribute Ipoint : Boolean = false;
                                attribute mass : Real = 0.15176071408181452;
                                attribute 'σ_mass' : Real = 0.28909372274994966;
                                attribute Cx : Real = -47.87710816599429;
                                attribute 'σ_Cx' : Real = 28.721044428837228;
                                attribute Cy : Real = -6.687679141759872;
                                attribute 'σ_Cy' : Real = 28.23690002309109;
                                attribute Cz : Real = 18.666162760928273;
                                attribute 'σ_Cz' : Real = 29.057750463592832;
                                attribute Ixx : Real = 0.14729331174887475;
                                attribute 'σ_Ixx' : Real = 0.37074144170588635;
                                attribute Iyy : Real = 0.1632888311960722;
                                attribute 'σ_Iyy' : Real = 0.3723953238821935;
                                attribute Izz : Real = 0.16580822073100293;
                                attribute 'σ_Izz' : Real = 0.37017423652493897;
                                attribute Ixy : Real = -0.00525362367617967;
                                attribute 'σ_Ixy' : Real = 0.02351283871158888;
                                attribute Ixz : Real = 0.003749598748022393;
                                attribute 'σ_Ixz' : Real = 0.022566176940390956;
                                attribute Iyz : Real = 0.003262346801937497;
                                attribute 'σ_Iyz' : Real = 0.02209918015384651;
                            }
                            part <'C.1.2.3.3.5.3.2'> 'Part 1184' {
                                attribute POIconv : String = "+";
                                attribute Ipoint : Boolean = false;
                                attribute mass : Real = 0.7122307940211613;
                                attribute 'σ_mass' : Real = 0.28909372274994966;
                                attribute Cx : Real = -36.32677481509745;
                                attribute 'σ_Cx' : Real = 28.721044428837228;
                                attribute Cy : Real = 22.489570593461394;
                                attribute 'σ_Cy' : Real = 28.23690002309109;
                                attribute Cz : Real = 10.23847064934671;
                                attribute 'σ_Cz' : Real = 29.057750463592832;
                                attribute Ixx : Real = 0.8893671757828507;
                                attribute 'σ_Ixx' : Real = 0.37074144170588635;
                                attribute Iyy : Real = 0.7892341138406285;
                                attribute 'σ_Iyy' : Real = 0.3723953238821935;
                                attribute Izz : Real = 0.7585659692934383;
                                attribute 'σ_Izz' : Real = 0.37017423652493897;
                                attribute Ixy : Real = -0.030936303163765357;
                                attribute 'σ_Ixy' : Real = 0.02351283871158888;
                                attribute Ixz : Real = 0.030972816081462545;
                                attribute 'σ_Ixz' : Real = 0.022566176940390956;
                                attribute Iyz : Real = 0.037887868304277136;
                                attribute 'σ_Iyz' : Real = 0.02209918015384651;
                            }
                            part <'C.1.2.3.3.5.3.3'> 'Part 1185' {
                                attribute POIconv : String = "+";
                                attribute Ipoint : Boolean = false;
                                attribute mass : Real = 0.9492864890261553;
                                attribute 'σ_mass' : Real = 0.28909372274994966;
                                attribute Cx : Real = 26.686201384291053;
                                attribute 'σ_Cx' : Real = 28.721044428837228;
                                attribute Cy : Real = 42.90138189680874;
                                attribute 'σ_Cy' : Real = 28.23690002309109;
                                attribute Cz : Real = 82.12528768926859;
                                attribute 'σ_Cz' : Real = 29.057750463592832;
                                attribute Ixx : Real = 1.3185949116024522;
                                attribute 'σ_Ixx' : Real = 0.37074144170588635;
                                attribute Iyy : Real = 1.3605636494769688;
                                attribute 'σ_Iyy' : Real = 0.3723953238821935;
                                attribute Izz : Real = 1.3700163503232434;
                                attribute 'σ_Izz' : Real = 0.37017423652493897;
                                attribute Ixy : Real = -0.001411921098397805;
                                attribute 'σ_Ixy' : Real = 0.02351283871158888;
                                attribute Ixz : Real = -5.460857876098469e-4;
                                attribute 'σ_Ixz' : Real = 0.022566176940390956;
                                attribute Iyz : Real = 0.02553685611001834;
                                attribute 'σ_Iyz' : Real = 0.02209918015384651;
                            }
                            part <'C.1.2.3.3.5.3.4'> 'Part 1186' {
                                attribute POIconv : String = "-";
                                attribute Ipoint : Boolean = false;
                                attribute mass : Real = 0.1801613999251276;
                                attribute 'σ_mass' : Real = 0.28909372274994966;
                                attribute Cx : Real = -28.705476876348257;
                                attribute 'σ_Cx' : Real = 28.721044428837228;
                                attribute Cy : Real = -42.708477610722184;
                                attribute 'σ_Cy' : Real = 28.23690002309109;
                                attribute Cz : Real = -37.684210017323494;
                                attribute 'σ_Cz' : Real = 29.057750463592832;
                                attribute Ixx : Real = 0.21981736142253447;
                                attribute 'σ_Ixx' : Real = 0.37074144170588635;
                                attribute Iyy : Real = 0.23640503568982682;
                                attribute 'σ_Iyy' : Real = 0.3723953238821935;
                                attribute Izz : Real = 0.2554400982778067;
                                attribute 'σ_Izz' : Real = 0.37017423652493897;
                                attribute Ixy : Real = -0.015605806845966425;
                                attribute 'σ_Ixy' : Real = 0.02351283871158888;
                                attribute Ixz : Real = -0.003999732426555158;
                                attribute 'σ_Ixz' : Real = 0.022566176940390956;
                                attribute Iyz : Real = 0.0011313666577094069;
                                attribute 'σ_Iyz' : Real = 0.02209918015384651;
                            }
                            part <'C.1.2.3.3.5.3.5'> 'Part 1187' {
                                attribute POIconv : String = "+";
                                attribute Ipoint : Boolean = false;
                                attribute mass : Real = 0.7467175956284627;
                                attribute 'σ_mass' : Real = 0.28909372274994966;
                                attribute Cx : Real = 61.99311059899628;
                                attribute 'σ_Cx' : Real = 28.721044428837228;
                                attribute Cy : Real = 78.22457253932953;
                                attribute 'σ_Cy' : Real = 28.23690002309109;
                                attribute Cz : Real = -65.92343943193555;
                                attribute 'σ_Cz' : Real = 29.057750463592832;
                                attribute Ixx : Real = 1.084697980021411;
                                attribute 'σ_Ixx' : Real = 0.37074144170588635;
                                attribute Iyy : Real = 1.016389021325471;
                                attribute 'σ_Iyy' : Real = 0.3723953238821935;
                                attribute Izz : Real = 1.0090557503487099;
                                attribute 'σ_Izz' : Real = 0.37017423652493897;
                                attribute Ixy : Real = 0.02941254032184017;
                                attribute 'σ_Ixy' : Real = 0.02351283871158888;
                                attribute Ixz : Real = -0.019732036770829076;
                                attribute 'σ_Ixz' : Real = 0.022566176940390956;
                                attribute Iyz : Real = -0.05544881808075673;
                                attribute 'σ_Iyz' : Real = 0.02209918015384651;
                            }
                        }
                        part <'C.1.2.3.3.5.4'> 'Subassembly 336' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.5.4.1'> 'Part 1188' {
                                attribute POIconv : String = "-";
                                attribute Ipoint : Boolean = false;
                                attribute mass : Real = 0.30652864956972187;
                                attribute 'σ_mass' : Real = 0.28909372274994966;
                                attribute Cx : Real = -50.09635570459068;
                                attribute 'σ_Cx' : Real = 28.721044428837228;
                                attribute Cy : Real = 22.151227155700326;
                                attribute 'σ_Cy' : Real = 28.23690002309109;
                                attribute Cz : Real = -69.80069228447974;
                                attribute 'σ_Cz' : Real = 29.057750463592832;
                                attribute Ixx : Real = 0.2673990657396424;
                                attribute 'σ_Ixx' : Real = 0.37074144170588635;
                                attribute Iyy : Real = 0.28143012705003834;
                                attribute 'σ_Iyy' : Real = 0.3723953238821935;
                                attribute Izz : Real = 0.2824010821572576;
                                attribute 'σ_Izz' : Real = 0.37017423652493897;
                                attribute Ixy : Real = 0.0021955986870638416;
                                attribute 'σ_Ixy' : Real = 0.02351283871158888;
                                attribute Ixz : Real = -0.0060248788326431055;
                                attribute 'σ_Ixz' : Real = 0.022566176940390956;
                                attribute Iyz : Real = 0.0021085429844813113;
                                attribute 'σ_Iyz' : Real = 0.02209918015384651;
                            }
                            part <'C.1.2.3.3.5.4.2'> 'Part 1189' {
                                attribute POIconv : String = "+";
                                attribute Ipoint : Boolean = false;
                                attribute mass : Real = 0.3564685169577133;
                                attribute 'σ_mass' : Real = 0.28909372274994966;
                                attribute Cx : Real = 87.0281957089901;
                                attribute 'σ_Cx' : Real = 28.721044428837228;
                                attribute Cy : Real = 51.38806686736643;
                                attribute 'σ_Cy' : Real = 28.23690002309109;
                                attribute Cz : Real = -99.0100737195462;
                                attribute 'σ_Cz' : Real = 29.057750463592832;
                                attribute Ixx : Real = 0.42564427308635416;
                                attribute 'σ_Ixx' : Real = 0.37074144170588635;
                                attribute Iyy : Real = 0.3901718824277889;
                                attribute 'σ_Iyy' : Real = 0.3723953238821935;
                                attribute Izz : Real = 0.3940133923018378;
                                attribute 'σ_Izz' : Real = 0.37017423652493897;
                                attribute Ixy : Real = -0.030680840415619727;
                                attribute 'σ_Ixy' : Real = 0.02351283871158888;
                                attribute Ixz : Real = 0.010308071453695848;
                                attribute 'σ_Ixz' : Real = 0.022566176940390956;
                                attribute Iyz : Real = 0.010548218201815469;
                                attribute 'σ_Iyz' : Real = 0.02209918015384651;
                            }
                            part <'C.1.2.3.3.5.4.3'> 'Part 1190' {
                                attribute POIconv : String = "-";
                                attribute Ipoint : Boolean = false;
                                attribute mass : Real = 0.8649283096198924;
                                attribute 'σ_mass' : Real = 0.28909372274994966;
                                attribute Cx : Real = -58.17913496866822;
                                attribute 'σ_Cx' : Real = 28.721044428837228;
                                attribute Cy : Real = -19.52681289985776;
                                attribute 'σ_Cy' : Real = 28.23690002309109;
                                attribute Cz : Real = 86.42389038577676;
                                attribute 'σ_Cz' : Real = 29.057750463592832;
                                attribute Ixx : Real = 0.9090796287805308;
                                attribute 'σ_Ixx' : Real = 0.37074144170588635;
                                attribute Iyy : Real = 0.971970392989424;
                                attribute 'σ_Iyy' : Real = 0.3723953238821935;
                                attribute Izz : Real = 0.9327991036545203;
                                attribute 'σ_Izz' : Real = 0.37017423652493897;
                                attribute Ixy : Real = -0.0333727449582402;
                                attribute 'σ_Ixy' : Real = 0.02351283871158888;
                                attribute Ixz : Real = 0.037570048234289735;
                                attribute 'σ_Ixz' : Real = 0.022566176940390956;
                                attribute Iyz : Real = 0.026644244251755662;
                                attribute 'σ_Iyz' : Real = 0.02209918015384651;
                            }
                            part <'C.1.2.3.3.5.4.4'> 'Part 1191' {
                                attribute POIconv : String = "+";
                                attribute Ipoint : Boolean = false;
                                attribute mass : Real = 0.8584145295151975;
                                attribute 'σ_mass' : Real = 0.28909372274994966;
                                attribute Cx : Real = 38.670690823346376;
                                attribute 'σ_Cx' : Real = 28.721044428837228;
                                attribute Cy : Real = 87.10065549239516;
                                attribute 'σ_Cy' : Real = 28.23690002309109;
                                attribute Cz : Real = 13.189571211114526;
                                attribute 'σ_Cz' : Real = 29.057750463592832;
                                attribute Ixx : Real = 1.0480924814204073;
                                attribute 'σ_Ixx' : Real = 0.37074144170588635;
                                attribute Iyy : Real = 1.0738066373458006;
                                attribute 'σ_Iyy' : Real = 0.3723953238821935;
                                attribute Izz : Real = 1.0088989081062059;
                                attribute 'σ_Izz' : Real = 0.37017423652493897;
                                attribute Ixy : Real = -0.018266017881797332;
                                attribute 'σ_Ixy' : Real = 0.02351283871158888;
                                attribute Ixz : Real = 0.024966079391719312;
                                attribute 'σ_Ixz' : Real = 0.022566176940390956;
                                attribute Iyz : Real = 0.026818487219560486;
                                attribute 'σ_Iyz' : Real = 0.02209918015384651;
                            }
                        }
                        part <'C.1.2.3.3.5.5'> 'Subassembly 337' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.3.5.5.1'> 'Part 1192' {
                                attribute POIconv : String = "-";
                                attribute Ipoint : Boolean = false;
                                attribute mass : Real = 0.9428046576266642;
                                attribute 'σ_mass' : Real = 0.28909372274994966;
                                attribute Cx : Real = 42.17588757164776;
                                attribute 'σ_Cx' : Real = 28.721044428837228;
                                attribute Cy : Real = -39.76542754098773;
                                attribute 'σ_Cy' : Real = 28.23690002309109;
                                attribute Cz : Real = -48.03979825228453;
                                attribute 'σ_Cz' : Real = 29.057750463592832;
                                attribute Ixx : Real = 1.5016593240103169;
                                attribute 'σ_Ixx' : Real = 0.37074144170588635;
                                attribute Iyy : Real = 1.4856591940433062;
                                attribute 'σ_Iyy' : Real = 0.3723953238821935;
                                attribute Izz : Real = 1.4914883729948292;
                                attribute 'σ_Izz' : Real = 0.37017423652493897;
                                attribute Ixy : Real = -0.0029911272411354776;
                                attribute 'σ_Ixy' : Real = 0.02351283871158888;
                                attribute Ixz : Real = 0.0091901297588101;
                                attribute 'σ_Ixz' : Real = 0.022566176940390956;
                                attribute Iyz : Real = 0.00747554309784382;
                                attribute 'σ_Iyz' : Real = 0.02209918015384651;
                            }
                            part <'C.1.2.3.3.5.5.2'> 'Part 1193' {
                                attribute POIconv : String = "-";
                                attribute Ipoint : Boolean = false;
                                attribute mass : Real = 0.585549096090952;
                                attribute 'σ_mass' : Real = 0.28909372274994966;
                                attribute Cx : Real = -96.35233390145004;
                                attribute 'σ_Cx' : Real = 28.721044428837228;
                                attribute Cy : Real = -65.29715922661126;
                                attribute 'σ_Cy' : Real = 28.23690002309109;
                                attribute Cz : Real = -76.59457600675523;
                                attribute 'σ_Cz' : Real = 29.057750463592832;
                                attribute Ixx : Real = 0.6676553794336636;
                                attribute 'σ_Ixx' : Real = 0.37074144170588635;
                                attribute Iyy : Real = 0.6905996315274058;
                                attribute 'σ_Iyy' : Real = 0.3723953238821935;
                                attribute Izz : Real = 0.5542419726701172;
                                attribute 'σ_Izz' : Real = 0.37017423652493897;
                                attribute Ixy : Real = 0.004805677805926533;
                                attribute 'σ_Ixy' : Real = 0.02351283871158888;
                                attribute Ixz : Real = 0.011210819131525003;
                                attribute 'σ_Ixz' : Real = 0.022566176940390956;
                                attribute Iyz : Real = -0.012690994353789543;
                                attribute 'σ_Iyz' : Real = 0.02209918015384651;
                            }
                            part <'C.1.2.3.3.5.5.3'> 'Part 1194' {
                                attribute POIconv : String = "-";
                                attribute Ipoint : Boolean = false;
                                attribute mass : Real = 0.7877497131845448;
                                attribute 'σ_mass' : Real = 0.28909372274994966;
                                attribute Cx : Real = -47.519047698006034;
                                attribute 'σ_Cx' : Real = 28.721044428837228;
                                attribute Cy : Real = 7.04563488252461;
                                attribute 'σ_Cy' : Real = 28.23690002309109;
                                attribute Cz : Real = -14.089943142607808;
                                attribute 'σ_Cz' : Real = 29.057750463592832;
                                attribute Ixx : Real = 1.070217593462583;
                                attribute 'σ_Ixx' : Real = 0.37074144170588635;
                                attribute Iyy : Real = 1.1285310651563765;
                                attribute 'σ_Iyy' : Real = 0.3723953238821935;
                                attribute Izz : Real = 1.0565678866398924;
                                attribute 'σ_Izz' : Real = 0.37017423652493897;
                                attribute Ixy : Real = -0.08852486178805327;
                                attribute 'σ_Ixy' : Real = 0.02351283871158888;
                                attribute Ixz : Real = 0.046988081763396826;
                                attribute 'σ_Ixz' : Real = 0.022566176940390956;
                                attribute Iyz : Real = -0.03055792171898878;
                                attribute 'σ_Iyz' : Real = 0.02209918015384651;
                            }
                            part <'C.1.2.3.3.5.5.4'> 'Part 1195' {
                                attribute POIconv : String = "+";
                                attribute Ipoint : Boolean = false;
                                attribute mass : Real = 0.28552112196339297;
                                attribute 'σ_mass' : Real = 0.28909372274994966;
                                attribute Cx : Real = -8.38005430996418;
                                attribute 'σ_Cx' : Real = 28.721044428837228;
                                attribute Cy : Real = 43.30366440117359;
                                attribute 'σ_Cy' : Real = 28.23690002309109;
                                attribute Cz : Real = -69.53580663539469;
                                attribute 'σ_Cz' : Real = 29.057750463592832;
                                attribute Ixx : Real = 0.31747065019210713;
                                attribute 'σ_Ixx' : Real = 0.37074144170588635;
                                attribute Iyy : Real = 0.32630019347221356;
                                attribute 'σ_Iyy' : Real = 0.3723953238821935;
                                attribute Izz : Real = 0.2859609680657334;
                                attribute 'σ_Izz' : Real = 0.37017423652493897;
                                attribute Ixy : Real = -0.010608600942390902;
                                attribute 'σ_Ixy' : Real = 0.02351283871158888;
                                attribute Ixz : Real = 0.028667899001052006;
                                attribute 'σ_Ixz' : Real = 0.022566176940390956;
                                attribute Iyz : Real = -0.01877017513384474;
                                attribute 'σ_Iyz' : Real = 0.02209918015384651;
                            }
                            part <'C.1.2.3.3.5.5.5'> 'Part 1196' {
                                attribute POIconv : String = "-";
                                attribute Ipoint : Boolean = false;
                                attribute mass : Real = 0.9312325891642831;
                                attribute 'σ_mass' : Real = 0.28909372274994966;
                                attribute Cx : Real = 69.40568634308875;
                                attribute 'σ_Cx' : Real = 28.721044428837228;
                                attribute Cy : Real = 68.70883093215525;
                                attribute 'σ_Cy' : Real = 28.23690002309109;
                                attribute Cz : Real = 84.28425122983754;
                                attribute 'σ_Cz' : Real = 29.057750463592832;
                                attribute Ixx : Real = 1.1384510280928442;
                                attribute 'σ_Ixx' : Real = 0.37074144170588635;
                                attribute Iyy : Real = 1.266617248300143;
                                attribute 'σ_Iyy' : Real = 0.3723953238821935;
                                attribute Izz : Real = 1.0806625961862404;
                                attribute 'σ_Izz' : Real = 0.37017423652493897;
                                attribute Ixy : Real = -0.03547099763743248;
                                attribute 'σ_Ixy' : Real = 0.02351283871158888;
                                attribute Ixz : Real = 0.0028423682856433853;
                                attribute 'σ_Ixz' : Real = 0.022566176940390956;
                                attribute Iyz : Real = -0.07038055531427001;
                                attribute 'σ_Iyz' : Real = 0.02209918015384651;
                            }
                        }
                    }
                }
                part <'C.1.2.3.4'> 'Subsystem 26' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.2.3.4.1'> 'Assembly 98' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.4.1.1'> 'Subassembly 338' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.4.1.1.1'> 'Part 1197' {
                                attribute POIconv : String = "+";
                                attribute Ipoint : Boolean = false;
                                attribute mass : Real = 0.23018171754688957;
                                attribute 'σ_mass' : Real = 0.28909372274994966;
                                attribute Cx : Real = 95.5246795900166;
                                attribute 'σ_Cx' : Real = 28.721044428837228;
                                attribute Cy : Real = 61.187514662742615;
                                attribute 'σ_Cy' : Real = 28.23690002309109;
                                attribute Cz : Real = 11.674417508766055;
                                attribute 'σ_Cz' : Real = 29.057750463592832;
                                attribute Ixx : Real = 0.3069745118789222;
                                attribute 'σ_Ixx' : Real = 0.37074144170588635;
                                attribute Iyy : Real = 0.31744604207443594;
                                attribute 'σ_Iyy' : Real = 0.3723953238821935;
                                attribute Izz : Real = 0.2842426748752614;
                                attribute 'σ_Izz' : Real = 0.37017423652493897;
                                attribute Ixy : Real = -0.0017517065207401897;
                                attribute 'σ_Ixy' : Real = 0.02351283871158888;
                                attribute Ixz : Real = 5.268557993259696e-5;
                                attribute 'σ_Ixz' : Real = 0.022566176940390956;
                                attribute Iyz : Real = 0.002290491340160407;
                                attribute 'σ_Iyz' : Real = 0.02209918015384651;
                            }
                            part <'C.1.2.3.4.1.1.2'> 'Part 1198' {
                                attribute POIconv : String = "-";
                                attribute Ipoint : Boolean = false;
                                attribute mass : Real = 0.6359203600841574;
                                attribute 'σ_mass' : Real = 0.28909372274994966;
                                attribute Cx : Real = 76.43651869148016;
                                attribute 'σ_Cx' : Real = 28.721044428837228;
                                attribute Cy : Real = -70.00100016593933;
                                attribute 'σ_Cy' : Real = 28.23690002309109;
                                attribute Cz : Real = -26.721250219270587;
                                attribute 'σ_Cz' : Real = 29.057750463592832;
                                attribute Ixx : Real = 0.6089424688423378;
                                attribute 'σ_Ixx' : Real = 0.37074144170588635;
                                attribute Iyy : Real = 0.6029232542657164;
                                attribute 'σ_Iyy' : Real = 0.3723953238821935;
                                attribute Izz : Real = 0.6187962497176541;
                                attribute 'σ_Izz' : Real = 0.37017423652493897;
                                attribute Ixy : Real = 0.003989223897206991;
                                attribute 'σ_Ixy' : Real = 0.02351283871158888;
                                attribute Ixz : Real = 0.0054633789357295065;
                                attribute 'σ_Ixz' : Real = 0.022566176940390956;
                                attribute Iyz : Real = 0.014061730982386188;
                                attribute 'σ_Iyz' : Real = 0.02209918015384651;
                            }
                            part <'C.1.2.3.4.1.1.3'> 'Part 1199' {
                                attribute POIconv : String = "+";
                                attribute Ipoint : Boolean = false;
                                attribute mass : Real = 0.996461322232848;
                                attribute 'σ_mass' : Real = 0.28909372274994966;
                                attribute Cx : Real = -49.709044955670834;
                                attribute 'σ_Cx' : Real = 28.721044428837228;
                                attribute Cy : Real = -70.66474366001785;
                                attribute 'σ_Cy' : Real = 28.23690002309109;
                                attribute Cz : Real = -81.71572457067668;
                                attribute 'σ_Cz' : Real = 29.057750463592832;
                                attribute Ixx : Real = 1.6295741725204236;
                                attribute 'σ_Ixx' : Real = 0.37074144170588635;
                                attribute Iyy : Real = 1.5705576093834526;
                                attribute 'σ_Iyy' : Real = 0.3723953238821935;
                                attribute Izz : Real = 1.5862381149068372;
                                attribute 'σ_Izz' : Real = 0.37017423652493897;
                                attribute Ixy : Real = 0.008185031127095163;
                                attribute 'σ_Ixy' : Real = 0.02351283871158888;
                                attribute Ixz : Real = 0.02361246937058287;
                                attribute 'σ_Ixz' : Real = 0.022566176940390956;
                                attribute Iyz : Real = -0.012441359767488645;
                                attribute 'σ_Iyz' : Real = 0.02209918015384651;
                            }
                        }
                        part <'C.1.2.3.4.1.2'> 'Subassembly 339' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.4.1.2.1'> 'Part 1200' {
                                attribute POIconv : String = "+";
                                attribute Ipoint : Boolean = false;
                                attribute mass : Real = 0.24791463754395954;
                                attribute 'σ_mass' : Real = 0.28909372274994966;
                                attribute Cx : Real = -6.434924015775323;
                                attribute 'σ_Cx' : Real = 28.721044428837228;
                                attribute Cy : Real = 69.44263693876565;
                                attribute 'σ_Cy' : Real = 28.23690002309109;
                                attribute Cz : Real = -59.38496878370643;
                                attribute 'σ_Cz' : Real = 29.057750463592832;
                                attribute Ixx : Real = 0.30408178827658733;
                                attribute 'σ_Ixx' : Real = 0.37074144170588635;
                                attribute Iyy : Real = 0.27296056539851027;
                                attribute 'σ_Iyy' : Real = 0.3723953238821935;
                                attribute Izz : Real = 0.305565162131866;
                                attribute 'σ_Izz' : Real = 0.37017423652493897;
                                attribute Ixy : Real = 0.026278982918982823;
                                attribute 'σ_Ixy' : Real = 0.02351283871158888;
                                attribute Ixz : Real = -0.008359360133204959;
                                attribute 'σ_Ixz' : Real = 0.022566176940390956;
                                attribute Iyz : Real = -0.004857278496176114;
                                attribute 'σ_Iyz' : Real = 0.02209918015384651;
                            }
                            part <'C.1.2.3.4.1.2.2'> 'Part 1201' {
                                attribute POIconv : String = "+";
                                attribute Ipoint : Boolean = false;
                                attribute mass : Real = 0.5133475823018234;
                                attribute 'σ_mass' : Real = 0.28909372274994966;
                                attribute Cx : Real = 46.79508386179805;
                                attribute 'σ_Cx' : Real = 28.721044428837228;
                                attribute Cy : Real = -73.16190833225846;
                                attribute 'σ_Cy' : Real = 28.23690002309109;
                                attribute Cz : Real = 95.17118851654232;
                                attribute 'σ_Cz' : Real = 29.057750463592832;
                                attribute Ixx : Real = 0.715867958016512;
                                attribute 'σ_Ixx' : Real = 0.37074144170588635;
                                attribute Iyy : Real = 0.7125286319649866;
                                attribute 'σ_Iyy' : Real = 0.3723953238821935;
                                attribute Izz : Real = 0.6832705343005893;
                                attribute 'σ_Izz' : Real = 0.37017423652493897;
                                attribute Ixy : Real = 0.017785012597743538;
                                attribute 'σ_Ixy' : Real = 0.02351283871158888;
                                attribute Ixz : Real = 0.009670737119423515;
                                attribute 'σ_Ixz' : Real = 0.022566176940390956;
                                attribute Iyz : Real = -0.013902577959321566;
                                attribute 'σ_Iyz' : Real = 0.02209918015384651;
                            }
                            part <'C.1.2.3.4.1.2.3'> 'Part 1202' {
                                attribute POIconv : String = "+";
                                attribute Ipoint : Boolean = false;
                                attribute mass : Real = 0.4610459090447985;
                                attribute 'σ_mass' : Real = 0.28909372274994966;
                                attribute Cx : Real = 54.372142907232046;
                                attribute 'σ_Cx' : Real = 28.721044428837228;
                                attribute Cy : Real = 58.3932017441839;
                                attribute 'σ_Cy' : Real = 28.23690002309109;
                                attribute Cz : Real = 28.444060077890754;
                                attribute 'σ_Cz' : Real = 29.057750463592832;
                                attribute Ixx : Real = 0.4639649931737143;
                                attribute 'σ_Ixx' : Real = 0.37074144170588635;
                                attribute Iyy : Real = 0.4647832601030392;
                                attribute 'σ_Iyy' : Real = 0.3723953238821935;
                                attribute Izz : Real = 0.5081465023688937;
                                attribute 'σ_Izz' : Real = 0.37017423652493897;
                                attribute Ixy : Real = -0.005759403203507457;
                                attribute 'σ_Ixy' : Real = 0.02351283871158888;
                                attribute Ixz : Real = -8.844889951697874e-4;
                                attribute 'σ_Ixz' : Real = 0.022566176940390956;
                                attribute Iyz : Real = -8.495170848509825e-4;
                                attribute 'σ_Iyz' : Real = 0.02209918015384651;
                            }
                        }
                        part <'C.1.2.3.4.1.3'> 'Subassembly 340' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.4.1.3.1'> 'Part 1203' {
                                attribute POIconv : String = "+";
                                attribute Ipoint : Boolean = false;
                                attribute mass : Real = 0.1624557269010693;
                                attribute 'σ_mass' : Real = 0.28909372274994966;
                                attribute Cx : Real = 11.05682710185647;
                                attribute 'σ_Cx' : Real = 28.721044428837228;
                                attribute Cy : Real = -95.06013114005327;
                                attribute 'σ_Cy' : Real = 28.23690002309109;
                                attribute Cz : Real = -27.754372963681817;
                                attribute 'σ_Cz' : Real = 29.057750463592832;
                                attribute Ixx : Real = 0.21477369924159126;
                                attribute 'σ_Ixx' : Real = 0.37074144170588635;
                                attribute Iyy : Real = 0.22027546416693852;
                                attribute 'σ_Iyy' : Real = 0.3723953238821935;
                                attribute Izz : Real = 0.19791697571173067;
                                attribute 'σ_Izz' : Real = 0.37017423652493897;
                                attribute Ixy : Real = -1.6067511720010313e-4;
                                attribute 'σ_Ixy' : Real = 0.02351283871158888;
                                attribute Ixz : Real = -0.010071054849285995;
                                attribute 'σ_Ixz' : Real = 0.022566176940390956;
                                attribute Iyz : Real = -6.930712087562078e-4;
                                attribute 'σ_Iyz' : Real = 0.02209918015384651;
                            }
                            part <'C.1.2.3.4.1.3.2'> 'Part 1204' {
                                attribute POIconv : String = "+";
                                attribute Ipoint : Boolean = false;
                                attribute mass : Real = 0.05097084034536965;
                                attribute 'σ_mass' : Real = 0.28909372274994966;
                                attribute Cx : Real = 87.67452016472816;
                                attribute 'σ_Cx' : Real = 28.721044428837228;
                                attribute Cy : Real = 19.559049466624856;
                                attribute 'σ_Cy' : Real = 28.23690002309109;
                                attribute Cz : Real = 51.411914359778166;
                                attribute 'σ_Cz' : Real = 29.057750463592832;
                                attribute Ixx : Real = 0.05850068915165696;
                                attribute 'σ_Ixx' : Real = 0.37074144170588635;
                                attribute Iyy : Real = 0.0473749776713285;
                                attribute 'σ_Iyy' : Real = 0.3723953238821935;
                                attribute Izz : Real = 0.058831512975141484;
                                attribute 'σ_Izz' : Real = 0.37017423652493897;
                                attribute Ixy : Real = 0.0015162668333161418;
                                attribute 'σ_Ixy' : Real = 0.02351283871158888;
                                attribute Ixz : Real = -4.681152694180767e-4;
                                attribute 'σ_Ixz' : Real = 0.022566176940390956;
                                attribute Iyz : Real = 0.0036207800377799073;
                                attribute 'σ_Iyz' : Real = 0.02209918015384651;
                            }
                            part <'C.1.2.3.4.1.3.3'> 'Part 1205' {
                                attribute POIconv : String = "+";
                                attribute Ipoint : Boolean = false;
                                attribute mass : Real = 0.5936982488569338;
                                attribute 'σ_mass' : Real = 0.28909372274994966;
                                attribute Cx : Real = -31.96576596237719;
                                attribute 'σ_Cx' : Real = 28.721044428837228;
                                attribute Cy : Real = -81.68279565870762;
                                attribute 'σ_Cy' : Real = 28.23690002309109;
                                attribute Cz : Real = -31.912634382024407;
                                attribute 'σ_Cz' : Real = 29.057750463592832;
                                attribute Ixx : Real = 0.7103963088838084;
                                attribute 'σ_Ixx' : Real = 0.37074144170588635;
                                attribute Iyy : Real = 0.7123187970002711;
                                attribute 'σ_Iyy' : Real = 0.3723953238821935;
                                attribute Izz : Real = 0.6744500804816671;
                                attribute 'σ_Izz' : Real = 0.37017423652493897;
                                attribute Ixy : Real = -0.03308433945396749;
                                attribute 'σ_Ixy' : Real = 0.02351283871158888;
                                attribute Ixz : Real = -0.006865272574987081;
                                attribute 'σ_Ixz' : Real = 0.022566176940390956;
                                attribute Iyz : Real = -0.002164742475760066;
                                attribute 'σ_Iyz' : Real = 0.02209918015384651;
                            }
                        }
                        part <'C.1.2.3.4.1.4'> 'Subassembly 341' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.4.1.4.1'> 'Part 1206' {
                                attribute POIconv : String = "-";
                                attribute Ipoint : Boolean = false;
                                attribute mass : Real = 0.31053965022508057;
                                attribute 'σ_mass' : Real = 0.28909372274994966;
                                attribute Cx : Real = 82.16296834871173;
                                attribute 'σ_Cx' : Real = 28.721044428837228;
                                attribute Cy : Real = -86.53600011020899;
                                attribute 'σ_Cy' : Real = 28.23690002309109;
                                attribute Cz : Real = 83.69044973514974;
                                attribute 'σ_Cz' : Real = 29.057750463592832;
                                attribute Ixx : Real = 0.4079048880869448;
                                attribute 'σ_Ixx' : Real = 0.37074144170588635;
                                attribute Iyy : Real = 0.4047036148068717;
                                attribute 'σ_Iyy' : Real = 0.3723953238821935;
                                attribute Izz : Real = 0.3969730315135618;
                                attribute 'σ_Izz' : Real = 0.37017423652493897;
                                attribute Ixy : Real = -0.010514561044438549;
                                attribute 'σ_Ixy' : Real = 0.02351283871158888;
                                attribute Ixz : Real = -0.014689737737081814;
                                attribute 'σ_Ixz' : Real = 0.022566176940390956;
                                attribute Iyz : Real = -0.018116262146247918;
                                attribute 'σ_Iyz' : Real = 0.02209918015384651;
                            }
                            part <'C.1.2.3.4.1.4.2'> 'Part 1207' {
                                attribute POIconv : String = "-";
                                attribute Ipoint : Boolean = false;
                                attribute mass : Real = 0.49811331197991965;
                                attribute 'σ_mass' : Real = 0.28909372274994966;
                                attribute Cx : Real = 20.360221806913614;
                                attribute 'σ_Cx' : Real = 28.721044428837228;
                                attribute Cy : Real = 48.02275183610618;
                                attribute 'σ_Cy' : Real = 28.23690002309109;
                                attribute Cz : Real = 1.006604265421629;
                                attribute 'σ_Cz' : Real = 29.057750463592832;
                                attribute Ixx : Real = 0.5984804433932001;
                                attribute 'σ_Ixx' : Real = 0.37074144170588635;
                                attribute Iyy : Real = 0.5752190953439233;
                                attribute 'σ_Iyy' : Real = 0.3723953238821935;
                                attribute Izz : Real = 0.6300229557218794;
                                attribute 'σ_Izz' : Real = 0.37017423652493897;
                                attribute Ixy : Real = -0.04374052153113046;
                                attribute 'σ_Ixy' : Real = 0.02351283871158888;
                                attribute Ixz : Real = 0.009637759466288764;
                                attribute 'σ_Ixz' : Real = 0.022566176940390956;
                                attribute Iyz : Real = -0.02597242703731132;
                                attribute 'σ_Iyz' : Real = 0.02209918015384651;
                            }
                            part <'C.1.2.3.4.1.4.3'> 'Part 1208' {
                                attribute POIconv : String = "-";
                                attribute Ipoint : Boolean = false;
                                attribute mass : Real = 0.11268071484123357;
                                attribute 'σ_mass' : Real = 0.28909372274994966;
                                attribute Cx : Real = -81.21525156311691;
                                attribute 'σ_Cx' : Real = 28.721044428837228;
                                attribute Cy : Real = -13.229603786021471;
                                attribute 'σ_Cy' : Real = 28.23690002309109;
                                attribute Cz : Real = 64.56721709109843;
                                attribute 'σ_Cz' : Real = 29.057750463592832;
                                attribute Ixx : Real = 0.1564561731672315;
                                attribute 'σ_Ixx' : Real = 0.37074144170588635;
                                attribute Iyy : Real = 0.12706718029504815;
                                attribute 'σ_Iyy' : Real = 0.3723953238821935;
                                attribute Izz : Real = 0.12985450859143252;
                                attribute 'σ_Izz' : Real = 0.37017423652493897;
                                attribute Ixy : Real = 0.005109733356001928;
                                attribute 'σ_Ixy' : Real = 0.02351283871158888;
                                attribute Ixz : Real = -0.001743523363976774;
                                attribute 'σ_Ixz' : Real = 0.022566176940390956;
                                attribute Iyz : Real = 5.201249573662269e-4;
                                attribute 'σ_Iyz' : Real = 0.02209918015384651;
                            }
                            part <'C.1.2.3.4.1.4.4'> 'Part 1209' {
                                attribute POIconv : String = "-";
                                attribute Ipoint : Boolean = false;
                                attribute mass : Real = 0.6608180928584189;
                                attribute 'σ_mass' : Real = 0.28909372274994966;
                                attribute Cx : Real = 11.376993404701352;
                                attribute 'σ_Cx' : Real = 28.721044428837228;
                                attribute Cy : Real = 44.547165324911475;
                                attribute 'σ_Cy' : Real = 28.23690002309109;
                                attribute Cz : Real = -96.19570393115282;
                                attribute 'σ_Cz' : Real = 29.057750463592832;
                                attribute Ixx : Real = 0.667427557780151;
                                attribute 'σ_Ixx' : Real = 0.37074144170588635;
                                attribute Iyy : Real = 0.8490477648961487;
                                attribute 'σ_Iyy' : Real = 0.3723953238821935;
                                attribute Izz : Real = 0.8200092016943944;
                                attribute 'σ_Izz' : Real = 0.37017423652493897;
                                attribute Ixy : Real = -0.031284423792082267;
                                attribute 'σ_Ixy' : Real = 0.02351283871158888;
                                attribute Ixz : Real = -0.03570983146907562;
                                attribute 'σ_Ixz' : Real = 0.022566176940390956;
                                attribute Iyz : Real = -0.008300927296662545;
                                attribute 'σ_Iyz' : Real = 0.02209918015384651;
                            }
                            part <'C.1.2.3.4.1.4.5'> 'Part 1210' {
                                attribute POIconv : String = "-";
                                attribute Ipoint : Boolean = false;
                                attribute mass : Real = 0.8685719280771446;
                                attribute 'σ_mass' : Real = 0.28909372274994966;
                                attribute Cx : Real = 40.143382688984275;
                                attribute 'σ_Cx' : Real = 28.721044428837228;
                                attribute Cy : Real = -24.273137748241425;
                                attribute 'σ_Cy' : Real = 28.23690002309109;
                                attribute Cz : Real = -66.32394045591354;
                                attribute 'σ_Cz' : Real = 29.057750463592832;
                                attribute Ixx : Real = 1.1325989543113293;
                                attribute 'σ_Ixx' : Real = 0.37074144170588635;
                                attribute Iyy : Real = 1.1793036439015683;
                                attribute 'σ_Iyy' : Real = 0.3723953238821935;
                                attribute Izz : Real = 1.1874154851252992;
                                attribute 'σ_Izz' : Real = 0.37017423652493897;
                                attribute Ixy : Real = 0.01116998637174376;
                                attribute 'σ_Ixy' : Real = 0.02351283871158888;
                                attribute Ixz : Real = 0.007753968223140213;
                                attribute 'σ_Ixz' : Real = 0.022566176940390956;
                                attribute Iyz : Real = -2.1081693427738328e-4;
                                attribute 'σ_Iyz' : Real = 0.02209918015384651;
                            }
                        }
                        part <'C.1.2.3.4.1.5'> 'Subassembly 342' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.4.1.5.1'> 'Part 1211' {
                                attribute POIconv : String = "-";
                                attribute Ipoint : Boolean = false;
                                attribute mass : Real = 0.9253771292541642;
                                attribute 'σ_mass' : Real = 0.28909372274994966;
                                attribute Cx : Real = -28.540639532729983;
                                attribute 'σ_Cx' : Real = 28.721044428837228;
                                attribute Cy : Real = -95.02116250805557;
                                attribute 'σ_Cy' : Real = 28.23690002309109;
                                attribute Cz : Real = -38.96304341033101;
                                attribute 'σ_Cz' : Real = 29.057750463592832;
                                attribute Ixx : Real = 1.0252569865246104;
                                attribute 'σ_Ixx' : Real = 0.37074144170588635;
                                attribute Iyy : Real = 0.9229744478406416;
                                attribute 'σ_Iyy' : Real = 0.3723953238821935;
                                attribute Izz : Real = 1.045445330723407;
                                attribute 'σ_Izz' : Real = 0.37017423652493897;
                                attribute Ixy : Real = 0.02305420714401632;
                                attribute 'σ_Ixy' : Real = 0.02351283871158888;
                                attribute Ixz : Real = 0.004392272488573504;
                                attribute 'σ_Ixz' : Real = 0.022566176940390956;
                                attribute Iyz : Real = -0.05310164370673251;
                                attribute 'σ_Iyz' : Real = 0.02209918015384651;
                            }
                            part <'C.1.2.3.4.1.5.2'> 'Part 1212' {
                                attribute POIconv : String = "+";
                                attribute Ipoint : Boolean = false;
                                attribute mass : Real = 0.45486251785163767;
                                attribute 'σ_mass' : Real = 0.28909372274994966;
                                attribute Cx : Real = -71.5090564917773;
                                attribute 'σ_Cx' : Real = 28.721044428837228;
                                attribute Cy : Real = -73.38967970572412;
                                attribute 'σ_Cy' : Real = 28.23690002309109;
                                attribute Cz : Real = 70.67902246490121;
                                attribute 'σ_Cz' : Real = 29.057750463592832;
                                attribute Ixx : Real = 0.5514238221369002;
                                attribute 'σ_Ixx' : Real = 0.37074144170588635;
                                attribute Iyy : Real = 0.5024478682098392;
                                attribute 'σ_Iyy' : Real = 0.3723953238821935;
                                attribute Izz : Real = 0.5572153127795414;
                                attribute 'σ_Izz' : Real = 0.37017423652493897;
                                attribute Ixy : Real = -0.05230570696090774;
                                attribute 'σ_Ixy' : Real = 0.02351283871158888;
                                attribute Ixz : Real = -0.04305566859936216;
                                attribute 'σ_Ixz' : Real = 0.022566176940390956;
                                attribute Iyz : Real = 0.058557911928675585;
                                attribute 'σ_Iyz' : Real = 0.02209918015384651;
                            }
                            part <'C.1.2.3.4.1.5.3'> 'Part 1213' {
                                attribute POIconv : String = "+";
                                attribute Ipoint : Boolean = false;
                                attribute mass : Real = 0.9754483755626716;
                                attribute 'σ_mass' : Real = 0.28909372274994966;
                                attribute Cx : Real = -51.88042349182069;
                                attribute 'σ_Cx' : Real = 28.721044428837228;
                                attribute Cy : Real = -26.834622118622065;
                                attribute 'σ_Cy' : Real = 28.23690002309109;
                                attribute Cz : Real = 52.94147925451398;
                                attribute 'σ_Cz' : Real = 29.057750463592832;
                                attribute Ixx : Real = 1.1983844929711078;
                                attribute 'σ_Ixx' : Real = 0.37074144170588635;
                                attribute Iyy : Real = 1.1612650039841859;
                                attribute 'σ_Iyy' : Real = 0.3723953238821935;
                                attribute Izz : Real = 1.3067747228430784;
                                attribute 'σ_Izz' : Real = 0.37017423652493897;
                                attribute Ixy : Real = 0.0022367138590890334;
                                attribute 'σ_Ixy' : Real = 0.02351283871158888;
                                attribute Ixz : Real = 0.06018785323751287;
                                attribute 'σ_Ixz' : Real = 0.022566176940390956;
                                attribute Iyz : Real = -0.014070412968562263;
                                attribute 'σ_Iyz' : Real = 0.02209918015384651;
                            }
                            part <'C.1.2.3.4.1.5.4'> 'Part 1214' {
                                attribute POIconv : String = "+";
                                attribute Ipoint : Boolean = false;
                                attribute mass : Real = 0.6336292925598099;
                                attribute 'σ_mass' : Real = 0.28909372274994966;
                                attribute Cx : Real = -56.30812807939947;
                                attribute 'σ_Cx' : Real = 28.721044428837228;
                                attribute Cy : Real = -20.049495808780193;
                                attribute 'σ_Cy' : Real = 28.23690002309109;
                                attribute Cz : Real = -7.245758501812816;
                                attribute 'σ_Cz' : Real = 29.057750463592832;
                                attribute Ixx : Real = 0.8636118697043312;
                                attribute 'σ_Ixx' : Real = 0.37074144170588635;
                                attribute Iyy : Real = 0.8661840310807734;
                                attribute 'σ_Iyy' : Real = 0.3723953238821935;
                                attribute Izz : Real = 0.8793129906532933;
                                attribute 'σ_Izz' : Real = 0.37017423652493897;
                                attribute Ixy : Real = 0.003248584527473052;
                                attribute 'σ_Ixy' : Real = 0.02351283871158888;
                                attribute Ixz : Real = -0.009569388216360506;
                                attribute 'σ_Ixz' : Real = 0.022566176940390956;
                                attribute Iyz : Real = 0.019240501890227;
                                attribute 'σ_Iyz' : Real = 0.02209918015384651;
                            }
                        }
                    }
                    part <'C.1.2.3.4.2'> 'Assembly 99' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.4.2.1'> 'Subassembly 343' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.4.2.1.1'> 'Part 1215' {
                                attribute POIconv : String = "-";
                                attribute Ipoint : Boolean = false;
                                attribute mass : Real = 0.14018993839807808;
                                attribute 'σ_mass' : Real = 0.28909372274994966;
                                attribute Cx : Real = -45.284552266821265;
                                attribute 'σ_Cx' : Real = 28.721044428837228;
                                attribute Cy : Real = 89.37675203196704;
                                attribute 'σ_Cy' : Real = 28.23690002309109;
                                attribute Cz : Real = 24.78629555553198;
                                attribute 'σ_Cz' : Real = 29.057750463592832;
                                attribute Ixx : Real = 0.1744797053004497;
                                attribute 'σ_Ixx' : Real = 0.37074144170588635;
                                attribute Iyy : Real = 0.17509864320516141;
                                attribute 'σ_Iyy' : Real = 0.3723953238821935;
                                attribute Izz : Real = 0.1784922198168826;
                                attribute 'σ_Izz' : Real = 0.37017423652493897;
                                attribute Ixy : Real = 2.647897538149731e-4;
                                attribute 'σ_Ixy' : Real = 0.02351283871158888;
                                attribute Ixz : Real = -0.002589744232280417;
                                attribute 'σ_Ixz' : Real = 0.022566176940390956;
                                attribute Iyz : Real = 8.030236557246436e-4;
                                attribute 'σ_Iyz' : Real = 0.02209918015384651;
                            }
                            part <'C.1.2.3.4.2.1.2'> 'Part 1216' {
                                attribute POIconv : String = "+";
                                attribute Ipoint : Boolean = false;
                                attribute mass : Real = 0.7928675107622984;
                                attribute 'σ_mass' : Real = 0.28909372274994966;
                                attribute Cx : Real = 4.040313791483641;
                                attribute 'σ_Cx' : Real = 28.721044428837228;
                                attribute Cy : Real = 3.4724437166005373;
                                attribute 'σ_Cy' : Real = 28.23690002309109;
                                attribute Cz : Real = 35.18093270249665;
                                attribute 'σ_Cz' : Real = 29.057750463592832;
                                attribute Ixx : Real = 0.9577415870941725;
                                attribute 'σ_Ixx' : Real = 0.37074144170588635;
                                attribute Iyy : Real = 1.0402156415950787;
                                attribute 'σ_Iyy' : Real = 0.3723953238821935;
                                attribute Izz : Real = 0.9765896306246936;
                                attribute 'σ_Izz' : Real = 0.37017423652493897;
                                attribute Ixy : Real = -0.04703818005083778;
                                attribute 'σ_Ixy' : Real = 0.02351283871158888;
                                attribute Ixz : Real = -0.006281842424107953;
                                attribute 'σ_Ixz' : Real = 0.022566176940390956;
                                attribute Iyz : Real = -0.024303674803286247;
                                attribute 'σ_Iyz' : Real = 0.02209918015384651;
                            }
                            part <'C.1.2.3.4.2.1.3'> 'Part 1217' {
                                attribute POIconv : String = "+";
                                attribute Ipoint : Boolean = false;
                                attribute mass : Real = 0.9245441264738329;
                                attribute 'σ_mass' : Real = 0.28909372274994966;
                                attribute Cx : Real = 26.067066425457597;
                                attribute 'σ_Cx' : Real = 28.721044428837228;
                                attribute Cy : Real = -4.1976196225732565;
                                attribute 'σ_Cy' : Real = 28.23690002309109;
                                attribute Cz : Real = 36.482014786452055;
                                attribute 'σ_Cz' : Real = 29.057750463592832;
                                attribute Ixx : Real = 1.0852840923621443;
                                attribute 'σ_Ixx' : Real = 0.37074144170588635;
                                attribute Iyy : Real = 1.2421879160354485;
                                attribute 'σ_Iyy' : Real = 0.3723953238821935;
                                attribute Izz : Real = 1.0625009303747057;
                                attribute 'σ_Izz' : Real = 0.37017423652493897;
                                attribute Ixy : Real = -0.09720429671983283;
                                attribute 'σ_Ixy' : Real = 0.02351283871158888;
                                attribute Ixz : Real = 0.005432631705803893;
                                attribute 'σ_Ixz' : Real = 0.022566176940390956;
                                attribute Iyz : Real = 0.011272388517156107;
                                attribute 'σ_Iyz' : Real = 0.02209918015384651;
                            }
                            part <'C.1.2.3.4.2.1.4'> 'Part 1218' {
                                attribute POIconv : String = "-";
                                attribute Ipoint : Boolean = false;
                                attribute mass : Real = 0.5518453717716039;
                                attribute 'σ_mass' : Real = 0.28909372274994966;
                                attribute Cx : Real = 47.53809990361333;
                                attribute 'σ_Cx' : Real = 28.721044428837228;
                                attribute Cy : Real = -79.64953398332;
                                attribute 'σ_Cy' : Real = 28.23690002309109;
                                attribute Cz : Real = -59.963800152763724;
                                attribute 'σ_Cz' : Real = 29.057750463592832;
                                attribute Ixx : Real = 0.7960976542480551;
                                attribute 'σ_Ixx' : Real = 0.37074144170588635;
                                attribute Iyy : Real = 0.6601283153450173;
                                attribute 'σ_Iyy' : Real = 0.3723953238821935;
                                attribute Izz : Real = 0.771462029499174;
                                attribute 'σ_Izz' : Real = 0.37017423652493897;
                                attribute Ixy : Real = 0.0064732761073713315;
                                attribute 'σ_Ixy' : Real = 0.02351283871158888;
                                attribute Ixz : Real = 1.370927398551994e-4;
                                attribute 'σ_Ixz' : Real = 0.022566176940390956;
                                attribute Iyz : Real = 0.0056868588587633915;
                                attribute 'σ_Iyz' : Real = 0.02209918015384651;
                            }
                        }
                        part <'C.1.2.3.4.2.2'> 'Subassembly 344' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.4.2.2.1'> 'Part 1219' {
                                attribute POIconv : String = "+";
                                attribute Ipoint : Boolean = false;
                                attribute mass : Real = 0.7624184520461131;
                                attribute 'σ_mass' : Real = 0.28909372274994966;
                                attribute Cx : Real = -71.00615780800581;
                                attribute 'σ_Cx' : Real = 28.721044428837228;
                                attribute Cy : Real = -55.46005740761757;
                                attribute 'σ_Cy' : Real = 28.23690002309109;
                                attribute Cz : Real = -22.927511716261506;
                                attribute 'σ_Cz' : Real = 29.057750463592832;
                                attribute Ixx : Real = 1.0095357094737216;
                                attribute 'σ_Ixx' : Real = 0.37074144170588635;
                                attribute Iyy : Real = 1.1377047745366777;
                                attribute 'σ_Iyy' : Real = 0.3723953238821935;
                                attribute Izz : Real = 1.0601915514187823;
                                attribute 'σ_Izz' : Real = 0.37017423652493897;
                                attribute Ixy : Real = 0.02556427045370066;
                                attribute 'σ_Ixy' : Real = 0.02351283871158888;
                                attribute Ixz : Real = 0.006520758893302737;
                                attribute 'σ_Ixz' : Real = 0.022566176940390956;
                                attribute Iyz : Real = 0.038324921894748065;
                                attribute 'σ_Iyz' : Real = 0.02209918015384651;
                            }
                            part <'C.1.2.3.4.2.2.2'> 'Part 1220' {
                                attribute POIconv : String = "-";
                                attribute Ipoint : Boolean = false;
                                attribute mass : Real = 0.14356255016545766;
                                attribute 'σ_mass' : Real = 0.28909372274994966;
                                attribute Cx : Real = 88.90291755087674;
                                attribute 'σ_Cx' : Real = 28.721044428837228;
                                attribute Cy : Real = 57.48446565121412;
                                attribute 'σ_Cy' : Real = 28.23690002309109;
                                attribute Cz : Real = -17.33270059339702;
                                attribute 'σ_Cz' : Real = 29.057750463592832;
                                attribute Ixx : Real = 0.13944234729379065;
                                attribute 'σ_Ixx' : Real = 0.37074144170588635;
                                attribute Iyy : Real = 0.16751054277071004;
                                attribute 'σ_Iyy' : Real = 0.3723953238821935;
                                attribute Izz : Real = 0.1698670173879568;
                                attribute 'σ_Izz' : Real = 0.37017423652493897;
                                attribute Ixy : Real = 0.014379577080152263;
                                attribute 'σ_Ixy' : Real = 0.02351283871158888;
                                attribute Ixz : Real = 0.006816857611360043;
                                attribute 'σ_Ixz' : Real = 0.022566176940390956;
                                attribute Iyz : Real = -0.0026793842114052387;
                                attribute 'σ_Iyz' : Real = 0.02209918015384651;
                            }
                            part <'C.1.2.3.4.2.2.3'> 'Part 1221' {
                                attribute POIconv : String = "+";
                                attribute Ipoint : Boolean = false;
                                attribute mass : Real = 0.020360782307572663;
                                attribute 'σ_mass' : Real = 0.28909372274994966;
                                attribute Cx : Real = 93.1681405287236;
                                attribute 'σ_Cx' : Real = 28.721044428837228;
                                attribute Cy : Real = -56.24124030582607;
                                attribute 'σ_Cy' : Real = 28.23690002309109;
                                attribute Cz : Real = -12.299714935943484;
                                attribute 'σ_Cz' : Real = 29.057750463592832;
                                attribute Ixx : Real = 0.021332907875465813;
                                attribute 'σ_Ixx' : Real = 0.37074144170588635;
                                attribute Iyy : Real = 0.02227305120744767;
                                attribute 'σ_Iyy' : Real = 0.3723953238821935;
                                attribute Izz : Real = 0.021259712341645094;
                                attribute 'σ_Izz' : Real = 0.37017423652493897;
                                attribute Ixy : Real = -3.766152262650409e-4;
                                attribute 'σ_Ixy' : Real = 0.02351283871158888;
                                attribute Ixz : Real = -0.0022143657647772422;
                                attribute 'σ_Ixz' : Real = 0.022566176940390956;
                                attribute Iyz : Real = 4.996824690278931e-4;
                                attribute 'σ_Iyz' : Real = 0.02209918015384651;
                            }
                            part <'C.1.2.3.4.2.2.4'> 'Part 1222' {
                                attribute POIconv : String = "+";
                                attribute Ipoint : Boolean = false;
                                attribute mass : Real = 0.12226045999093912;
                                attribute 'σ_mass' : Real = 0.28909372274994966;
                                attribute Cx : Real = 18.275998765602708;
                                attribute 'σ_Cx' : Real = 28.721044428837228;
                                attribute Cy : Real = 99.76903623901308;
                                attribute 'σ_Cy' : Real = 28.23690002309109;
                                attribute Cz : Real = -35.02549366094172;
                                attribute 'σ_Cz' : Real = 29.057750463592832;
                                attribute Ixx : Real = 0.15440117370761738;
                                attribute 'σ_Ixx' : Real = 0.37074144170588635;
                                attribute Iyy : Real = 0.17499414128639668;
                                attribute 'σ_Iyy' : Real = 0.3723953238821935;
                                attribute Izz : Real = 0.17801505497646525;
                                attribute 'σ_Izz' : Real = 0.37017423652493897;
                                attribute Ixy : Real = 0.005247241173813501;
                                attribute 'σ_Ixy' : Real = 0.02351283871158888;
                                attribute Ixz : Real = 1.5115575163074472e-4;
                                attribute 'σ_Ixz' : Real = 0.022566176940390956;
                                attribute Iyz : Real = -1.3542479617262708e-5;
                                attribute 'σ_Iyz' : Real = 0.02209918015384651;
                            }
                            part <'C.1.2.3.4.2.2.5'> 'Part 1223' {
                                attribute POIconv : String = "-";
                                attribute Ipoint : Boolean = false;
                                attribute mass : Real = 0.4497093737798277;
                                attribute 'σ_mass' : Real = 0.28909372274994966;
                                attribute Cx : Real = -8.599200425669551;
                                attribute 'σ_Cx' : Real = 28.721044428837228;
                                attribute Cy : Real = 14.461542945355177;
                                attribute 'σ_Cy' : Real = 28.23690002309109;
                                attribute Cz : Real = -20.737309753894806;
                                attribute 'σ_Cz' : Real = 29.057750463592832;
                                attribute Ixx : Real = 0.5709853260537264;
                                attribute 'σ_Ixx' : Real = 0.37074144170588635;
                                attribute Iyy : Real = 0.5260483799173741;
                                attribute 'σ_Iyy' : Real = 0.3723953238821935;
                                attribute Izz : Real = 0.4750191227716839;
                                attribute 'σ_Izz' : Real = 0.37017423652493897;
                                attribute Ixy : Real = 0.03167733982626806;
                                attribute 'σ_Ixy' : Real = 0.02351283871158888;
                                attribute Ixz : Real = 0.05429001158268744;
                                attribute 'σ_Ixz' : Real = 0.022566176940390956;
                                attribute Iyz : Real = -0.04972857273891146;
                                attribute 'σ_Iyz' : Real = 0.02209918015384651;
                            }
                        }
                        part <'C.1.2.3.4.2.3'> 'Subassembly 345' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.4.2.3.1'> 'Part 1224' {
                                attribute POIconv : String = "-";
                                attribute Ipoint : Boolean = false;
                                attribute mass : Real = 0.84417522983253;
                                attribute 'σ_mass' : Real = 0.28909372274994966;
                                attribute Cx : Real = -24.486743193119764;
                                attribute 'σ_Cx' : Real = 28.721044428837228;
                                attribute Cy : Real = -43.18207474425435;
                                attribute 'σ_Cy' : Real = 28.23690002309109;
                                attribute Cz : Real = 72.44566157460213;
                                attribute 'σ_Cz' : Real = 29.057750463592832;
                                attribute Ixx : Real = 1.065894861419456;
                                attribute 'σ_Ixx' : Real = 0.37074144170588635;
                                attribute Iyy : Real = 0.8832950542897401;
                                attribute 'σ_Iyy' : Real = 0.3723953238821935;
                                attribute Izz : Real = 1.1219573249609962;
                                attribute 'σ_Izz' : Real = 0.37017423652493897;
                                attribute Ixy : Real = -0.015019019399915906;
                                attribute 'σ_Ixy' : Real = 0.02351283871158888;
                                attribute Ixz : Real = -0.04183599286311755;
                                attribute 'σ_Ixz' : Real = 0.022566176940390956;
                                attribute Iyz : Real = -0.0867870770375726;
                                attribute 'σ_Iyz' : Real = 0.02209918015384651;
                            }
                            part <'C.1.2.3.4.2.3.2'> 'Part 1225' {
                                attribute POIconv : String = "+";
                                attribute Ipoint : Boolean = false;
                                attribute mass : Real = 0.41232388240331785;
                                attribute 'σ_mass' : Real = 0.28909372274994966;
                                attribute Cx : Real = -37.69333395175636;
                                attribute 'σ_Cx' : Real = 28.721044428837228;
                                attribute Cy : Real = 8.571316441521049;
                                attribute 'σ_Cy' : Real = 28.23690002309109;
                                attribute Cz : Real = 83.48979679867625;
                                attribute 'σ_Cz' : Real = 29.057750463592832;
                                attribute Ixx : Real = 0.5530045015707653;
                                attribute 'σ_Ixx' : Real = 0.37074144170588635;
                                attribute Iyy : Real = 0.5560193317403082;
                                attribute 'σ_Iyy' : Real = 0.3723953238821935;
                                attribute Izz : Real = 0.5917422654359216;
                                attribute 'σ_Izz' : Real = 0.37017423652493897;
                                attribute Ixy : Real = -0.004414012317710063;
                                attribute 'σ_Ixy' : Real = 0.02351283871158888;
                                attribute Ixz : Real = -0.005060237547583198;
                                attribute 'σ_Ixz' : Real = 0.022566176940390956;
                                attribute Iyz : Real = 5.534629840237461e-4;
                                attribute 'σ_Iyz' : Real = 0.02209918015384651;
                            }
                        }
                    }
                    part <'C.1.2.3.4.3'> 'Assembly 100' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.4.3.1'> 'Subassembly 346' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.4.3.1.1'> 'Part 1226' {
                                attribute POIconv : String = "+";
                                attribute Ipoint : Boolean = false;
                                attribute mass : Real = 0.8887760209697299;
                                attribute 'σ_mass' : Real = 0.28909372274994966;
                                attribute Cx : Real = -94.55333561636508;
                                attribute 'σ_Cx' : Real = 28.721044428837228;
                                attribute Cy : Real = -48.07567927055061;
                                attribute 'σ_Cy' : Real = 28.23690002309109;
                                attribute Cz : Real = 57.3687335010618;
                                attribute 'σ_Cz' : Real = 29.057750463592832;
                                attribute Ixx : Real = 0.9681078607984221;
                                attribute 'σ_Ixx' : Real = 0.37074144170588635;
                                attribute Iyy : Real = 1.1566886408285675;
                                attribute 'σ_Iyy' : Real = 0.3723953238821935;
                                attribute Izz : Real = 1.2213536333227448;
                                attribute 'σ_Izz' : Real = 0.37017423652493897;
                                attribute Ixy : Real = -0.05163081342588777;
                                attribute 'σ_Ixy' : Real = 0.02351283871158888;
                                attribute Ixz : Real = -0.002221971143847304;
                                attribute 'σ_Ixz' : Real = 0.022566176940390956;
                                attribute Iyz : Real = -0.03507299904897307;
                                attribute 'σ_Iyz' : Real = 0.02209918015384651;
                            }
                            part <'C.1.2.3.4.3.1.2'> 'Part 1227' {
                                attribute POIconv : String = "-";
                                attribute Ipoint : Boolean = false;
                                attribute mass : Real = 0.7454087423814927;
                                attribute 'σ_mass' : Real = 0.28909372274994966;
                                attribute Cx : Real = -55.25266686454415;
                                attribute 'σ_Cx' : Real = 28.721044428837228;
                                attribute Cy : Real = 87.32788013294339;
                                attribute 'σ_Cy' : Real = 28.23690002309109;
                                attribute Cz : Real = 68.57433654367924;
                                attribute 'σ_Cz' : Real = 29.057750463592832;
                                attribute Ixx : Real = 0.9078750677648647;
                                attribute 'σ_Ixx' : Real = 0.37074144170588635;
                                attribute Iyy : Real = 0.9632076687982218;
                                attribute 'σ_Iyy' : Real = 0.3723953238821935;
                                attribute Izz : Real = 0.9166185560589292;
                                attribute 'σ_Izz' : Real = 0.37017423652493897;
                                attribute Ixy : Real = -0.08312485854645174;
                                attribute 'σ_Ixy' : Real = 0.02351283871158888;
                                attribute Ixz : Real = -0.006210118563222998;
                                attribute 'σ_Ixz' : Real = 0.022566176940390956;
                                attribute Iyz : Real = -0.046088217079240434;
                                attribute 'σ_Iyz' : Real = 0.02209918015384651;
                            }
                            part <'C.1.2.3.4.3.1.3'> 'Part 1228' {
                                attribute POIconv : String = "+";
                                attribute Ipoint : Boolean = false;
                                attribute mass : Real = 0.7528804621580056;
                                attribute 'σ_mass' : Real = 0.28909372274994966;
                                attribute Cx : Real = 94.53241233713925;
                                attribute 'σ_Cx' : Real = 28.721044428837228;
                                attribute Cy : Real = -21.036946680396795;
                                attribute 'σ_Cy' : Real = 28.23690002309109;
                                attribute Cz : Real = -1.4626286923885345;
                                attribute 'σ_Cz' : Real = 29.057750463592832;
                                attribute Ixx : Real = 1.1623795318550816;
                                attribute 'σ_Ixx' : Real = 0.37074144170588635;
                                attribute Iyy : Real = 1.2200190900400096;
                                attribute 'σ_Iyy' : Real = 0.3723953238821935;
                                attribute Izz : Real = 1.1891856418239375;
                                attribute 'σ_Izz' : Real = 0.37017423652493897;
                                attribute Ixy : Real = 0.009139032848586894;
                                attribute 'σ_Ixy' : Real = 0.02351283871158888;
                                attribute Ixz : Real = 0.002468363796709512;
                                attribute 'σ_Ixz' : Real = 0.022566176940390956;
                                attribute Iyz : Real = -0.03659010146709007;
                                attribute 'σ_Iyz' : Real = 0.02209918015384651;
                            }
                        }
                        part <'C.1.2.3.4.3.2'> 'Subassembly 347' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.4.3.2.1'> 'Part 1229' {
                                attribute POIconv : String = "+";
                                attribute Ipoint : Boolean = false;
                                attribute mass : Real = 0.9425255339709111;
                                attribute 'σ_mass' : Real = 0.28909372274994966;
                                attribute Cx : Real = -36.0169883351773;
                                attribute 'σ_Cx' : Real = 28.721044428837228;
                                attribute Cy : Real = 62.73062382824719;
                                attribute 'σ_Cy' : Real = 28.23690002309109;
                                attribute Cz : Real = -82.23370020277798;
                                attribute 'σ_Cz' : Real = 29.057750463592832;
                                attribute Ixx : Real = 1.4166508101749156;
                                attribute 'σ_Ixx' : Real = 0.37074144170588635;
                                attribute Iyy : Real = 1.440371333419505;
                                attribute 'σ_Iyy' : Real = 0.3723953238821935;
                                attribute Izz : Real = 1.3544307702319267;
                                attribute 'σ_Izz' : Real = 0.37017423652493897;
                                attribute Ixy : Real = 0.014497383935852032;
                                attribute 'σ_Ixy' : Real = 0.02351283871158888;
                                attribute Ixz : Real = -0.0167696320586855;
                                attribute 'σ_Ixz' : Real = 0.022566176940390956;
                                attribute Iyz : Real = -0.019881132629455324;
                                attribute 'σ_Iyz' : Real = 0.02209918015384651;
                            }
                            part <'C.1.2.3.4.3.2.2'> 'Part 1230' {
                                attribute POIconv : String = "-";
                                attribute Ipoint : Boolean = false;
                                attribute mass : Real = 0.9229548323696944;
                                attribute 'σ_mass' : Real = 0.28909372274994966;
                                attribute Cx : Real = 20.20778814330697;
                                attribute 'σ_Cx' : Real = 28.721044428837228;
                                attribute Cy : Real = -92.37292567268014;
                                attribute 'σ_Cy' : Real = 28.23690002309109;
                                attribute Cz : Real = -13.204154325649142;
                                attribute 'σ_Cz' : Real = 29.057750463592832;
                                attribute Ixx : Real = 1.3288876260886053;
                                attribute 'σ_Ixx' : Real = 0.37074144170588635;
                                attribute Iyy : Real = 1.3289935895365619;
                                attribute 'σ_Iyy' : Real = 0.3723953238821935;
                                attribute Izz : Real = 1.3753190819520789;
                                attribute 'σ_Izz' : Real = 0.37017423652493897;
                                attribute Ixy : Real = 0.02210176413775327;
                                attribute 'σ_Ixy' : Real = 0.02351283871158888;
                                attribute Ixz : Real = -0.020497363215445624;
                                attribute 'σ_Ixz' : Real = 0.022566176940390956;
                                attribute Iyz : Real = -0.0422153746267752;
                                attribute 'σ_Iyz' : Real = 0.02209918015384651;
                            }
                            part <'C.1.2.3.4.3.2.3'> 'Part 1231' {
                                attribute POIconv : String = "+";
                                attribute Ipoint : Boolean = false;
                                attribute mass : Real = 0.02166795061598532;
                                attribute 'σ_mass' : Real = 0.28909372274994966;
                                attribute Cx : Real = -31.414156267419457;
                                attribute 'σ_Cx' : Real = 28.721044428837228;
                                attribute Cy : Real = -23.786183400079608;
                                attribute 'σ_Cy' : Real = 28.23690002309109;
                                attribute Cz : Real = -27.62659047730267;
                                attribute 'σ_Cz' : Real = 29.057750463592832;
                                attribute Ixx : Real = 0.027248941858548866;
                                attribute 'σ_Ixx' : Real = 0.37074144170588635;
                                attribute Iyy : Real = 0.02807880583631137;
                                attribute 'σ_Iyy' : Real = 0.3723953238821935;
                                attribute Izz : Real = 0.024251381342115255;
                                attribute 'σ_Izz' : Real = 0.37017423652493897;
                                attribute Ixy : Real = 4.164934185500108e-4;
                                attribute 'σ_Ixy' : Real = 0.02351283871158888;
                                attribute Ixz : Real = -0.0020605139397297757;
                                attribute 'σ_Ixz' : Real = 0.022566176940390956;
                                attribute Iyz : Real = -9.501757923268289e-4;
                                attribute 'σ_Iyz' : Real = 0.02209918015384651;
                            }
                            part <'C.1.2.3.4.3.2.4'> 'Part 1232' {
                                attribute POIconv : String = "+";
                                attribute Ipoint : Boolean = false;
                                attribute mass : Real = 0.4497773667725269;
                                attribute 'σ_mass' : Real = 0.28909372274994966;
                                attribute Cx : Real = -76.29518327303231;
                                attribute 'σ_Cx' : Real = 28.721044428837228;
                                attribute Cy : Real = 90.79723069444299;
                                attribute 'σ_Cy' : Real = 28.23690002309109;
                                attribute Cz : Real = -82.54691399633884;
                                attribute 'σ_Cz' : Real = 29.057750463592832;
                                attribute Ixx : Real = 0.5551721838350132;
                                attribute 'σ_Ixx' : Real = 0.37074144170588635;
                                attribute Iyy : Real = 0.6718741175144284;
                                attribute 'σ_Iyy' : Real = 0.3723953238821935;
                                attribute Izz : Real = 0.5437058027664015;
                                attribute 'σ_Izz' : Real = 0.37017423652493897;
                                attribute Ixy : Real = -0.05112265010763005;
                                attribute 'σ_Ixy' : Real = 0.02351283871158888;
                                attribute Ixz : Real = 0.0013925075738839372;
                                attribute 'σ_Ixz' : Real = 0.022566176940390956;
                                attribute Iyz : Real = -0.0031026503560824294;
                                attribute 'σ_Iyz' : Real = 0.02209918015384651;
                            }
                        }
                    }
                }
                part <'C.1.2.3.5'> 'Subsystem 27' {
                    attribute POIconv : String = "-";
                    attribute Ipoint : Boolean;
                    attribute mass : Real;
                    attribute 'σ_mass' : Real;
                    attribute Cx : Real;
                    attribute 'σ_Cx' : Real;
                    attribute Cy : Real;
                    attribute 'σ_Cy' : Real;
                    attribute Cz : Real;
                    attribute 'σ_Cz' : Real;
                    attribute Ixx : Real;
                    attribute 'σ_Ixx' : Real;
                    attribute Iyy : Real;
                    attribute 'σ_Iyy' : Real;
                    attribute Izz : Real;
                    attribute 'σ_Izz' : Real;
                    attribute Ixy : Real;
                    attribute 'σ_Ixy' : Real;
                    attribute Ixz : Real;
                    attribute 'σ_Ixz' : Real;
                    attribute Iyz : Real;
                    attribute 'σ_Iyz' : Real;
                    part <'C.1.2.3.5.1'> 'Assembly 101' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.5.1.1'> 'Subassembly 348' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.5.1.1.1'> 'Part 1233' {
                                attribute POIconv : String = "+";
                                attribute Ipoint : Boolean = false;
                                attribute mass : Real = 0.22666995134670287;
                                attribute 'σ_mass' : Real = 0.28909372274994966;
                                attribute Cx : Real = 46.82083432562649;
                                attribute 'σ_Cx' : Real = 28.721044428837228;
                                attribute Cy : Real = 83.26813052408397;
                                attribute 'σ_Cy' : Real = 28.23690002309109;
                                attribute Cz : Real = 39.585072034969926;
                                attribute 'σ_Cz' : Real = 29.057750463592832;
                                attribute Ixx : Real = 0.3001066899636975;
                                attribute 'σ_Ixx' : Real = 0.37074144170588635;
                                attribute Iyy : Real = 0.33782805497635304;
                                attribute 'σ_Iyy' : Real = 0.3723953238821935;
                                attribute Izz : Real = 0.2760758527342382;
                                attribute 'σ_Izz' : Real = 0.37017423652493897;
                                attribute Ixy : Real = -0.006456171252190321;
                                attribute 'σ_Ixy' : Real = 0.02351283871158888;
                                attribute Ixz : Real = -0.011820872916293256;
                                attribute 'σ_Ixz' : Real = 0.022566176940390956;
                                attribute Iyz : Real = 0.006681835140664046;
                                attribute 'σ_Iyz' : Real = 0.02209918015384651;
                            }
                            part <'C.1.2.3.5.1.1.2'> 'Part 1234' {
                                attribute POIconv : String = "+";
                                attribute Ipoint : Boolean = false;
                                attribute mass : Real = 0.7957524172503035;
                                attribute 'σ_mass' : Real = 0.28909372274994966;
                                attribute Cx : Real = -48.327252035960555;
                                attribute 'σ_Cx' : Real = 28.721044428837228;
                                attribute Cy : Real = -99.13239404559135;
                                attribute 'σ_Cy' : Real = 28.23690002309109;
                                attribute Cz : Real = 1.0650597047060728;
                                attribute 'σ_Cz' : Real = 29.057750463592832;
                                attribute Ixx : Real = 1.0207718461420159;
                                attribute 'σ_Ixx' : Real = 0.37074144170588635;
                                attribute Iyy : Real = 1.0369276008840338;
                                attribute 'σ_Iyy' : Real = 0.3723953238821935;
                                attribute Izz : Real = 1.2135886026228058;
                                attribute 'σ_Izz' : Real = 0.37017423652493897;
                                attribute Ixy : Real = -0.0016952285537999532;
                                attribute 'σ_Ixy' : Real = 0.02351283871158888;
                                attribute Ixz : Real = -0.04848621631579215;
                                attribute 'σ_Ixz' : Real = 0.022566176940390956;
                                attribute Iyz : Real = -0.047769847241058414;
                                attribute 'σ_Iyz' : Real = 0.02209918015384651;
                            }
                            part <'C.1.2.3.5.1.1.3'> 'Part 1235' {
                                attribute POIconv : String = "+";
                                attribute Ipoint : Boolean = false;
                                attribute mass : Real = 0.7954125288114883;
                                attribute 'σ_mass' : Real = 0.28909372274994966;
                                attribute Cx : Real = -9.119902458041906;
                                attribute 'σ_Cx' : Real = 28.721044428837228;
                                attribute Cy : Real = 20.752541488036513;
                                attribute 'σ_Cy' : Real = 28.23690002309109;
                                attribute Cz : Real = -85.95985691063106;
                                attribute 'σ_Cz' : Real = 29.057750463592832;
                                attribute Ixx : Real = 1.02956872042714;
                                attribute 'σ_Ixx' : Real = 0.37074144170588635;
                                attribute Iyy : Real = 0.9809241146418645;
                                attribute 'σ_Iyy' : Real = 0.3723953238821935;
                                attribute Izz : Real = 0.9628925351956685;
                                attribute 'σ_Izz' : Real = 0.37017423652493897;
                                attribute Ixy : Real = 0.02808652490844335;
                                attribute 'σ_Ixy' : Real = 0.02351283871158888;
                                attribute Ixz : Real = -0.028776776377454537;
                                attribute 'σ_Ixz' : Real = 0.022566176940390956;
                                attribute Iyz : Real = 6.470697068030823e-4;
                                attribute 'σ_Iyz' : Real = 0.02209918015384651;
                            }
                        }
                        part <'C.1.2.3.5.1.2'> 'Subassembly 349' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.5.1.2.1'> 'Part 1236' {
                                attribute POIconv : String = "-";
                                attribute Ipoint : Boolean = false;
                                attribute mass : Real = 0.028669977720361204;
                                attribute 'σ_mass' : Real = 0.28909372274994966;
                                attribute Cx : Real = 7.8325701877474785;
                                attribute 'σ_Cx' : Real = 28.721044428837228;
                                attribute Cy : Real = -30.79293561168015;
                                attribute 'σ_Cy' : Real = 28.23690002309109;
                                attribute Cz : Real = -27.09494512528181;
                                attribute 'σ_Cz' : Real = 29.057750463592832;
                                attribute Ixx : Real = 0.038764728341863675;
                                attribute 'σ_Ixx' : Real = 0.37074144170588635;
                                attribute Iyy : Real = 0.038298783306221294;
                                attribute 'σ_Iyy' : Real = 0.3723953238821935;
                                attribute Izz : Real = 0.037384705712386244;
                                attribute 'σ_Izz' : Real = 0.37017423652493897;
                                attribute Ixy : Real = 7.174932599655494e-5;
                                attribute 'σ_Ixy' : Real = 0.02351283871158888;
                                attribute Ixz : Real = -0.0011627568211055;
                                attribute 'σ_Ixz' : Real = 0.022566176940390956;
                                attribute Iyz : Real = 0.001549302083599849;
                                attribute 'σ_Iyz' : Real = 0.02209918015384651;
                            }
                            part <'C.1.2.3.5.1.2.2'> 'Part 1237' {
                                attribute POIconv : String = "+";
                                attribute Ipoint : Boolean = false;
                                attribute mass : Real = 0.09765278878458776;
                                attribute 'σ_mass' : Real = 0.28909372274994966;
                                attribute Cx : Real = 63.3061442989856;
                                attribute 'σ_Cx' : Real = 28.721044428837228;
                                attribute Cy : Real = -41.65270128287375;
                                attribute 'σ_Cy' : Real = 28.23690002309109;
                                attribute Cz : Real = -66.70942339114845;
                                attribute 'σ_Cz' : Real = 29.057750463592832;
                                attribute Ixx : Real = 0.1177821649008545;
                                attribute 'σ_Ixx' : Real = 0.37074144170588635;
                                attribute Iyy : Real = 0.10623754770298825;
                                attribute 'σ_Iyy' : Real = 0.3723953238821935;
                                attribute Izz : Real = 0.09981332575065407;
                                attribute 'σ_Izz' : Real = 0.37017423652493897;
                                attribute Ixy : Real = -0.002843364233600392;
                                attribute 'σ_Ixy' : Real = 0.02351283871158888;
                                attribute Ixz : Real = -8.723067838638854e-4;
                                attribute 'σ_Ixz' : Real = 0.022566176940390956;
                                attribute Iyz : Real = -0.005602734921786284;
                                attribute 'σ_Iyz' : Real = 0.02209918015384651;
                            }
                            part <'C.1.2.3.5.1.2.3'> 'Part 1238' {
                                attribute POIconv : String = "+";
                                attribute Ipoint : Boolean = false;
                                attribute mass : Real = 0.46308294393727556;
                                attribute 'σ_mass' : Real = 0.28909372274994966;
                                attribute Cx : Real = 23.701453488320112;
                                attribute 'σ_Cx' : Real = 28.721044428837228;
                                attribute Cy : Real = -90.69789256900549;
                                attribute 'σ_Cy' : Real = 28.23690002309109;
                                attribute Cz : Real = -58.624538173899055;
                                attribute 'σ_Cz' : Real = 29.057750463592832;
                                attribute Ixx : Real = 0.49092931833873765;
                                attribute 'σ_Ixx' : Real = 0.37074144170588635;
                                attribute Iyy : Real = 0.5073879525343943;
                                attribute 'σ_Iyy' : Real = 0.3723953238821935;
                                attribute Izz : Real = 0.46441618652834865;
                                attribute 'σ_Izz' : Real = 0.37017423652493897;
                                attribute Ixy : Real = -0.007232296814225083;
                                attribute 'σ_Ixy' : Real = 0.02351283871158888;
                                attribute Ixz : Real = 0.05245730264999222;
                                attribute 'σ_Ixz' : Real = 0.022566176940390956;
                                attribute Iyz : Real = -0.016793137364945365;
                                attribute 'σ_Iyz' : Real = 0.02209918015384651;
                            }
                            part <'C.1.2.3.5.1.2.4'> 'Part 1239' {
                                attribute POIconv : String = "-";
                                attribute Ipoint : Boolean = false;
                                attribute mass : Real = 0.5503887898386456;
                                attribute 'σ_mass' : Real = 0.28909372274994966;
                                attribute Cx : Real = -81.84429737739265;
                                attribute 'σ_Cx' : Real = 28.721044428837228;
                                attribute Cy : Real = 75.48872185871005;
                                attribute 'σ_Cy' : Real = 28.23690002309109;
                                attribute Cz : Real = 85.14078063890338;
                                attribute 'σ_Cz' : Real = 29.057750463592832;
                                attribute Ixx : Real = 0.5804846695536577;
                                attribute 'σ_Ixx' : Real = 0.37074144170588635;
                                attribute Iyy : Real = 0.623510434223508;
                                attribute 'σ_Iyy' : Real = 0.3723953238821935;
                                attribute Izz : Real = 0.5971426047870412;
                                attribute 'σ_Izz' : Real = 0.37017423652493897;
                                attribute Ixy : Real = 0.038983880094853436;
                                attribute 'σ_Ixy' : Real = 0.02351283871158888;
                                attribute Ixz : Real = -0.017644884867001318;
                                attribute 'σ_Ixz' : Real = 0.022566176940390956;
                                attribute Iyz : Real = -0.028764995279669227;
                                attribute 'σ_Iyz' : Real = 0.02209918015384651;
                            }
                            part <'C.1.2.3.5.1.2.5'> 'Part 1240' {
                                attribute POIconv : String = "-";
                                attribute Ipoint : Boolean = false;
                                attribute mass : Real = 0.6681789579128381;
                                attribute 'σ_mass' : Real = 0.28909372274994966;
                                attribute Cx : Real = -9.4069036655128;
                                attribute 'σ_Cx' : Real = 28.721044428837228;
                                attribute Cy : Real = -87.77754264883697;
                                attribute 'σ_Cy' : Real = 28.23690002309109;
                                attribute Cz : Real = 44.423402566462755;
                                attribute 'σ_Cz' : Real = 29.057750463592832;
                                attribute Ixx : Real = 0.8602232134964805;
                                attribute 'σ_Ixx' : Real = 0.37074144170588635;
                                attribute Iyy : Real = 0.9943086804372709;
                                attribute 'σ_Iyy' : Real = 0.3723953238821935;
                                attribute Izz : Real = 0.7938467565876774;
                                attribute 'σ_Izz' : Real = 0.37017423652493897;
                                attribute Ixy : Real = 0.014941206709004678;
                                attribute 'σ_Ixy' : Real = 0.02351283871158888;
                                attribute Ixz : Real = -0.031483272468263074;
                                attribute 'σ_Ixz' : Real = 0.022566176940390956;
                                attribute Iyz : Real = 0.0371749812087482;
                                attribute 'σ_Iyz' : Real = 0.02209918015384651;
                            }
                        }
                        part <'C.1.2.3.5.1.3'> 'Subassembly 350' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.5.1.3.1'> 'Part 1241' {
                                attribute POIconv : String = "-";
                                attribute Ipoint : Boolean = false;
                                attribute mass : Real = 0.4524043802027591;
                                attribute 'σ_mass' : Real = 0.28909372274994966;
                                attribute Cx : Real = -61.25743710435927;
                                attribute 'σ_Cx' : Real = 28.721044428837228;
                                attribute Cy : Real = -97.67109882086515;
                                attribute 'σ_Cy' : Real = 28.23690002309109;
                                attribute Cz : Real = -3.21130333468318;
                                attribute 'σ_Cz' : Real = 29.057750463592832;
                                attribute Ixx : Real = 0.5669003066787957;
                                attribute 'σ_Ixx' : Real = 0.37074144170588635;
                                attribute Iyy : Real = 0.5355483741996078;
                                attribute 'σ_Iyy' : Real = 0.3723953238821935;
                                attribute Izz : Real = 0.5607491378991943;
                                attribute 'σ_Izz' : Real = 0.37017423652493897;
                                attribute Ixy : Real = 0.031807412311889764;
                                attribute 'σ_Ixy' : Real = 0.02351283871158888;
                                attribute Ixz : Real = 0.011423964063863649;
                                attribute 'σ_Ixz' : Real = 0.022566176940390956;
                                attribute Iyz : Real = 0.010511086375891064;
                                attribute 'σ_Iyz' : Real = 0.02209918015384651;
                            }
                            part <'C.1.2.3.5.1.3.2'> 'Part 1242' {
                                attribute POIconv : String = "-";
                                attribute Ipoint : Boolean = false;
                                attribute mass : Real = 0.42198422060185115;
                                attribute 'σ_mass' : Real = 0.28909372274994966;
                                attribute Cx : Real = -20.270169293507934;
                                attribute 'σ_Cx' : Real = 28.721044428837228;
                                attribute Cy : Real = 41.306568309664726;
                                attribute 'σ_Cy' : Real = 28.23690002309109;
                                attribute Cz : Real = 64.15808480232954;
                                attribute 'σ_Cz' : Real = 29.057750463592832;
                                attribute Ixx : Real = 0.49600471211019675;
                                attribute 'σ_Ixx' : Real = 0.37074144170588635;
                                attribute Iyy : Real = 0.46659338265001865;
                                attribute 'σ_Iyy' : Real = 0.3723953238821935;
                                attribute Izz : Real = 0.4304747934405064;
                                attribute 'σ_Izz' : Real = 0.37017423652493897;
                                attribute Ixy : Real = -0.026736246160264487;
                                attribute 'σ_Ixy' : Real = 0.02351283871158888;
                                attribute Ixz : Real = -0.021840414064926175;
                                attribute 'σ_Ixz' : Real = 0.022566176940390956;
                                attribute Iyz : Real = 6.159228948878891e-4;
                                attribute 'σ_Iyz' : Real = 0.02209918015384651;
                            }
                            part <'C.1.2.3.5.1.3.3'> 'Part 1243' {
                                attribute POIconv : String = "+";
                                attribute Ipoint : Boolean = false;
                                attribute mass : Real = 0.317937930498505;
                                attribute 'σ_mass' : Real = 0.28909372274994966;
                                attribute Cx : Real = 6.58334163017571;
                                attribute 'σ_Cx' : Real = 28.721044428837228;
                                attribute Cy : Real = 27.41168146021664;
                                attribute 'σ_Cy' : Real = 28.23690002309109;
                                attribute Cz : Real = -34.940012730658054;
                                attribute 'σ_Cz' : Real = 29.057750463592832;
                                attribute Ixx : Real = 0.35929360465398785;
                                attribute 'σ_Ixx' : Real = 0.37074144170588635;
                                attribute Iyy : Real = 0.322735092206;
                                attribute 'σ_Iyy' : Real = 0.3723953238821935;
                                attribute Izz : Real = 0.37621190582861225;
                                attribute 'σ_Izz' : Real = 0.37017423652493897;
                                attribute Ixy : Real = 0.027161517331259592;
                                attribute 'σ_Ixy' : Real = 0.02351283871158888;
                                attribute Ixz : Real = -0.007271241202886192;
                                attribute 'σ_Ixz' : Real = 0.022566176940390956;
                                attribute Iyz : Real = 0.008641019117807451;
                                attribute 'σ_Iyz' : Real = 0.02209918015384651;
                            }
                        }
                        part <'C.1.2.3.5.1.4'> 'Subassembly 351' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.5.1.4.1'> 'Part 1244' {
                                attribute POIconv : String = "-";
                                attribute Ipoint : Boolean = false;
                                attribute mass : Real = 0.4470364071626682;
                                attribute 'σ_mass' : Real = 0.28909372274994966;
                                attribute Cx : Real = -27.962521743029356;
                                attribute 'σ_Cx' : Real = 28.721044428837228;
                                attribute Cy : Real = -86.31998859345913;
                                attribute 'σ_Cy' : Real = 28.23690002309109;
                                attribute Cz : Real = 9.86206135712564;
                                attribute 'σ_Cz' : Real = 29.057750463592832;
                                attribute Ixx : Real = 0.5680081333668138;
                                attribute 'σ_Ixx' : Real = 0.37074144170588635;
                                attribute Iyy : Real = 0.6240042609967352;
                                attribute 'σ_Iyy' : Real = 0.3723953238821935;
                                attribute Izz : Real = 0.5478544600513949;
                                attribute 'σ_Izz' : Real = 0.37017423652493897;
                                attribute Ixy : Real = 0.005604570655368566;
                                attribute 'σ_Ixy' : Real = 0.02351283871158888;
                                attribute Ixz : Real = 0.007457408282342681;
                                attribute 'σ_Ixz' : Real = 0.022566176940390956;
                                attribute Iyz : Real = 0.01745886173598111;
                                attribute 'σ_Iyz' : Real = 0.02209918015384651;
                            }
                            part <'C.1.2.3.5.1.4.2'> 'Part 1245' {
                                attribute POIconv : String = "+";
                                attribute Ipoint : Boolean = false;
                                attribute mass : Real = 0.5333260146111716;
                                attribute 'σ_mass' : Real = 0.28909372274994966;
                                attribute Cx : Real = 88.41905957087874;
                                attribute 'σ_Cx' : Real = 28.721044428837228;
                                attribute Cy : Real = -65.50305760465562;
                                attribute 'σ_Cy' : Real = 28.23690002309109;
                                attribute Cz : Real = -40.15970500186086;
                                attribute 'σ_Cz' : Real = 29.057750463592832;
                                attribute Ixx : Real = 0.7734150683740445;
                                attribute 'σ_Ixx' : Real = 0.37074144170588635;
                                attribute Iyy : Real = 0.6847862206467095;
                                attribute 'σ_Iyy' : Real = 0.3723953238821935;
                                attribute Izz : Real = 0.7274667406800986;
                                attribute 'σ_Izz' : Real = 0.37017423652493897;
                                attribute Ixy : Real = -0.01956274793327845;
                                attribute 'σ_Ixy' : Real = 0.02351283871158888;
                                attribute Ixz : Real = 0.07132569432285725;
                                attribute 'σ_Ixz' : Real = 0.022566176940390956;
                                attribute Iyz : Real = -0.008152531502002923;
                                attribute 'σ_Iyz' : Real = 0.02209918015384651;
                            }
                            part <'C.1.2.3.5.1.4.3'> 'Part 1246' {
                                attribute POIconv : String = "+";
                                attribute Ipoint : Boolean = false;
                                attribute mass : Real = 0.887260308253346;
                                attribute 'σ_mass' : Real = 0.28909372274994966;
                                attribute Cx : Real = -10.44005542062223;
                                attribute 'σ_Cx' : Real = 28.721044428837228;
                                attribute Cy : Real = -48.2870539650321;
                                attribute 'σ_Cy' : Real = 28.23690002309109;
                                attribute Cz : Real = -43.64437595941126;
                                attribute 'σ_Cz' : Real = 29.057750463592832;
                                attribute Ixx : Real = 1.3035226829313638;
                                attribute 'σ_Ixx' : Real = 0.37074144170588635;
                                attribute Iyy : Real = 1.3894795576716723;
                                attribute 'σ_Iyy' : Real = 0.3723953238821935;
                                attribute Izz : Real = 1.2572713525036767;
                                attribute 'σ_Izz' : Real = 0.37017423652493897;
                                attribute Ixy : Real = 0.015121147284160176;
                                attribute 'σ_Ixy' : Real = 0.02351283871158888;
                                attribute Ixz : Real = -0.007767246486558844;
                                attribute 'σ_Ixz' : Real = 0.022566176940390956;
                                attribute Iyz : Real = 0.04812820856883939;
                                attribute 'σ_Iyz' : Real = 0.02209918015384651;
                            }
                            part <'C.1.2.3.5.1.4.4'> 'Part 1247' {
                                attribute POIconv : String = "-";
                                attribute Ipoint : Boolean = false;
                                attribute mass : Real = 0.2132096054579597;
                                attribute 'σ_mass' : Real = 0.28909372274994966;
                                attribute Cx : Real = 20.354890124872327;
                                attribute 'σ_Cx' : Real = 28.721044428837228;
                                attribute Cy : Real = 37.31562593020499;
                                attribute 'σ_Cy' : Real = 28.23690002309109;
                                attribute Cz : Real = 31.637340923771262;
                                attribute 'σ_Cz' : Real = 29.057750463592832;
                                attribute Ixx : Real = 0.2404530294255714;
                                attribute 'σ_Ixx' : Real = 0.37074144170588635;
                                attribute Iyy : Real = 0.24095081871753804;
                                attribute 'σ_Iyy' : Real = 0.3723953238821935;
                                attribute Izz : Real = 0.2531414246098385;
                                attribute 'σ_Izz' : Real = 0.37017423652493897;
                                attribute Ixy : Real = -0.004698048216591972;
                                attribute 'σ_Ixy' : Real = 0.02351283871158888;
                                attribute Ixz : Real = 0.004672059347782935;
                                attribute 'σ_Ixz' : Real = 0.022566176940390956;
                                attribute Iyz : Real = 0.011519409308047391;
                                attribute 'σ_Iyz' : Real = 0.02209918015384651;
                            }
                        }
                    }
                    part <'C.1.2.3.5.2'> 'Assembly 102' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.5.2.1'> 'Subassembly 352' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.5.2.1.1'> 'Part 1248' {
                                attribute POIconv : String = "-";
                                attribute Ipoint : Boolean = false;
                                attribute mass : Real = 0.29437477652193045;
                                attribute 'σ_mass' : Real = 0.28909372274994966;
                                attribute Cx : Real = 14.658892247825861;
                                attribute 'σ_Cx' : Real = 28.721044428837228;
                                attribute Cy : Real = 59.79750747792423;
                                attribute 'σ_Cy' : Real = 28.23690002309109;
                                attribute Cz : Real = -6.9031111896038055;
                                attribute 'σ_Cz' : Real = 29.057750463592832;
                                attribute Ixx : Real = 0.3679380766441123;
                                attribute 'σ_Ixx' : Real = 0.37074144170588635;
                                attribute Iyy : Real = 0.31934331779487013;
                                attribute 'σ_Iyy' : Real = 0.3723953238821935;
                                attribute Izz : Real = 0.42167607734835183;
                                attribute 'σ_Izz' : Real = 0.37017423652493897;
                                attribute Ixy : Real = -0.005047470923799126;
                                attribute 'σ_Ixy' : Real = 0.02351283871158888;
                                attribute Ixz : Real = -0.01310841618579281;
                                attribute 'σ_Ixz' : Real = 0.022566176940390956;
                                attribute Iyz : Real = -0.017902217264677375;
                                attribute 'σ_Iyz' : Real = 0.02209918015384651;
                            }
                            part <'C.1.2.3.5.2.1.2'> 'Part 1249' {
                                attribute POIconv : String = "+";
                                attribute Ipoint : Boolean = false;
                                attribute mass : Real = 0.7738428878854029;
                                attribute 'σ_mass' : Real = 0.28909372274994966;
                                attribute Cx : Real = -20.669632637873292;
                                attribute 'σ_Cx' : Real = 28.721044428837228;
                                attribute Cy : Real = -53.4666140563786;
                                attribute 'σ_Cy' : Real = 28.23690002309109;
                                attribute Cz : Real = 36.612317990511656;
                                attribute 'σ_Cz' : Real = 29.057750463592832;
                                attribute Ixx : Real = 0.9762497857757203;
                                attribute 'σ_Ixx' : Real = 0.37074144170588635;
                                attribute Iyy : Real = 0.8357901172397927;
                                attribute 'σ_Iyy' : Real = 0.3723953238821935;
                                attribute Izz : Real = 1.057359780191937;
                                attribute 'σ_Izz' : Real = 0.37017423652493897;
                                attribute Ixy : Real = -0.051994891628190154;
                                attribute 'σ_Ixy' : Real = 0.02351283871158888;
                                attribute Ixz : Real = -0.008879176366365746;
                                attribute 'σ_Ixz' : Real = 0.022566176940390956;
                                attribute Iyz : Real = 0.052016808910468046;
                                attribute 'σ_Iyz' : Real = 0.02209918015384651;
                            }
                            part <'C.1.2.3.5.2.1.3'> 'Part 1250' {
                                attribute POIconv : String = "+";
                                attribute Ipoint : Boolean = false;
                                attribute mass : Real = 0.6719840699620545;
                                attribute 'σ_mass' : Real = 0.28909372274994966;
                                attribute Cx : Real = 72.21237975172698;
                                attribute 'σ_Cx' : Real = 28.721044428837228;
                                attribute Cy : Real = 21.529939398169518;
                                attribute 'σ_Cy' : Real = 28.23690002309109;
                                attribute Cz : Real = -48.76855155453086;
                                attribute 'σ_Cz' : Real = 29.057750463592832;
                                attribute Ixx : Real = 0.936002883890469;
                                attribute 'σ_Ixx' : Real = 0.37074144170588635;
                                attribute Iyy : Real = 0.8341371909865365;
                                attribute 'σ_Iyy' : Real = 0.3723953238821935;
                                attribute Izz : Real = 0.897219455667445;
                                attribute 'σ_Izz' : Real = 0.37017423652493897;
                                attribute Ixy : Real = -0.003378685298492448;
                                attribute 'σ_Ixy' : Real = 0.02351283871158888;
                                attribute Ixz : Real = -0.0023557849089775726;
                                attribute 'σ_Ixz' : Real = 0.022566176940390956;
                                attribute Iyz : Real = 0.06268085830089416;
                                attribute 'σ_Iyz' : Real = 0.02209918015384651;
                            }
                        }
                        part <'C.1.2.3.5.2.2'> 'Subassembly 353' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.5.2.2.1'> 'Part 1251' {
                                attribute POIconv : String = "+";
                                attribute Ipoint : Boolean = false;
                                attribute mass : Real = 0.8867515277513303;
                                attribute 'σ_mass' : Real = 0.28909372274994966;
                                attribute Cx : Real = 10.376930655911565;
                                attribute 'σ_Cx' : Real = 28.721044428837228;
                                attribute Cy : Real = 83.76390621997416;
                                attribute 'σ_Cy' : Real = 28.23690002309109;
                                attribute Cz : Real = -79.20667519792914;
                                attribute 'σ_Cz' : Real = 29.057750463592832;
                                attribute Ixx : Real = 0.9303535111971629;
                                attribute 'σ_Ixx' : Real = 0.37074144170588635;
                                attribute Iyy : Real = 1.117018648060944;
                                attribute 'σ_Iyy' : Real = 0.3723953238821935;
                                attribute Izz : Real = 1.0119365011393968;
                                attribute 'σ_Izz' : Real = 0.37017423652493897;
                                attribute Ixy : Real = 0.06932017897973057;
                                attribute 'σ_Ixy' : Real = 0.02351283871158888;
                                attribute Ixz : Real = -0.12742892376013726;
                                attribute 'σ_Ixz' : Real = 0.022566176940390956;
                                attribute Iyz : Real = -0.027492673171577067;
                                attribute 'σ_Iyz' : Real = 0.02209918015384651;
                            }
                            part <'C.1.2.3.5.2.2.2'> 'Part 1252' {
                                attribute POIconv : String = "+";
                                attribute Ipoint : Boolean = false;
                                attribute mass : Real = 0.942455944892019;
                                attribute 'σ_mass' : Real = 0.28909372274994966;
                                attribute Cx : Real = -72.35633078962564;
                                attribute 'σ_Cx' : Real = 28.721044428837228;
                                attribute Cy : Real = -26.404158677905798;
                                attribute 'σ_Cy' : Real = 28.23690002309109;
                                attribute Cz : Real = 7.8602418303489685;
                                attribute 'σ_Cz' : Real = 29.057750463592832;
                                attribute Ixx : Real = 1.3336256706147664;
                                attribute 'σ_Ixx' : Real = 0.37074144170588635;
                                attribute Iyy : Real = 1.3748005075173215;
                                attribute 'σ_Iyy' : Real = 0.3723953238821935;
                                attribute Izz : Real = 1.325117687275256;
                                attribute 'σ_Izz' : Real = 0.37017423652493897;
                                attribute Ixy : Real = 0.05723250374521085;
                                attribute 'σ_Ixy' : Real = 0.02351283871158888;
                                attribute Ixz : Real = 0.03623217068390695;
                                attribute 'σ_Ixz' : Real = 0.022566176940390956;
                                attribute Iyz : Real = -0.05147582875410803;
                                attribute 'σ_Iyz' : Real = 0.02209918015384651;
                            }
                            part <'C.1.2.3.5.2.2.3'> 'Part 1253' {
                                attribute POIconv : String = "-";
                                attribute Ipoint : Boolean = false;
                                attribute mass : Real = 0.6424602351048961;
                                attribute 'σ_mass' : Real = 0.28909372274994966;
                                attribute Cx : Real = 58.17139125429094;
                                attribute 'σ_Cx' : Real = 28.721044428837228;
                                attribute Cy : Real = 80.45100830495358;
                                attribute 'σ_Cy' : Real = 28.23690002309109;
                                attribute Cz : Real = 8.601095294579864;
                                attribute 'σ_Cz' : Real = 29.057750463592832;
                                attribute Ixx : Real = 0.8101251969999419;
                                attribute 'σ_Ixx' : Real = 0.37074144170588635;
                                attribute Iyy : Real = 0.7620250017627846;
                                attribute 'σ_Iyy' : Real = 0.3723953238821935;
                                attribute Izz : Real = 0.7628121625498019;
                                attribute 'σ_Izz' : Real = 0.37017423652493897;
                                attribute Ixy : Real = -0.026948795968022937;
                                attribute 'σ_Ixy' : Real = 0.02351283871158888;
                                attribute Ixz : Real = -0.013666729350058542;
                                attribute 'σ_Ixz' : Real = 0.022566176940390956;
                                attribute Iyz : Real = -0.03666297346373025;
                                attribute 'σ_Iyz' : Real = 0.02209918015384651;
                            }
                        }
                    }
                    part <'C.1.2.3.5.3'> 'Assembly 103' {
                        attribute POIconv : String = "-";
                        attribute Ipoint : Boolean;
                        attribute mass : Real;
                        attribute 'σ_mass' : Real;
                        attribute Cx : Real;
                        attribute 'σ_Cx' : Real;
                        attribute Cy : Real;
                        attribute 'σ_Cy' : Real;
                        attribute Cz : Real;
                        attribute 'σ_Cz' : Real;
                        attribute Ixx : Real;
                        attribute 'σ_Ixx' : Real;
                        attribute Iyy : Real;
                        attribute 'σ_Iyy' : Real;
                        attribute Izz : Real;
                        attribute 'σ_Izz' : Real;
                        attribute Ixy : Real;
                        attribute 'σ_Ixy' : Real;
                        attribute Ixz : Real;
                        attribute 'σ_Ixz' : Real;
                        attribute Iyz : Real;
                        attribute 'σ_Iyz' : Real;
                        part <'C.1.2.3.5.3.1'> 'Subassembly 354' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.5.3.1.1'> 'Part 1254' {
                                attribute POIconv : String = "+";
                                attribute Ipoint : Boolean = false;
                                attribute mass : Real = 0.33016640045610257;
                                attribute 'σ_mass' : Real = 0.28909372274994966;
                                attribute Cx : Real = -35.44810418970883;
                                attribute 'σ_Cx' : Real = 28.721044428837228;
                                attribute Cy : Real = 65.93697317875922;
                                attribute 'σ_Cy' : Real = 28.23690002309109;
                                attribute Cz : Real = 14.03087368234992;
                                attribute 'σ_Cz' : Real = 29.057750463592832;
                                attribute Ixx : Real = 0.4841319693156862;
                                attribute 'σ_Ixx' : Real = 0.37074144170588635;
                                attribute Iyy : Real = 0.49410997565877923;
                                attribute 'σ_Iyy' : Real = 0.3723953238821935;
                                attribute Izz : Real = 0.5139325157423997;
                                attribute 'σ_Izz' : Real = 0.37017423652493897;
                                attribute Ixy : Real = -0.01368839964348144;
                                attribute 'σ_Ixy' : Real = 0.02351283871158888;
                                attribute Ixz : Real = 0.019441801700544624;
                                attribute 'σ_Ixz' : Real = 0.022566176940390956;
                                attribute Iyz : Real = 0.02784312114829495;
                                attribute 'σ_Iyz' : Real = 0.02209918015384651;
                            }
                            part <'C.1.2.3.5.3.1.2'> 'Part 1255' {
                                attribute POIconv : String = "-";
                                attribute Ipoint : Boolean = false;
                                attribute mass : Real = 0.602905201816;
                                attribute 'σ_mass' : Real = 0.28909372274994966;
                                attribute Cx : Real = -41.07709606178105;
                                attribute 'σ_Cx' : Real = 28.721044428837228;
                                attribute Cy : Real = -57.330096093937755;
                                attribute 'σ_Cy' : Real = 28.23690002309109;
                                attribute Cz : Real = -59.63577590882778;
                                attribute 'σ_Cz' : Real = 29.057750463592832;
                                attribute Ixx : Real = 0.867166398110262;
                                attribute 'σ_Ixx' : Real = 0.37074144170588635;
                                attribute Iyy : Real = 0.8600417004258021;
                                attribute 'σ_Iyy' : Real = 0.3723953238821935;
                                attribute Izz : Real = 0.8067052110298519;
                                attribute 'σ_Izz' : Real = 0.37017423652493897;
                                attribute Ixy : Real = 0.008920014766684324;
                                attribute 'σ_Ixy' : Real = 0.02351283871158888;
                                attribute Ixz : Real = 0.011488415818434811;
                                attribute 'σ_Ixz' : Real = 0.022566176940390956;
                                attribute Iyz : Real = 0.055085227572233525;
                                attribute 'σ_Iyz' : Real = 0.02209918015384651;
                            }
                            part <'C.1.2.3.5.3.1.3'> 'Part 1256' {
                                attribute POIconv : String = "-";
                                attribute Ipoint : Boolean = false;
                                attribute mass : Real = 0.2283896844435949;
                                attribute 'σ_mass' : Real = 0.28909372274994966;
                                attribute Cx : Real = -66.60578926093876;
                                attribute 'σ_Cx' : Real = 28.721044428837228;
                                attribute Cy : Real = -60.728950053453445;
                                attribute 'σ_Cy' : Real = 28.23690002309109;
                                attribute Cz : Real = 36.63800577633083;
                                attribute 'σ_Cz' : Real = 29.057750463592832;
                                attribute Ixx : Real = 0.25787027317159444;
                                attribute 'σ_Ixx' : Real = 0.37074144170588635;
                                attribute Iyy : Real = 0.24653307990206466;
                                attribute 'σ_Iyy' : Real = 0.3723953238821935;
                                attribute Izz : Real = 0.21522451145446275;
                                attribute 'σ_Izz' : Real = 0.37017423652493897;
                                attribute Ixy : Real = -0.004176609088616075;
                                attribute 'σ_Ixy' : Real = 0.02351283871158888;
                                attribute Ixz : Real = -4.126912672390296e-4;
                                attribute 'σ_Ixz' : Real = 0.022566176940390956;
                                attribute Iyz : Real = 0.0021269974645339936;
                                attribute 'σ_Iyz' : Real = 0.02209918015384651;
                            }
                            part <'C.1.2.3.5.3.1.4'> 'Part 1257' {
                                attribute POIconv : String = "+";
                                attribute Ipoint : Boolean = false;
                                attribute mass : Real = 0.3838924115416594;
                                attribute 'σ_mass' : Real = 0.28909372274994966;
                                attribute Cx : Real = 1.6697112936526537;
                                attribute 'σ_Cx' : Real = 28.721044428837228;
                                attribute Cy : Real = -97.07937496714294;
                                attribute 'σ_Cy' : Real = 28.23690002309109;
                                attribute Cz : Real = -1.4842706732451916;
                                attribute 'σ_Cz' : Real = 29.057750463592832;
                                attribute Ixx : Real = 0.5868579035477605;
                                attribute 'σ_Ixx' : Real = 0.37074144170588635;
                                attribute Iyy : Real = 0.6083982273421362;
                                attribute 'σ_Iyy' : Real = 0.3723953238821935;
                                attribute Izz : Real = 0.5775773199641188;
                                attribute 'σ_Izz' : Real = 0.37017423652493897;
                                attribute Ixy : Real = 0.02605880122359817;
                                attribute 'σ_Ixy' : Real = 0.02351283871158888;
                                attribute Ixz : Real = 0.0030654902422688705;
                                attribute 'σ_Ixz' : Real = 0.022566176940390956;
                                attribute Iyz : Real = -0.007850604691216578;
                                attribute 'σ_Iyz' : Real = 0.02209918015384651;
                            }
                        }
                        part <'C.1.2.3.5.3.2'> 'Subassembly 355' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.5.3.2.1'> 'Part 1258' {
                                attribute POIconv : String = "-";
                                attribute Ipoint : Boolean = false;
                                attribute mass : Real = 0.7904170762877911;
                                attribute 'σ_mass' : Real = 0.28909372274994966;
                                attribute Cx : Real = -18.88536843471229;
                                attribute 'σ_Cx' : Real = 28.721044428837228;
                                attribute Cy : Real = 53.307269886136055;
                                attribute 'σ_Cy' : Real = 28.23690002309109;
                                attribute Cz : Real = -65.97607689909637;
                                attribute 'σ_Cz' : Real = 29.057750463592832;
                                attribute Ixx : Real = 1.0564934970951025;
                                attribute 'σ_Ixx' : Real = 0.37074144170588635;
                                attribute Iyy : Real = 0.9080027013385203;
                                attribute 'σ_Iyy' : Real = 0.3723953238821935;
                                attribute Izz : Real = 1.054648457058773;
                                attribute 'σ_Izz' : Real = 0.37017423652493897;
                                attribute Ixy : Real = -0.0060826693920741585;
                                attribute 'σ_Ixy' : Real = 0.02351283871158888;
                                attribute Ixz : Real = 0.09063436123285354;
                                attribute 'σ_Ixz' : Real = 0.022566176940390956;
                                attribute Iyz : Real = 0.018272587087929896;
                                attribute 'σ_Iyz' : Real = 0.02209918015384651;
                            }
                            part <'C.1.2.3.5.3.2.2'> 'Part 1259' {
                                attribute POIconv : String = "-";
                                attribute Ipoint : Boolean = false;
                                attribute mass : Real = 0.3967228453371208;
                                attribute 'σ_mass' : Real = 0.28909372274994966;
                                attribute Cx : Real = -39.45915508083999;
                                attribute 'σ_Cx' : Real = 28.721044428837228;
                                attribute Cy : Real = 39.57333196885884;
                                attribute 'σ_Cy' : Real = 28.23690002309109;
                                attribute Cz : Real = -41.61475459113717;
                                attribute 'σ_Cz' : Real = 29.057750463592832;
                                attribute Ixx : Real = 0.46098099894650835;
                                attribute 'σ_Ixx' : Real = 0.37074144170588635;
                                attribute Iyy : Real = 0.5215819349007708;
                                attribute 'σ_Iyy' : Real = 0.3723953238821935;
                                attribute Izz : Real = 0.4648527426251887;
                                attribute 'σ_Izz' : Real = 0.37017423652493897;
                                attribute Ixy : Real = 0.023408180701812185;
                                attribute 'σ_Ixy' : Real = 0.02351283871158888;
                                attribute Ixz : Real = -0.006842838268444533;
                                attribute 'σ_Ixz' : Real = 0.022566176940390956;
                                attribute Iyz : Real = 0.04806855519917744;
                                attribute 'σ_Iyz' : Real = 0.02209918015384651;
                            }
                        }
                        part <'C.1.2.3.5.3.3'> 'Subassembly 356' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.5.3.3.1'> 'Part 1260' {
                                attribute POIconv : String = "+";
                                attribute Ipoint : Boolean = false;
                                attribute mass : Real = 0.7011275064474903;
                                attribute 'σ_mass' : Real = 0.28909372274994966;
                                attribute Cx : Real = -66.1839063744992;
                                attribute 'σ_Cx' : Real = 28.721044428837228;
                                attribute Cy : Real = 8.027808088809252;
                                attribute 'σ_Cy' : Real = 28.23690002309109;
                                attribute Cz : Real = -78.1874118372798;
                                attribute 'σ_Cz' : Real = 29.057750463592832;
                                attribute Ixx : Real = 0.8246837649337543;
                                attribute 'σ_Ixx' : Real = 0.37074144170588635;
                                attribute Iyy : Real = 0.8229540591235416;
                                attribute 'σ_Iyy' : Real = 0.3723953238821935;
                                attribute Izz : Real = 0.8000623016461933;
                                attribute 'σ_Izz' : Real = 0.37017423652493897;
                                attribute Ixy : Real = -0.0032319440869591825;
                                attribute 'σ_Ixy' : Real = 0.02351283871158888;
                                attribute Ixz : Real = 0.007726934799492403;
                                attribute 'σ_Ixz' : Real = 0.022566176940390956;
                                attribute Iyz : Real = -0.014373984120215306;
                                attribute 'σ_Iyz' : Real = 0.02209918015384651;
                            }
                            part <'C.1.2.3.5.3.3.2'> 'Part 1261' {
                                attribute POIconv : String = "-";
                                attribute Ipoint : Boolean = false;
                                attribute mass : Real = 0.6089722820075695;
                                attribute 'σ_mass' : Real = 0.28909372274994966;
                                attribute Cx : Real = -56.18304922245443;
                                attribute 'σ_Cx' : Real = 28.721044428837228;
                                attribute Cy : Real = -60.97481483593583;
                                attribute 'σ_Cy' : Real = 28.23690002309109;
                                attribute Cz : Real = 36.10155996866524;
                                attribute 'σ_Cz' : Real = 29.057750463592832;
                                attribute Ixx : Real = 0.7827329456311622;
                                attribute 'σ_Ixx' : Real = 0.37074144170588635;
                                attribute Iyy : Real = 0.8547375049333515;
                                attribute 'σ_Iyy' : Real = 0.3723953238821935;
                                attribute Izz : Real = 0.8269510657506963;
                                attribute 'σ_Izz' : Real = 0.37017423652493897;
                                attribute Ixy : Real = 0.0436862200873175;
                                attribute 'σ_Ixy' : Real = 0.02351283871158888;
                                attribute Ixz : Real = 0.011838626742432367;
                                attribute 'σ_Ixz' : Real = 0.022566176940390956;
                                attribute Iyz : Real = -0.07517959808866224;
                                attribute 'σ_Iyz' : Real = 0.02209918015384651;
                            }
                            part <'C.1.2.3.5.3.3.3'> 'Part 1262' {
                                attribute POIconv : String = "-";
                                attribute Ipoint : Boolean = false;
                                attribute mass : Real = 0.4344434152622707;
                                attribute 'σ_mass' : Real = 0.28909372274994966;
                                attribute Cx : Real = 85.65983013249934;
                                attribute 'σ_Cx' : Real = 28.721044428837228;
                                attribute Cy : Real = 25.82510020583868;
                                attribute 'σ_Cy' : Real = 28.23690002309109;
                                attribute Cz : Real = 34.25372582860291;
                                attribute 'σ_Cz' : Real = 29.057750463592832;
                                attribute Ixx : Real = 0.43072646685810545;
                                attribute 'σ_Ixx' : Real = 0.37074144170588635;
                                attribute Iyy : Real = 0.4666613761837854;
                                attribute 'σ_Iyy' : Real = 0.3723953238821935;
                                attribute Izz : Real = 0.4943183701840302;
                                attribute 'σ_Izz' : Real = 0.37017423652493897;
                                attribute Ixy : Real = -0.03311439435726936;
                                attribute 'σ_Ixy' : Real = 0.02351283871158888;
                                attribute Ixz : Real = -0.025238821831793795;
                                attribute 'σ_Ixz' : Real = 0.022566176940390956;
                                attribute Iyz : Real = -0.017855909603244017;
                                attribute 'σ_Iyz' : Real = 0.02209918015384651;
                            }
                        }
                        part <'C.1.2.3.5.3.4'> 'Subassembly 357' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.5.3.4.1'> 'Part 1263' {
                                attribute POIconv : String = "-";
                                attribute Ipoint : Boolean = false;
                                attribute mass : Real = 0.12083789502293803;
                                attribute 'σ_mass' : Real = 0.28909372274994966;
                                attribute Cx : Real = 16.167417960241437;
                                attribute 'σ_Cx' : Real = 28.721044428837228;
                                attribute Cy : Real = 34.07032806426287;
                                attribute 'σ_Cy' : Real = 28.23690002309109;
                                attribute Cz : Real = 95.27612244710326;
                                attribute 'σ_Cz' : Real = 29.057750463592832;
                                attribute Ixx : Real = 0.16208459719037385;
                                attribute 'σ_Ixx' : Real = 0.37074144170588635;
                                attribute Iyy : Real = 0.1379671616600087;
                                attribute 'σ_Iyy' : Real = 0.3723953238821935;
                                attribute Izz : Real = 0.1608687897282162;
                                attribute 'σ_Izz' : Real = 0.37017423652493897;
                                attribute Ixy : Real = 0.007945272000720708;
                                attribute 'σ_Ixy' : Real = 0.02351283871158888;
                                attribute Ixz : Real = 1.940737438532174e-4;
                                attribute 'σ_Ixz' : Real = 0.022566176940390956;
                                attribute Iyz : Real = -5.141544973517658e-4;
                                attribute 'σ_Iyz' : Real = 0.02209918015384651;
                            }
                            part <'C.1.2.3.5.3.4.2'> 'Part 1264' {
                                attribute POIconv : String = "-";
                                attribute Ipoint : Boolean = false;
                                attribute mass : Real = 0.19884579942235722;
                                attribute 'σ_mass' : Real = 0.28909372274994966;
                                attribute Cx : Real = 71.2396068032831;
                                attribute 'σ_Cx' : Real = 28.721044428837228;
                                attribute Cy : Real = 36.51759293861687;
                                attribute 'σ_Cy' : Real = 28.23690002309109;
                                attribute Cz : Real = -83.5364740807563;
                                attribute 'σ_Cz' : Real = 29.057750463592832;
                                attribute Ixx : Real = 0.1789578156280865;
                                attribute 'σ_Ixx' : Real = 0.37074144170588635;
                                attribute Iyy : Real = 0.18341294754277443;
                                attribute 'σ_Iyy' : Real = 0.3723953238821935;
                                attribute Izz : Real = 0.17794810838382322;
                                attribute 'σ_Izz' : Real = 0.37017423652493897;
                                attribute Ixy : Real = -0.00300798546050413;
                                attribute 'σ_Ixy' : Real = 0.02351283871158888;
                                attribute Ixz : Real = -6.300995043304796e-4;
                                attribute 'σ_Ixz' : Real = 0.022566176940390956;
                                attribute Iyz : Real = 0.0033925289272170645;
                                attribute 'σ_Iyz' : Real = 0.02209918015384651;
                            }
                        }
                        part <'C.1.2.3.5.3.5'> 'Subassembly 358' {
                            attribute POIconv : String = "-";
                            attribute Ipoint : Boolean;
                            attribute mass : Real;
                            attribute 'σ_mass' : Real;
                            attribute Cx : Real;
                            attribute 'σ_Cx' : Real;
                            attribute Cy : Real;
                            attribute 'σ_Cy' : Real;
                            attribute Cz : Real;
                            attribute 'σ_Cz' : Real;
                            attribute Ixx : Real;
                            attribute 'σ_Ixx' : Real;
                            attribute Iyy : Real;
                            attribute 'σ_Iyy' : Real;
                            attribute Izz : Real;
                            attribute 'σ_Izz' : Real;
                            attribute Ixy : Real;
                            attribute 'σ_Ixy' : Real;
                            attribute Ixz : Real;
                            attribute 'σ_Ixz' : Real;
                            attribute Iyz : Real;
                            attribute 'σ_Iyz' : Real;
                            part <'C.1.2.3.5.3.5.1'> 'Part 1265' {
                                attribute POIconv : String = "-";
                                attribute Ipoint : Boolean = false;
                                attribute mass : Real = 0.42090389098459857;
                                attribute 'σ_mass' : Real = 0.28909372274994966;
                                attribute Cx : Real = -6.534124352037907;
                                attribute 'σ_Cx' : Real = 28.721044428837228;
                                attribute Cy : Real = 83.6108683142811;
                                attribute 'σ_Cy' : Real = 28.23690002309109;
                                attribute Cz : Real = 2.581757726147771;
                                attribute 'σ_Cz' : Real = 29.057750463592832;
                                attribute Ixx : Real = 0.5046761020634841;
                                attribute 'σ_Ixx' : Real = 0.37074144170588635;
                                attribute Iyy : Real = 0.6031403992323359;
                                attribute 'σ_Iyy' : Real = 0.3723953238821935;
                                attribute Izz : Real = 0.5702913065379649;
                                attribute 'σ_Izz' : Real = 0.37017423652493897;
                                attribute Ixy : Real = -0.005545422399502046;
                                attribute 'σ_Ixy' : Real = 0.02351283871158888;
                                attribute Ixz : Real = -0.03195887161427102;
                                attribute 'σ_Ixz' : Real = 0.022566176940390956;
                                attribute Iyz : Real = 0.045982303943210553;
                                attribute 'σ_Iyz' : Real = 0.02209918015384651;
                            }
                            part <'C.1.2.3.5.3.5.2'> 'Part 1266' {
                                attribute POIconv : String = "-";
                                attribute Ipoint : Boolean = false;
                                attribute mass : Real = 0.6296246529894415;
                                attribute 'σ_mass' : Real = 0.28909372274994966;
                                attribute Cx : Real = -57.72018609568477;
                                attribute 'σ_Cx' : Real = 28.721044428837228;
                                attribute Cy : Real = -22.049976931884885;
                                attribute 'σ_Cy' : Real = 28.23690002309109;
                                attribute Cz : Real = -91.82306164875627;
                                attribute 'σ_Cz' : Real = 29.057750463592832;
                                attribute Ixx : Real = 0.6231644456469169;
                                attribute 'σ_Ixx' : Real = 0.37074144170588635;
                                attribute Iyy : Real = 0.6628805997296834;
                                attribute 'σ_Iyy' : Real = 0.3723953238821935;
                                attribute Izz : Real = 0.6527029964441059;
                                attribute 'σ_Izz' : Real = 0.37017423652493897;
                                attribute Ixy : Real = 0.052228824100441454;
                                attribute 'σ_Ixy' : Real = 0.02351283871158888;
                                attribute Ixz : Real = -0.046873321509659616;
                                attribute 'σ_Ixz' : Real = 0.022566176940390956;
                                attribute Iyz : Real = 0.028349500091427567;
                                attribute 'σ_Iyz' : Real = 0.02209918015384651;
                            }
                            part <'C.1.2.3.5.3.5.3'> 'Part 1267' {
                                attribute POIconv : String = "+";
                                attribute Ipoint : Boolean = false;
                                attribute mass : Real = 0.1852113326715771;
                                attribute 'σ_mass' : Real = 0.28909372274994966;
                                attribute Cx : Real = 75.75643570162356;
                                attribute 'σ_Cx' : Real = 28.721044428837228;
                                attribute Cy : Real = -18.75137803144753;
                                attribute 'σ_Cy' : Real = 28.23690002309109;
                                attribute Cz : Real = -90.89313428848982;
                                attribute 'σ_Cz' : Real = 29.057750463592832;
                                attribute Ixx : Real = 0.2560248456709822;
                                attribute 'σ_Ixx' : Real = 0.37074144170588635;
                                attribute Iyy : Real = 0.26465729564891216;
                                attribute 'σ_Iyy' : Real = 0.3723953238821935;
                                attribute Izz : Real = 0.25143480489790515;
                                attribute 'σ_Izz' : Real = 0.37017423652493897;
                                attribute Ixy : Real = 0.01376368747788926;
                                attribute 'σ_Ixy' : Real = 0.02351283871158888;
                                attribute Ixz : Real = 0.007029625680584375;
                                attribute 'σ_Ixz' : Real = 0.022566176940390956;
                                attribute Iyz : Real = -0.008164116654090416;
                                attribute 'σ_Iyz' : Real = 0.02209918015384651;
                            }
                        }
                    }
                }
            }
        }
    }

}
