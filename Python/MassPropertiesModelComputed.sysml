package MassPropertiesModelComputed {
    private import ScalarValues::Boolean;
    private import ScalarValues::Real;
    private import ScalarValues::String;

    part <'C.1'> 'System 1' {
        attribute POIconv : String = "-";
        attribute Ipoint : Boolean = false;
        attribute mass : Real = 639.0103349237929;
        attribute sigma_mass : Real = 10.29027471624782;
        attribute Cx : Real = -0.4652566134301631;
        attribute sigma_Cx : Real = 1.3761535263664577;
        attribute Cy : Real = -0.8895186926913492;
        attribute sigma_Cy : Real = 1.3398906654200435;
        attribute Cz : Real = 0.1697844839726794;
        attribute sigma_Cz : Real = 1.3627992165359768;
        attribute Ixx : Real = 4087389.6343959933;
        attribute sigma_Ixx : Real = 130263.28452541346;
        attribute Iyy : Real = 4214116.008991565;
        attribute sigma_Iyy : Real = 134731.9812053999;
        attribute Izz : Real = 4158436.613697667;
        attribute sigma_Izz : Real = 133559.45218357517;
        attribute Ixy : Real = -89412.81361726798;
        attribute sigma_Ixy : Real = 62003.63855371233;
        attribute Ixz : Real = -42184.240893756156;
        attribute sigma_Ixz : Real = 62759.64381263537;
        attribute Iyz : Real = -46461.97996986614;
        attribute sigma_Iyz : Real = 61185.295675813286;
        part <'C.1.1'> 'Segment 1' {
            attribute POIconv : String = "-";
            attribute Ipoint : Boolean = false;
            attribute mass : Real = 372.62377527500854;
            attribute sigma_mass : Real = 7.810882267029767;
            attribute Cx : Real = 0.29500406241751576;
            attribute sigma_Cx : Real = 1.7952120275301782;
            attribute Cy : Real = -0.38006993879987255;
            attribute sigma_Cy : Real = 1.7394640481744439;
            attribute Cz : Real = -0.20519019605504557;
            attribute sigma_Cz : Real = 1.7713487656890816;
            attribute Ixx : Real = 2328069.8267189884;
            attribute sigma_Ixx : Real = 97529.57430415497;
            attribute Iyy : Real = 2435839.4699866404;
            attribute sigma_Iyy : Real = 102000.49375378032;
            attribute Izz : Real = 2394809.2253805567;
            attribute sigma_Izz : Real = 100872.6324183872;
            attribute Ixy : Real = -69096.99304471878;
            attribute sigma_Ixy : Real = 46928.44521912959;
            attribute Ixz : Real = -20216.144481108837;
            attribute sigma_Ixz : Real = 47564.4989690206;
            attribute Iyz : Real = -1746.0492371616165;
            attribute sigma_Iyz : Real = 45787.68012296459;
            part <'C.1.1.1'> 'Element 1' {
                attribute POIconv : String = "-";
                attribute Ipoint : Boolean = false;
                attribute mass : Real = 47.75851407979661;
                attribute sigma_mass : Real = 2.6964867339573457;
                attribute Cx : Real = 12.529872840432589;
                attribute sigma_Cx : Real = 5.049204230547871;
                attribute Cy : Real = -3.8107196414578595;
                attribute sigma_Cy : Real = 4.843551973280654;
                attribute Cz : Real = -5.514181394877913;
                attribute sigma_Cz : Real = 4.750347209297229;
                attribute Ixx : Real = 300979.324670833;
                attribute sigma_Ixx : Real = 33514.999784521984;
                attribute Iyy : Real = 310618.16300882155;
                attribute sigma_Iyy : Real = 35589.3648641232;
                attribute Izz : Real = 333367.95175749017;
                attribute sigma_Izz : Real = 36850.00248452121;
                attribute Ixy : Real = -16907.42737942391;
                attribute sigma_Ixy : Real = 17518.21076712086;
                attribute Ixz : Real = -8415.841141076155;
                attribute sigma_Ixz : Real = 16933.707689874387;
                attribute Iyz : Real = 22173.215503814303;
                attribute sigma_Iyz : Real = 15964.650593400556;
                part <'C.1.1.1.1'> 'Subsystem 1' {
                    attribute POIconv : String = "-";
                    attribute Ipoint : Boolean = false;
                    attribute mass : Real = 26.993326929193923;
                    attribute sigma_mass : Real = 2.0029000638085734;
                    attribute Cx : Real = 16.51724204684185;
                    attribute sigma_Cx : Real = 6.307708131143107;
                    attribute Cy : Real = -4.410054065063986;
                    attribute sigma_Cy : Real = 6.415995892457973;
                    attribute Cz : Real = -12.523373425045156;
                    attribute sigma_Cz : Real = 6.352089624903942;
                    attribute Ixx : Real = 179074.0432237413;
                    attribute sigma_Ixx : Real = 25939.483828548757;
                    attribute Iyy : Real = 171936.91679449636;
                    attribute sigma_Iyy : Real = 24864.133002552677;
                    attribute Izz : Real = 182311.73669636794;
                    attribute sigma_Izz : Real = 25752.504001328733;
                    attribute Ixy : Real = -6117.042248359788;
                    attribute sigma_Ixy : Real = 12501.638248881874;
                    attribute Ixz : Real = 2202.460905348248;
                    attribute sigma_Ixz : Real = 12136.189103944484;
                    attribute Iyz : Real = 4478.7717382724995;
                    attribute sigma_Iyz : Real = 12315.527038658633;
                    part <'C.1.1.1.1.1'> 'Assembly 1' {
                        attribute POIconv : String = "-";
                        attribute Ipoint : Boolean = false;
                        attribute mass : Real = 9.437501752843614;
                        attribute sigma_mass : Real = 1.2265207905297184;
                        attribute Cx : Real = 26.380995001105052;
                        attribute sigma_Cx : Real = 10.757115819880168;
                        attribute Cy : Real = -5.7913636372700426;
                        attribute sigma_Cy : Real = 10.687129576114337;
                        attribute Cz : Real = -20.23583989470241;
                        attribute sigma_Cz : Real = 10.582143618772712;
                        attribute Ixx : Real = 53865.61128873449;
                        attribute sigma_Ixx : Real = 13753.284148337554;
                        attribute Iyy : Real = 50022.51529151407;
                        attribute sigma_Iyy : Real = 13209.458270438421;
                        attribute Izz : Real = 57628.543575058204;
                        attribute sigma_Izz : Real = 14504.896416618969;
                        attribute Ixy : Real = -8993.68538739472;
                        attribute sigma_Ixy : Real = 7101.262500825364;
                        attribute Ixz : Real = 7006.987410213221;
                        attribute sigma_Ixz : Real = 6344.185262278462;
                        attribute Iyz : Real = 8741.831091673452;
                        attribute sigma_Iyz : Real = 6437.07416913134;
                        part <'C.1.1.1.1.1.1'> 'Subassembly 1' {
                            attribute POIconv : String = "-";
                            attribute Ipoint : Boolean = false;
                            attribute mass : Real = 1.1105671058557927;
                            attribute sigma_mass : Real = 0.5007250159521434;
                            attribute Cx : Real = -22.59712751387718;
                            attribute sigma_Cx : Real = 21.378071040097886;
                            attribute Cy : Real = 0.6519388317155196;
                            attribute sigma_Cy : Real = 28.277428347850392;
                            attribute Cz : Real = -37.726965003630134;
                            attribute sigma_Cz : Real = 33.42610120259329;
                            attribute Ixx : Real = 3081.9879435164135;
                            attribute sigma_Ixx : Real = 3533.6534950467817;
                            attribute Iyy : Real = 2032.9517847252766;
                            attribute sigma_Iyy : Real = 2817.6476626806116;
                            attribute Izz : Real = 1192.9402500866536;
                            attribute sigma_Izz : Real = 1756.98388743211;
                            attribute Ixy : Real = -263.3066091135466;
                            attribute sigma_Ixy : Real = 617.0514604668992;
                            attribute Ixz : Real = 212.1579148435338;
                            attribute sigma_Ixz : Real = 727.6503930263974;
                            attribute Iyz : Real = 339.2900450504472;
                            attribute sigma_Iyz : Real = 1296.2797686582057;
                            part <'C.1.1.1.1.1.1.1'> 'Part 1' {
                                attribute POIconv : String = "+";
                                attribute Ipoint : Boolean = false;
                                attribute mass : Real = 0.1521751119736582;
                                attribute sigma_mass : Real = 0.28909372274994966;
                                attribute Cx : Real = -34.29865841753781;
                                attribute sigma_Cx : Real = 28.721044428837228;
                                attribute Cy : Real = -66.12854544073343;
                                attribute sigma_Cy : Real = 28.23690002309109;
                                attribute Cz : Real = -73.53497515432537;
                                attribute sigma_Cz : Real = 29.057750463592832;
                                attribute Ixx : Real = 0.18346195470478338;
                                attribute sigma_Ixx : Real = 0.37074144170588635;
                                attribute Iyy : Real = 0.15837006341318408;
                                attribute sigma_Iyy : Real = 0.3723953238821935;
                                attribute Izz : Real = 0.18470199509290466;
                                attribute sigma_Izz : Real = 0.37017423652493897;
                                attribute Ixy : Real = 0.0037985231754760324;
                                attribute sigma_Ixy : Real = 0.02351283871158888;
                                attribute Ixz : Real = 0.0037582877147340657;
                                attribute sigma_Ixz : Real = 0.022566176940390956;
                                attribute Iyz : Real = -0.014017164148438758;
                                attribute sigma_Iyz : Real = 0.02209918015384651;
                            }
                            part <'C.1.1.1.1.1.1.2'> 'Part 2' {
                                attribute POIconv : String = "+";
                                attribute Ipoint : Boolean = false;
                                attribute mass : Real = 0.18868499795440585;
                                attribute sigma_mass : Real = 0.28909372274994966;
                                attribute Cx : Real = -34.91070759482682;
                                attribute sigma_Cx : Real = 28.721044428837228;
                                attribute Cy : Real = -26.443653739988804;
                                attribute sigma_Cy : Real = 28.23690002309109;
                                attribute Cz : Real = 53.87474172748625;
                                attribute sigma_Cz : Real = 29.057750463592832;
                                attribute Ixx : Real = 0.27656684418566047;
                                attribute sigma_Ixx : Real = 0.37074144170588635;
                                attribute Iyy : Real = 0.27637506714868143;
                                attribute sigma_Iyy : Real = 0.3723953238821935;
                                attribute Izz : Real = 0.27051180191523305;
                                attribute sigma_Izz : Real = 0.37017423652493897;
                                attribute Ixy : Real = 0.00778657987414301;
                                attribute sigma_Ixy : Real = 0.02351283871158888;
                                attribute Ixz : Real = -0.0023871384096893107;
                                attribute sigma_Ixz : Real = 0.022566176940390956;
                                attribute Iyz : Real = 0.00589012398047391;
                                attribute sigma_Iyz : Real = 0.02209918015384651;
                            }
                            part <'C.1.1.1.1.1.1.3'> 'Part 3' {
                                attribute POIconv : String = "+";
                                attribute Ipoint : Boolean = false;
                                attribute mass : Real = 0.7697069959277287;
                                attribute sigma_mass : Real = 0.28909372274994966;
                                attribute Cx : Real = -17.265138030052185;
                                attribute sigma_Cx : Real = 28.721044428837228;
                                attribute Cy : Real = 20.49697022885084;
                                attribute sigma_Cy : Real = 28.23690002309109;
                                attribute Cz : Real = -53.10265985317528;
                                attribute sigma_Cz : Real = 29.057750463592832;
                                attribute Ixx : Real = 0.904850891478444;
                                attribute sigma_Ixx : Real = 0.37074144170588635;
                                attribute Iyy : Real = 0.867503905740675;
                                attribute sigma_Iyy : Real = 0.3723953238821935;
                                attribute Izz : Real = 0.853946253806776;
                                attribute sigma_Izz : Real = 0.37017423652493897;
                                attribute Ixy : Real = -0.01872761180810094;
                                attribute sigma_Ixy : Real = 0.02351283871158888;
                                attribute Ixz : Real = 0.007255691281044883;
                                attribute sigma_Ixz : Real = 0.022566176940390956;
                                attribute Iyz : Real = 0.003569366743797703;
                                attribute sigma_Iyz : Real = 0.02209918015384651;
                            }
                        }
                        part <'C.1.1.1.1.1.2'> 'Subassembly 2' {
                            attribute POIconv : String = "-";
                            attribute Ipoint : Boolean = false;
                            attribute mass : Real = 3.533991458012024;
                            attribute sigma_mass : Real = 0.6464332159373649;
                            attribute Cx : Real = 45.51221382740256;
                            attribute sigma_Cx : Real = 14.459549506662363;
                            attribute Cy : Real = -8.434676996940743;
                            attribute sigma_Cy : Real = 17.006032342691423;
                            attribute Cz : Real = -34.03026889557729;
                            attribute sigma_Cz : Real = 15.77020918047544;
                            attribute Ixx : Real = 13226.998955098521;
                            attribute sigma_Ixx : Real = 6660.425305738779;
                            attribute Iyy : Real = 6738.93620355943;
                            attribute sigma_Iyy : Real = 4454.52402749815;
                            attribute Izz : Real = 10394.45727085018;
                            attribute sigma_Izz : Real = 5891.823440456941;
                            attribute Ixy : Real = -333.4752438434008;
                            attribute sigma_Ixy : Real = 2695.9111933124373;
                            attribute Ixz : Real = -385.1697561022531;
                            attribute sigma_Ixz : Real = 2126.055643887889;
                            attribute Iyz : Real = -2351.6703557374262;
                            attribute sigma_Iyz : Real = 3123.055642175128;
                            part <'C.1.1.1.1.1.2.1'> 'Part 4' {
                                attribute POIconv : String = "+";
                                attribute Ipoint : Boolean = false;
                                attribute mass : Real = 0.1454309616452083;
                                attribute sigma_mass : Real = 0.28909372274994966;
                                attribute Cx : Real = 41.68215095996857;
                                attribute sigma_Cx : Real = 28.721044428837228;
                                attribute Cy : Real = -91.38107933104038;
                                attribute sigma_Cy : Real = 28.23690002309109;
                                attribute Cz : Real = -68.34089234471321;
                                attribute sigma_Cz : Real = 29.057750463592832;
                                attribute Ixx : Real = 0.1717862834362892;
                                attribute sigma_Ixx : Real = 0.37074144170588635;
                                attribute Iyy : Real = 0.20386716344036002;
                                attribute sigma_Iyy : Real = 0.3723953238821935;
                                attribute Izz : Real = 0.16809870997644813;
                                attribute sigma_Izz : Real = 0.37017423652493897;
                                attribute Ixy : Real = 0.006733403644455866;
                                attribute sigma_Ixy : Real = 0.02351283871158888;
                                attribute Ixz : Real = -0.009373831223081025;
                                attribute sigma_Ixz : Real = 0.022566176940390956;
                                attribute Iyz : Real = -0.0005888376607972038;
                                attribute sigma_Iyz : Real = 0.02209918015384651;
                            }
                            part <'C.1.1.1.1.1.2.2'> 'Part 5' {
                                attribute POIconv : String = "-";
                                attribute Ipoint : Boolean = false;
                                attribute mass : Real = 0.9522862783651799;
                                attribute sigma_mass : Real = 0.28909372274994966;
                                attribute Cx : Real = 79.8512370325625;
                                attribute sigma_Cx : Real = 28.721044428837228;
                                attribute Cy : Real = 32.26179811172187;
                                attribute sigma_Cy : Real = 28.23690002309109;
                                attribute Cz : Real = -25.890729343518615;
                                attribute sigma_Cz : Real = 29.057750463592832;
                                attribute Ixx : Real = 1.2568463851420968;
                                attribute sigma_Ixx : Real = 0.37074144170588635;
                                attribute Iyy : Real = 1.1609834388077394;
                                attribute sigma_Iyy : Real = 0.3723953238821935;
                                attribute Izz : Real = 1.2267789861314367;
                                attribute sigma_Izz : Real = 0.37017423652493897;
                                attribute Ixy : Real = 0.005367798972772337;
                                attribute sigma_Ixy : Real = 0.02351283871158888;
                                attribute Ixz : Real = -0.013565949879023667;
                                attribute sigma_Ixz : Real = 0.022566176940390956;
                                attribute Iyz : Real = 0.10434382732355574;
                                attribute sigma_Iyz : Real = 0.02209918015384651;
                            }
                            part <'C.1.1.1.1.1.2.3'> 'Part 6' {
                                attribute POIconv : String = "+";
                                attribute Ipoint : Boolean = false;
                                attribute mass : Real = 0.8294994919870514;
                                attribute sigma_mass : Real = 0.28909372274994966;
                                attribute Cx : Real = 18.63987920805812;
                                attribute sigma_Cx : Real = 28.721044428837228;
                                attribute Cy : Real = 12.642979109659791;
                                attribute sigma_Cy : Real = 28.23690002309109;
                                attribute Cz : Real = -75.99323713220656;
                                attribute sigma_Cz : Real = 29.057750463592832;
                                attribute Ixx : Real = 0.7835029760668094;
                                attribute sigma_Ixx : Real = 0.37074144170588635;
                                attribute Iyy : Real = 0.7752406776518191;
                                attribute sigma_Iyy : Real = 0.3723953238821935;
                                attribute Izz : Real = 0.7801212941347628;
                                attribute sigma_Izz : Real = 0.37017423652493897;
                                attribute Ixy : Real = -0.0015970713176399714;
                                attribute sigma_Ixy : Real = 0.02351283871158888;
                                attribute Ixz : Real = -0.023550038977687725;
                                attribute sigma_Ixz : Real = 0.022566176940390956;
                                attribute Iyz : Real = 0.01137750065967411;
                                attribute sigma_Iyz : Real = 0.02209918015384651;
                            }
                            part <'C.1.1.1.1.1.2.4'> 'Part 7' {
                                attribute POIconv : String = "+";
                                attribute Ipoint : Boolean = false;
                                attribute mass : Real = 0.6792828879216686;
                                attribute sigma_mass : Real = 0.28909372274994966;
                                attribute Cx : Real = 27.477146219462156;
                                attribute sigma_Cx : Real = 28.721044428837228;
                                attribute Cy : Real = 24.369020108133554;
                                attribute sigma_Cy : Real = 28.23690002309109;
                                attribute Cz : Real = 31.537090241909027;
                                attribute sigma_Cz : Real = 29.057750463592832;
                                attribute Ixx : Real = 0.8372575836394387;
                                attribute sigma_Ixx : Real = 0.37074144170588635;
                                attribute Iyy : Real = 0.943580796291087;
                                attribute sigma_Iyy : Real = 0.3723953238821935;
                                attribute Izz : Real = 0.7879040587225734;
                                attribute sigma_Izz : Real = 0.37017423652493897;
                                attribute Ixy : Real = 0.0076169696805578994;
                                attribute sigma_Ixy : Real = 0.02351283871158888;
                                attribute Ixz : Real = -0.010881734663394874;
                                attribute sigma_Ixz : Real = 0.022566176940390956;
                                attribute Iyz : Real = -0.008582621063851836;
                                attribute sigma_Iyz : Real = 0.02209918015384651;
                            }
                            part <'C.1.1.1.1.1.2.5'> 'Part 8' {
                                attribute POIconv : String = "-";
                                attribute Ipoint : Boolean = false;
                                attribute mass : Real = 0.9274918380929157;
                                attribute sigma_mass : Real = 0.28909372274994966;
                                attribute Cx : Real = 48.09760567732155;
                                attribute sigma_Cx : Real = 28.721044428837228;
                                attribute Cy : Real = -80.08880070410669;
                                attribute sigma_Cy : Real = 28.23690002309109;
                                attribute Cz : Real = -47.49870989471674;
                                attribute sigma_Cz : Real = 29.057750463592832;
                                attribute Ixx : Real = 1.182191375767316;
                                attribute sigma_Ixx : Real = 0.37074144170588635;
                                attribute Iyy : Real = 1.1778809746036805;
                                attribute sigma_Iyy : Real = 0.3723953238821935;
                                attribute Izz : Real = 1.0313577602875554;
                                attribute sigma_Izz : Real = 0.37017423652493897;
                                attribute Ixy : Real = 0.0023185027804681546;
                                attribute sigma_Ixy : Real = 0.02351283871158888;
                                attribute Ixz : Real = -0.09811931207805208;
                                attribute sigma_Ixz : Real = 0.022566176940390956;
                                attribute Iyz : Real = 0.01526965162144308;
                                attribute sigma_Iyz : Real = 0.02209918015384651;
                            }
                        }
                        part <'C.1.1.1.1.1.3'> 'Subassembly 3' {
                            attribute POIconv : String = "-";
                            attribute Ipoint : Boolean = false;
                            attribute mass : Real = 1.5240703212746884;
                            attribute sigma_mass : Real = 0.5781874454998993;
                            attribute Cx : Real = 3.747498799896942;
                            attribute sigma_Cx : Real = 33.0817429141197;
                            attribute Cy : Real = 22.684730717091547;
                            attribute sigma_Cy : Real = 28.09116612996942;
                            attribute Cz : Real = -8.65185335717391;
                            attribute sigma_Cz : Real = 22.767000012088;
                            attribute Ixx : Real = 7887.680022351698;
                            attribute sigma_Ixx : Real = 4875.995017499665;
                            attribute Iyy : Real = 7947.797193183322;
                            attribute sigma_Iyy : Real = 5442.374886913716;
                            attribute Izz : Real = 14571.551627200179;
                            attribute sigma_Izz : Real = 7870.860954136013;
                            attribute Ixy : Real = -6345.674791524776;
                            attribute sigma_Ixy : Real = 3815.632569922191;
                            attribute Ixz : Real = -186.58439392363675;
                            attribute sigma_Ixz : Real = 2276.1693784272593;
                            attribute Iyz : Real = 788.8542509274569;
                            attribute sigma_Iyz : Real = 2024.8949047774067;
                            part <'C.1.1.1.1.1.3.1'> 'Part 9' {
                                attribute POIconv : String = "-";
                                attribute Ipoint : Boolean = false;
                                attribute mass : Real = 0.012705426325090228;
                                attribute sigma_mass : Real = 0.28909372274994966;
                                attribute Cx : Real = -61.86356646940112;
                                attribute sigma_Cx : Real = 28.721044428837228;
                                attribute Cy : Real = 39.72041537053883;
                                attribute sigma_Cy : Real = 28.23690002309109;
                                attribute Cz : Real = 39.86886125057936;
                                attribute sigma_Cz : Real = 29.057750463592832;
                                attribute Ixx : Real = 0.014102043535239485;
                                attribute sigma_Ixx : Real = 0.37074144170588635;
                                attribute Iyy : Real = 0.015186854591097613;
                                attribute sigma_Iyy : Real = 0.3723953238821935;
                                attribute Izz : Real = 0.015178208293440349;
                                attribute sigma_Izz : Real = 0.37017423652493897;
                                attribute Ixy : Real = -0.0007571641608683109;
                                attribute sigma_Ixy : Real = 0.02351283871158888;
                                attribute Ixz : Real = 0.0009218718164940613;
                                attribute sigma_Ixz : Real = 0.022566176940390956;
                                attribute Iyz : Real = 0.0009860125308335174;
                                attribute sigma_Iyz : Real = 0.02209918015384651;
                            }
                            part <'C.1.1.1.1.1.3.2'> 'Part 10' {
                                attribute POIconv : String = "+";
                                attribute Ipoint : Boolean = false;
                                attribute mass : Real = 0.8187970951176249;
                                attribute sigma_mass : Real = 0.28909372274994966;
                                attribute Cx : Real = 45.64918917603791;
                                attribute sigma_Cx : Real = 28.721044428837228;
                                attribute Cy : Real = 82.09767998196185;
                                attribute sigma_Cy : Real = 28.23690002309109;
                                attribute Cz : Real = -21.63806138560176;
                                attribute sigma_Cz : Real = 29.057750463592832;
                                attribute Ixx : Real = 0.7926596080396694;
                                attribute sigma_Ixx : Real = 0.37074144170588635;
                                attribute Iyy : Real = 0.7918937658538793;
                                attribute sigma_Iyy : Real = 0.3723953238821935;
                                attribute Izz : Real = 0.8374083084660802;
                                attribute sigma_Izz : Real = 0.37017423652493897;
                                attribute Ixy : Real = 0.005264876541506831;
                                attribute sigma_Ixy : Real = 0.02351283871158888;
                                attribute Ixz : Real = -0.022091082560101775;
                                attribute sigma_Ixz : Real = 0.022566176940390956;
                                attribute Iyz : Real = -0.03450787670732504;
                                attribute sigma_Iyz : Real = 0.02209918015384651;
                            }
                            part <'C.1.1.1.1.1.3.3'> 'Part 11' {
                                attribute POIconv : String = "-";
                                attribute Ipoint : Boolean = false;
                                attribute mass : Real = 0.48895880657131785;
                                attribute sigma_mass : Real = 0.28909372274994966;
                                attribute Cx : Real = -94.86765237525105;
                                attribute sigma_Cx : Real = 28.721044428837228;
                                attribute Cy : Real = -71.30342787131667;
                                attribute sigma_Cy : Real = 28.23690002309109;
                                attribute Cz : Real = -8.021717378869653;
                                attribute sigma_Cz : Real = 29.057750463592832;
                                attribute Ixx : Real = 0.6301673669658536;
                                attribute sigma_Ixx : Real = 0.37074144170588635;
                                attribute Iyy : Real = 0.5959242710680464;
                                attribute sigma_Iyy : Real = 0.3723953238821935;
                                attribute Izz : Real = 0.5951663723889477;
                                attribute sigma_Izz : Real = 0.37017423652493897;
                                attribute Ixy : Real = -0.005026221719268833;
                                attribute sigma_Ixy : Real = 0.02351283871158888;
                                attribute Ixz : Real = 0.011158228346530134;
                                attribute sigma_Ixz : Real = 0.022566176940390956;
                                attribute Iyz : Real = -0.004689767300963031;
                                attribute sigma_Iyz : Real = 0.02209918015384651;
                            }
                            part <'C.1.1.1.1.1.3.4'> 'Part 12' {
                                attribute POIconv : String = "-";
                                attribute Ipoint : Boolean = false;
                                attribute mass : Real = 0.20360899326065554;
                                attribute sigma_mass : Real = 0.28909372274994966;
                                attribute Cx : Real = 76.15776215679944;
                                attribute sigma_Cx : Real = 28.721044428837228;
                                attribute Cy : Real = 8.406097907572985;
                                attribute sigma_Cy : Real = 28.23690002309109;
                                attribute Cz : Real = 39.03013924136758;
                                attribute sigma_Cz : Real = 29.057750463592832;
                                attribute Ixx : Real = 0.3128143534696859;
                                attribute sigma_Ixx : Real = 0.37074144170588635;
                                attribute Iyy : Real = 0.3152177792644552;
                                attribute sigma_Iyy : Real = 0.3723953238821935;
                                attribute Izz : Real = 0.3127604152723791;
                                attribute sigma_Izz : Real = 0.37017423652493897;
                                attribute Ixy : Real = 0.008740178069113726;
                                attribute sigma_Ixy : Real = 0.02351283871158888;
                                attribute Ixz : Real = -0.0004100437388877678;
                                attribute sigma_Ixz : Real = 0.022566176940390956;
                                attribute Iyz : Real = 0.0009315418409794618;
                                attribute sigma_Iyz : Real = 0.02209918015384651;
                            }
                        }
                        part <'C.1.1.1.1.1.4'> 'Subassembly 4' {
                            attribute POIconv : String = "-";
                            attribute Ipoint : Boolean = false;
                            attribute mass : Real = 2.2265367471294013;
                            attribute sigma_mass : Real = 0.5781874454998993;
                            attribute Cx : Real = 62.91787128820371;
                            attribute sigma_Cx : Real = 20.54439432625212;
                            attribute Cy : Real = -23.6167068733304;
                            attribute sigma_Cy : Real = 21.984473858468657;
                            attribute Cz : Real = -16.770678126176293;
                            attribute sigma_Cz : Real = 23.690661234377497;
                            attribute Ixx : Real = 21452.835757143068;
                            attribute sigma_Ixx : Real = 8684.972038359549;
                            attribute Iyy : Real = 17437.775021104648;
                            attribute sigma_Iyy : Real = 7815.284031766267;
                            attribute Izz : Real = 16700.980849934997;
                            attribute sigma_Izz : Real = 7718.6110877902165;
                            attribute Ixy : Real = -4690.943761574751;
                            attribute sigma_Ixy : Real = 3687.9090653201174;
                            attribute Ixz : Real = 4558.481211013208;
                            attribute sigma_Ixz : Real = 3756.0943095114567;
                            attribute Iyz : Real = 8673.963401245011;
                            attribute sigma_Iyz : Real = 4269.18368004821;
                            part <'C.1.1.1.1.1.4.1'> 'Part 13' {
                                attribute POIconv : String = "-";
                                attribute Ipoint : Boolean = false;
                                attribute mass : Real = 0.3572169222852681;
                                attribute sigma_mass : Real = 0.28909372274994966;
                                attribute Cx : Real = 84.20433290302753;
                                attribute sigma_Cx : Real = 28.721044428837228;
                                attribute Cy : Real = -54.49259839951992;
                                attribute sigma_Cy : Real = 28.23690002309109;
                                attribute Cz : Real = -81.80367383174598;
                                attribute sigma_Cz : Real = 29.057750463592832;
                                attribute Ixx : Real = 0.47484915144953266;
                                attribute sigma_Ixx : Real = 0.37074144170588635;
                                attribute Iyy : Real = 0.5360134926434229;
                                attribute sigma_Iyy : Real = 0.3723953238821935;
                                attribute Izz : Real = 0.42690188421355063;
                                attribute sigma_Izz : Real = 0.37017423652493897;
                                attribute Ixy : Real = -0.040837676934439904;
                                attribute sigma_Ixy : Real = 0.02351283871158888;
                                attribute Ixz : Real = 0.008546856401091856;
                                attribute sigma_Ixz : Real = 0.022566176940390956;
                                attribute Iyz : Real = -0.006819686196795118;
                                attribute sigma_Iyz : Real = 0.02209918015384651;
                            }
                            part <'C.1.1.1.1.1.4.2'> 'Part 14' {
                                attribute POIconv : String = "+";
                                attribute Ipoint : Boolean = false;
                                attribute mass : Real = 0.5571071715857834;
                                attribute sigma_mass : Real = 0.28909372274994966;
                                attribute Cx : Real = 99.08350468613207;
                                attribute sigma_Cx : Real = 28.721044428837228;
                                attribute Cy : Real = -62.094857916235924;
                                attribute sigma_Cy : Real = 28.23690002309109;
                                attribute Cz : Real = 51.5940326731652;
                                attribute sigma_Cz : Real = 29.057750463592832;
                                attribute Ixx : Real = 0.7362727185191851;
                                attribute sigma_Ixx : Real = 0.37074144170588635;
                                attribute Iyy : Real = 0.768145720247189;
                                attribute sigma_Iyy : Real = 0.3723953238821935;
                                attribute Izz : Real = 0.7087226870067952;
                                attribute sigma_Izz : Real = 0.37017423652493897;
                                attribute Ixy : Real = -0.0596578707553419;
                                attribute sigma_Ixy : Real = 0.02351283871158888;
                                attribute Ixz : Real = 0.014016170605811895;
                                attribute sigma_Ixz : Real = 0.022566176940390956;
                                attribute Iyz : Real = 0.023145325843034623;
                                attribute sigma_Iyz : Real = 0.02209918015384651;
                            }
                            part <'C.1.1.1.1.1.4.3'> 'Part 15' {
                                attribute POIconv : String = "-";
                                attribute Ipoint : Boolean = false;
                                attribute mass : Real = 0.5190961779379286;
                                attribute sigma_mass : Real = 0.28909372274994966;
                                attribute Cx : Real = -33.48792656324804;
                                attribute sigma_Cx : Real = 28.721044428837228;
                                attribute Cy : Real = -97.70168159157038;
                                attribute sigma_Cy : Real = 28.23690002309109;
                                attribute Cz : Real = 60.95813768915832;
                                attribute sigma_Cz : Real = 29.057750463592832;
                                attribute Ixx : Real = 0.6284872739303747;
                                attribute sigma_Ixx : Real = 0.37074144170588635;
                                attribute Iyy : Real = 0.5800037008023744;
                                attribute sigma_Iyy : Real = 0.3723953238821935;
                                attribute Izz : Real = 0.6021852105108795;
                                attribute sigma_Izz : Real = 0.37017423652493897;
                                attribute Ixy : Real = -0.047508415561734615;
                                attribute sigma_Ixy : Real = 0.02351283871158888;
                                attribute Ixz : Real = -0.0014863199142704706;
                                attribute sigma_Ixz : Real = 0.022566176940390956;
                                attribute Iyz : Real = -0.004023124277438803;
                                attribute sigma_Iyz : Real = 0.02209918015384651;
                            }
                            part <'C.1.1.1.1.1.4.4'> 'Part 16' {
                                attribute POIconv : String = "+";
                                attribute Ipoint : Boolean = false;
                                attribute mass : Real = 0.7931164753204212;
                                attribute sigma_mass : Real = 0.28909372274994966;
                                attribute Cx : Real = 91.02454143576324;
                                attribute sigma_Cx : Real = 28.721044428837228;
                                attribute Cy : Real = 65.8065673429519;
                                attribute sigma_Cy : Real = 28.23690002309109;
                                attribute Cz : Real = -86.37497588060796;
                                attribute sigma_Cz : Real = 29.057750463592832;
                                attribute Ixx : Real = 1.0813363570354253;
                                attribute sigma_Ixx : Real = 0.37074144170588635;
                                attribute Iyy : Real = 1.0293142713537367;
                                attribute sigma_Iyy : Real = 0.3723953238821935;
                                attribute Izz : Real = 0.9894751949948105;
                                attribute sigma_Izz : Real = 0.37017423652493897;
                                attribute Ixy : Real = 0.043647868381421054;
                                attribute sigma_Ixy : Real = 0.02351283871158888;
                                attribute Ixz : Real = 0.054978072317282925;
                                attribute sigma_Ixz : Real = 0.022566176940390956;
                                attribute Iyz : Real = 0.010604305309151851;
                                attribute sigma_Iyz : Real = 0.02209918015384651;
                            }
                        }
                        part <'C.1.1.1.1.1.5'> 'Subassembly 5' {
                            attribute POIconv : String = "-";
                            attribute Ipoint : Boolean = false;
                            attribute mass : Real = 1.0423361205717083;
                            attribute sigma_mass : Real = 0.40884026350990615;
                            attribute Cx : Real = -31.250827218039323;
                            attribute sigma_Cx : Real = 22.903355671978115;
                            attribute Cy : Real = -7.254482334903096;
                            attribute sigma_Cy : Real = 29.641953525313756;
                            attribute Cz : Real = 20.829936783829012;
                            attribute sigma_Cz : Real = 30.586396685662915;
                            attribute Ixx : Real = 3198.4842119738955;
                            attribute sigma_Ixx : Real = 3360.4413437767084;
                            attribute Iyy : Real = 1691.1458303613692;
                            attribute sigma_Iyy : Real = 2058.178885077754;
                            attribute Izz : Real = 1579.6355185129705;
                            attribute sigma_Izz : Real = 1928.5527149519867;
                            attribute Ixy : Real = -233.96801083184585;
                            attribute sigma_Ixy : Real = 739.3249417116122;
                            attribute Ixz : Real = 242.28147675859674;
                            attribute sigma_Ixz : Real = 765.4841311954159;
                            attribute Iyz : Real = 1597.6762404526467;
                            attribute sigma_Iyz : Real = 1678.9598648050537;
                            part <'C.1.1.1.1.1.5.1'> 'Part 17' {
                                attribute POIconv : String = "+";
                                attribute Ipoint : Boolean = false;
                                attribute mass : Real = 0.26025292832637203;
                                attribute sigma_mass : Real = 0.28909372274994966;
                                attribute Cx : Real = -41.36475306004286;
                                attribute sigma_Cx : Real = 28.721044428837228;
                                attribute Cy : Real = -73.9494463428855;
                                attribute sigma_Cy : Real = 28.23690002309109;
                                attribute Cz : Real = 89.89339577965438;
                                attribute sigma_Cz : Real = 29.057750463592832;
                                attribute Ixx : Real = 0.3116709562430628;
                                attribute sigma_Ixx : Real = 0.37074144170588635;
                                attribute Iyy : Real = 0.3530933369496171;
                                attribute sigma_Iyy : Real = 0.3723953238821935;
                                attribute Izz : Real = 0.2972344682989129;
                                attribute sigma_Izz : Real = 0.37017423652493897;
                                attribute Ixy : Real = 0.0018383202757886082;
                                attribute sigma_Ixy : Real = 0.02351283871158888;
                                attribute Ixz : Real = 0.01412175398157994;
                                attribute sigma_Ixz : Real = 0.022566176940390956;
                                attribute Iyz : Real = -0.018449147825117758;
                                attribute sigma_Iyz : Real = 0.02209918015384651;
                            }
                            part <'C.1.1.1.1.1.5.2'> 'Part 18' {
                                attribute POIconv : String = "-";
                                attribute Ipoint : Boolean = false;
                                attribute mass : Real = 0.7820831922453363;
                                attribute sigma_mass : Real = 0.28909372274994966;
                                attribute Cx : Real = -27.885227696970105;
                                attribute sigma_Cx : Real = 28.721044428837228;
                                attribute Cy : Real = 14.93952446617186;
                                attribute sigma_Cy : Real = 28.23690002309109;
                                attribute Cz : Real = -2.1522313822060823;
                                attribute sigma_Cz : Real = 29.057750463592832;
                                attribute Ixx : Real = 0.8518186503340801;
                                attribute sigma_Ixx : Real = 0.37074144170588635;
                                attribute Iyy : Real = 0.8871099261236091;
                                attribute sigma_Iyy : Real = 0.3723953238821935;
                                attribute Izz : Real = 0.9621465209277352;
                                attribute sigma_Izz : Real = 0.37017423652493897;
                                attribute Ixy : Real = 0.005493539823235515;
                                attribute sigma_Ixy : Real = 0.02351283871158888;
                                attribute Ixz : Real = 0.015048475976331601;
                                attribute sigma_Ixz : Real = 0.022566176940390956;
                                attribute Iyz : Real = -0.029676148897113057;
                                attribute sigma_Iyz : Real = 0.02209918015384651;
                            }
                        }
                    }
                    part <'C.1.1.1.1.2'> 'Assembly 2' {
                        attribute POIconv : String = "-";
                        attribute Ipoint : Boolean = false;
                        attribute mass : Real = 12.074115218328778;
                        attribute sigma_mass : Real = 1.260130322678996;
                        attribute Cx : Real = 19.49444948066113;
                        attribute sigma_Cx : Real = 9.129735523017954;
                        attribute Cy : Real = -2.6476350086084723;
                        attribute sigma_Cy : Real = 9.308119778903391;
                        attribute Cz : Real = -8.343041051529594;
                        attribute sigma_Cz : Real = 10.061598834281977;
                        attribute Ixx : Real = 90835.7697635496;
                        attribute sigma_Ixx : Real = 18886.686068798645;
                        attribute Iyy : Real = 91887.83070209181;
                        attribute sigma_Iyy : Real = 18486.22756268305;
                        attribute Izz : Real = 76673.1261486362;
                        attribute sigma_Izz : Real = 17158.237456653314;
                        attribute Ixy : Real = 9505.22599408994;
                        attribute sigma_Ixy : Real = 7927.96595325297;
                        attribute Ixz : Real = -3872.93763754308;
                        attribute sigma_Ixz : Real = 9090.960828588048;
                        attribute Iyz : Real = 1166.563536316694;
                        attribute sigma_Iyz : Real = 9097.194738660915;
                        part <'C.1.1.1.1.2.1'> 'Subassembly 6' {
                            attribute POIconv : String = "-";
                            attribute Ipoint : Boolean = false;
                            attribute mass : Real = 2.135799898905214;
                            attribute sigma_mass : Real = 0.5007250159521434;
                            attribute Cx : Real = 21.27962729349213;
                            attribute sigma_Cx : Real = 25.13052003512201;
                            attribute Cy : Real = 37.09393925739985;
                            attribute sigma_Cy : Real = 24.98534987196899;
                            attribute Cz : Real = -4.542134288912079;
                            attribute sigma_Cz : Real = 23.793643657363077;
                            attribute Ixx : Real = 19639.52424259323;
                            attribute sigma_Ixx : Real = 9730.412585635198;
                            attribute Iyy : Real = 22920.812356454742;
                            attribute sigma_Iyy : Real = 9660.28312040128;
                            attribute Izz : Real = 24596.207549018607;
                            attribute sigma_Izz : Real = 10052.138808363978;
                            attribute Ixy : Real = 4135.694627272493;
                            attribute sigma_Ixy : Real = 4351.628985128218;
                            attribute Ixz : Real = -9177.125254541555;
                            attribute sigma_Ixz : Real = 4621.599378366162;
                            attribute Iyz : Real = 7986.708360963796;
                            attribute sigma_Iyz : Real = 4721.601881399361;
                            part <'C.1.1.1.1.2.1.1'> 'Part 19' {
                                attribute POIconv : String = "+";
                                attribute Ipoint : Boolean = false;
                                attribute mass : Real = 0.5135785475107841;
                                attribute sigma_mass : Real = 0.28909372274994966;
                                attribute Cx : Real = 70.91835285536945;
                                attribute sigma_Cx : Real = 28.721044428837228;
                                attribute Cy : Real = -88.44160186126828;
                                attribute sigma_Cy : Real = 28.23690002309109;
                                attribute Cz : Real = 89.99599302187562;
                                attribute sigma_Cz : Real = 29.057750463592832;
                                attribute Ixx : Real = 0.5418073046051372;
                                attribute sigma_Ixx : Real = 0.37074144170588635;
                                attribute Iyy : Real = 0.5932172548868199;
                                attribute sigma_Iyy : Real = 0.3723953238821935;
                                attribute Izz : Real = 0.5824304131793494;
                                attribute sigma_Izz : Real = 0.37017423652493897;
                                attribute Ixy : Real = 0.0016399993397964328;
                                attribute sigma_Ixy : Real = 0.02351283871158888;
                                attribute Ixz : Real = -0.017114214656449286;
                                attribute sigma_Ixz : Real = 0.022566176940390956;
                                attribute Iyz : Real = -0.0011244915949632785;
                                attribute sigma_Iyz : Real = 0.02209918015384651;
                            }
                            part <'C.1.1.1.1.2.1.2'> 'Part 20' {
                                attribute POIconv : String = "-";
                                attribute Ipoint : Boolean = false;
                                attribute mass : Real = 0.7413986765367444;
                                attribute sigma_mass : Real = 0.28909372274994966;
                                attribute Cx : Real = -89.23627063632011;
                                attribute sigma_Cx : Real = 28.721044428837228;
                                attribute Cy : Real = 76.23628829605877;
                                attribute sigma_Cy : Real = 28.23690002309109;
                                attribute Cz : Real = -80.8549493085593;
                                attribute sigma_Cz : Real = 29.057750463592832;
                                attribute Ixx : Real = 0.7888714458993766;
                                attribute sigma_Ixx : Real = 0.37074144170588635;
                                attribute Iyy : Real = 0.8292074355111392;
                                attribute sigma_Iyy : Real = 0.3723953238821935;
                                attribute Izz : Real = 0.7861894780092485;
                                attribute sigma_Izz : Real = 0.37017423652493897;
                                attribute Ixy : Real = -0.008352315737316422;
                                attribute sigma_Ixy : Real = 0.02351283871158888;
                                attribute Ixz : Real = 0.032743987892089356;
                                attribute sigma_Ixz : Real = 0.022566176940390956;
                                attribute Iyz : Real = 0.007893626385324908;
                                attribute sigma_Iyz : Real = 0.02209918015384651;
                            }
                            part <'C.1.1.1.1.2.1.3'> 'Part 21' {
                                attribute POIconv : String = "-";
                                attribute Ipoint : Boolean = false;
                                attribute mass : Real = 0.8808226748576854;
                                attribute sigma_mass : Real = 0.28909372274994966;
                                attribute Cx : Real = 85.35944437608123;
                                attribute sigma_Cx : Real = 28.721044428837228;
                                attribute Cy : Real = 77.34298836439848;
                                attribute sigma_Cy : Real = 28.23690002309109;
                                attribute Cz : Real = 4.569195583462715;
                                attribute sigma_Cz : Real = 29.057750463592832;
                                attribute Ixx : Real = 0.9338089361498445;
                                attribute sigma_Ixx : Real = 0.37074144170588635;
                                attribute Iyy : Real = 0.9559248959713871;
                                attribute sigma_Iyy : Real = 0.3723953238821935;
                                attribute Izz : Real = 0.8498839843522831;
                                attribute sigma_Izz : Real = 0.37017423652493897;
                                attribute Ixy : Real = -0.026741949099851788;
                                attribute sigma_Ixy : Real = 0.02351283871158888;
                                attribute Ixz : Real = -0.015093191609550995;
                                attribute sigma_Ixz : Real = 0.022566176940390956;
                                attribute Iyz : Real = 0.016018618533133334;
                                attribute sigma_Iyz : Real = 0.02209918015384651;
                            }
                        }
                        part <'C.1.1.1.1.2.2'> 'Subassembly 7' {
                            attribute POIconv : String = "-";
                            attribute Ipoint : Boolean = false;
                            attribute mass : Real = 2.2437645727037454;
                            attribute sigma_mass : Real = 0.5007250159521434;
                            attribute Cx : Real = 41.432171790761416;
                            attribute sigma_Cx : Real = 17.470924911687874;
                            attribute Cy : Real = -6.25353734327174;
                            attribute sigma_Cy : Real = 18.169218867192246;
                            attribute Cz : Real = -32.76620841234531;
                            attribute sigma_Cz : Real = 20.380403891391257;
                            attribute Ixx : Real = 8701.059566897919;
                            attribute sigma_Ixx : Real = 5171.205661973612;
                            attribute Iyy : Real = 7489.402711606606;
                            attribute sigma_Iyy : Real = 4909.024254568417;
                            attribute Izz : Real = 3597.613133516679;
                            attribute sigma_Izz : Real = 3056.596000869344;
                            attribute Ixy : Real = 1025.4435944743445;
                            attribute sigma_Ixy : Real = 1502.9040300652318;
                            attribute Ixz : Real = 2710.506954224582;
                            attribute sigma_Ixz : Real = 2355.7574786638725;
                            attribute Iyz : Real = -1887.327090713583;
                            attribute sigma_Iyz : Real = 2460.031012980603;
                            part <'C.1.1.1.1.2.2.1'> 'Part 22' {
                                attribute POIconv : String = "-";
                                attribute Ipoint : Boolean = false;
                                attribute mass : Real = 0.7712820994718932;
                                attribute sigma_mass : Real = 0.28909372274994966;
                                attribute Cx : Real = 12.463552132248878;
                                attribute sigma_Cx : Real = 28.721044428837228;
                                attribute Cy : Real = 33.60808356665075;
                                attribute sigma_Cy : Real = 28.23690002309109;
                                attribute Cz : Real = 28.75491394661367;
                                attribute sigma_Cz : Real = 29.057750463592832;
                                attribute Ixx : Real = 0.9896094194201455;
                                attribute sigma_Ixx : Real = 0.37074144170588635;
                                attribute Iyy : Real = 0.9995423118036598;
                                attribute sigma_Iyy : Real = 0.3723953238821935;
                                attribute Izz : Real = 0.7714555629277365;
                                attribute sigma_Izz : Real = 0.37017423652493897;
                                attribute Ixy : Real = -0.042997255698823456;
                                attribute sigma_Ixy : Real = 0.02351283871158888;
                                attribute Ixz : Real = 0.01937819990961847;
                                attribute sigma_Ixz : Real = 0.022566176940390956;
                                attribute Iyz : Real = 0.04890118300263788;
                                attribute sigma_Iyz : Real = 0.02209918015384651;
                            }
                            part <'C.1.1.1.1.2.2.2'> 'Part 23' {
                                attribute POIconv : String = "-";
                                attribute Ipoint : Boolean = false;
                                attribute mass : Real = 0.6032088426768314;
                                attribute sigma_mass : Real = 0.28909372274994966;
                                attribute Cx : Real = 42.426528595387936;
                                attribute sigma_Cx : Real = 28.721044428837228;
                                attribute Cy : Real = -50.0353897921741;
                                attribute sigma_Cy : Real = 28.23690002309109;
                                attribute Cz : Real = -22.477717651054263;
                                attribute sigma_Cz : Real = 29.057750463592832;
                                attribute Ixx : Real = 0.6082759830375095;
                                attribute sigma_Ixx : Real = 0.37074144170588635;
                                attribute Iyy : Real = 0.7294572504843319;
                                attribute sigma_Iyy : Real = 0.3723953238821935;
                                attribute Izz : Real = 0.732360445450684;
                                attribute sigma_Izz : Real = 0.37017423652493897;
                                attribute Ixy : Real = 0.0864758372841277;
                                attribute sigma_Ixy : Real = 0.02351283871158888;
                                attribute Ixz : Real = -0.04663228031792355;
                                attribute sigma_Ixz : Real = 0.022566176940390956;
                                attribute Iyz : Real = 0.01064362876184336;
                                attribute sigma_Iyz : Real = 0.02209918015384651;
                            }
                            part <'C.1.1.1.1.2.2.3'> 'Part 24' {
                                attribute POIconv : String = "+";
                                attribute Ipoint : Boolean = false;
                                attribute mass : Real = 0.8692736305550206;
                                attribute sigma_mass : Real = 0.28909372274994966;
                                attribute Cx : Real = 66.44520820118487;
                                attribute sigma_Cx : Real = 28.721044428837228;
                                attribute Cy : Real = -11.240406800061464;
                                attribute sigma_Cy : Real = 28.23690002309109;
                                attribute Cz : Real = -94.49159284122288;
                                attribute sigma_Cz : Real = 29.057750463592832;
                                attribute Ixx : Real = 1.0648305957090487;
                                attribute sigma_Ixx : Real = 0.37074144170588635;
                                attribute Iyy : Real = 0.9793059901999447;
                                attribute sigma_Iyy : Real = 0.3723953238821935;
                                attribute Izz : Real = 0.9980270038897266;
                                attribute sigma_Izz : Real = 0.37017423652493897;
                                attribute Ixy : Real = -0.08187407144464187;
                                attribute sigma_Ixy : Real = 0.02351283871158888;
                                attribute Ixz : Real = -0.03451382343710634;
                                attribute sigma_Ixz : Real = 0.022566176940390956;
                                attribute Iyz : Real = 0.0853480077839882;
                                attribute sigma_Iyz : Real = 0.02209918015384651;
                            }
                        }
                        part <'C.1.1.1.1.2.3'> 'Subassembly 8' {
                            attribute POIconv : String = "-";
                            attribute Ipoint : Boolean = false;
                            attribute mass : Real = 3.3671419708817267;
                            attribute sigma_mass : Real = 0.6464332159373649;
                            attribute Cx : Real = 23.329743125296073;
                            attribute sigma_Cx : Real = 15.73537346911231;
                            attribute Cy : Real = -24.55577832580647;
                            attribute sigma_Cy : Real = 15.804271287079702;
                            attribute Cz : Real = -17.18827757457143;
                            attribute sigma_Cz : Real = 18.824189585208888;
                            attribute Ixx : Real = 24136.35257856896;
                            attribute sigma_Ixx : Real = 9264.814767232489;
                            attribute Iyy : Real = 22628.991692648073;
                            attribute sigma_Iyy : Real = 8964.594530201612;
                            attribute Izz : Real = 14484.483325897138;
                            attribute sigma_Izz : Real = 7031.085617685055;
                            attribute Ixy : Real = 4770.647597886474;
                            attribute sigma_Ixy : Real = 3470.1507347959737;
                            attribute Ixz : Real = -9014.682511645231;
                            attribute sigma_Ixz : Real = 4272.896779995865;
                            attribute Iyz : Real = 4972.147373209659;
                            attribute sigma_Iyz : Real = 4317.431166907114;
                            part <'C.1.1.1.1.2.3.1'> 'Part 25' {
                                attribute POIconv : String = "-";
                                attribute Ipoint : Boolean = false;
                                attribute mass : Real = 0.43263949803891594;
                                attribute sigma_mass : Real = 0.28909372274994966;
                                attribute Cx : Real = 71.7912663705647;
                                attribute sigma_Cx : Real = 28.721044428837228;
                                attribute Cy : Real = -8.486271928995848;
                                attribute sigma_Cy : Real = 28.23690002309109;
                                attribute Cz : Real = 42.408562218770385;
                                attribute sigma_Cz : Real = 29.057750463592832;
                                attribute Ixx : Real = 0.4110113670047712;
                                attribute sigma_Ixx : Real = 0.37074144170588635;
                                attribute Iyy : Real = 0.5230117612574051;
                                attribute sigma_Iyy : Real = 0.3723953238821935;
                                attribute Izz : Real = 0.5064963110824754;
                                attribute sigma_Izz : Real = 0.37017423652493897;
                                attribute Ixy : Real = -0.027218124716260356;
                                attribute sigma_Ixy : Real = 0.02351283871158888;
                                attribute Ixz : Real = -0.0554366259456813;
                                attribute sigma_Ixz : Real = 0.022566176940390956;
                                attribute Iyz : Real = -0.004615459387363461;
                                attribute sigma_Iyz : Real = 0.02209918015384651;
                            }
                            part <'C.1.1.1.1.2.3.2'> 'Part 26' {
                                attribute POIconv : String = "+";
                                attribute Ipoint : Boolean = false;
                                attribute mass : Real = 0.5616151409610175;
                                attribute sigma_mass : Real = 0.28909372274994966;
                                attribute Cx : Real = 23.045656364411116;
                                attribute sigma_Cx : Real = 28.721044428837228;
                                attribute Cy : Real = -40.90169197879732;
                                attribute sigma_Cy : Real = 28.23690002309109;
                                attribute Cz : Real = -78.23526933789253;
                                attribute sigma_Cz : Real = 29.057750463592832;
                                attribute Ixx : Real = 0.6726617743261615;
                                attribute sigma_Ixx : Real = 0.37074144170588635;
                                attribute Iyy : Real = 0.6535860322980943;
                                attribute sigma_Iyy : Real = 0.3723953238821935;
                                attribute Izz : Real = 0.6483018815249533;
                                attribute sigma_Izz : Real = 0.37017423652493897;
                                attribute Ixy : Real = 0.0047905078751247256;
                                attribute sigma_Ixy : Real = 0.02351283871158888;
                                attribute Ixz : Real = -0.02586964620047131;
                                attribute sigma_Ixz : Real = 0.022566176940390956;
                                attribute Iyz : Real = -0.01652036659346097;
                                attribute sigma_Iyz : Real = 0.02209918015384651;
                            }
                            part <'C.1.1.1.1.2.3.3'> 'Part 27' {
                                attribute POIconv : String = "-";
                                attribute Ipoint : Boolean = false;
                                attribute mass : Real = 0.8929159117490053;
                                attribute sigma_mass : Real = 0.28909372274994966;
                                attribute Cx : Real = 15.40752169676125;
                                attribute sigma_Cx : Real = 28.721044428837228;
                                attribute Cy : Real = -68.8828909303993;
                                attribute sigma_Cy : Real = 28.23690002309109;
                                attribute Cz : Real = -37.21725856885314;
                                attribute sigma_Cz : Real = 29.057750463592832;
                                attribute Ixx : Real = 1.3836969050186676;
                                attribute sigma_Ixx : Real = 0.37074144170588635;
                                attribute Iyy : Real = 1.1247671667969468;
                                attribute sigma_Iyy : Real = 0.3723953238821935;
                                attribute Izz : Real = 1.184343945119268;
                                attribute sigma_Izz : Real = 0.37017423652493897;
                                attribute Ixy : Real = -0.04590787104991288;
                                attribute sigma_Ixy : Real = 0.02351283871158888;
                                attribute Ixz : Real = -0.03864313172501027;
                                attribute sigma_Ixz : Real = 0.022566176940390956;
                                attribute Iyz : Real = 0.021437510926272454;
                                attribute sigma_Iyz : Real = 0.02209918015384651;
                            }
                            part <'C.1.1.1.1.2.3.4'> 'Part 28' {
                                attribute POIconv : String = "-";
                                attribute Ipoint : Boolean = false;
                                attribute mass : Real = 0.7840164996779058;
                                attribute sigma_mass : Real = 0.28909372274994966;
                                attribute Cx : Real = 70.36396483890712;
                                attribute sigma_Cx : Real = 28.721044428837228;
                                attribute Cy : Real = -49.943631794303656;
                                attribute sigma_Cy : Real = 28.23690002309109;
                                attribute Cz : Real = 84.3402674421668;
                                attribute sigma_Cz : Real = 29.057750463592832;
                                attribute Ixx : Real = 0.7498778096224765;
                                attribute sigma_Ixx : Real = 0.37074144170588635;
                                attribute Iyy : Real = 0.7420379089018556;
                                attribute sigma_Iyy : Real = 0.3723953238821935;
                                attribute Izz : Real = 0.7675189025218033;
                                attribute sigma_Izz : Real = 0.37017423652493897;
                                attribute Ixy : Real = -0.0018618220508169769;
                                attribute sigma_Ixy : Real = 0.02351283871158888;
                                attribute Ixz : Real = -1.6751341913394552e-05;
                                attribute sigma_Ixz : Real = 0.022566176940390956;
                                attribute Iyz : Real = 0.002102450383311292;
                                attribute sigma_Iyz : Real = 0.02209918015384651;
                            }
                            part <'C.1.1.1.1.2.3.5'> 'Part 29' {
                                attribute POIconv : String = "+";
                                attribute Ipoint : Boolean = false;
                                attribute mass : Real = 0.695954920454882;
                                attribute sigma_mass : Real = 0.28909372274994966;
                                attribute Cx : Real = -49.38840065151453;
                                attribute sigma_Cx : Real = 28.721044428837228;
                                attribute Cy : Real = 64.11762246862054;
                                attribute sigma_Cy : Real = 28.23690002309109;
                                attribute Cz : Real = -93.65140623413026;
                                attribute sigma_Cz : Real = 29.057750463592832;
                                attribute Ixx : Real = 0.7776619133776641;
                                attribute sigma_Ixx : Real = 0.37074144170588635;
                                attribute Iyy : Real = 0.7350937571569712;
                                attribute sigma_Iyy : Real = 0.3723953238821935;
                                attribute Izz : Real = 0.7850556748371398;
                                attribute sigma_Izz : Real = 0.37017423652493897;
                                attribute Ixy : Real = 0.005618900920627741;
                                attribute sigma_Ixy : Real = 0.02351283871158888;
                                attribute Ixz : Real = 0.047816837860602326;
                                attribute sigma_Ixz : Real = 0.022566176940390956;
                                attribute Iyz : Real = -0.0004039556146849208;
                                attribute sigma_Iyz : Real = 0.02209918015384651;
                            }
                        }
                        part <'C.1.1.1.1.2.4'> 'Subassembly 9' {
                            attribute POIconv : String = "-";
                            attribute Ipoint : Boolean = false;
                            attribute mass : Real = 2.081349927955307;
                            attribute sigma_mass : Real = 0.5781874454998993;
                            attribute Cx : Real = -9.705366002072122;
                            attribute sigma_Cx : Real = 24.95871509421204;
                            attribute Cy : Real = 33.97153914377077;
                            attribute sigma_Cy : Real = 23.00148471358607;
                            attribute Cz : Real = 69.91370010038368;
                            attribute sigma_Cz : Real = 18.065193704136114;
                            attribute Ixx : Real = 6560.411709523754;
                            attribute sigma_Ixx : Real = 4770.970212775469;
                            attribute Iyy : Real = 13179.636097228386;
                            attribute sigma_Iyy : Real = 6830.945731486618;
                            attribute Izz : Real = 16977.926439587172;
                            attribute sigma_Izz : Real = 8203.922203227821;
                            attribute Ixy : Real = -3742.0701956438425;
                            attribute sigma_Ixy : Real = 3565.982572226357;
                            attribute Ixz : Real = 3910.439676422053;
                            attribute sigma_Ixz : Real = 3051.0590001933037;
                            attribute Iyz : Real = 692.6137144345391;
                            attribute sigma_Iyz : Real = 1701.8674291914622;
                            part <'C.1.1.1.1.2.4.1'> 'Part 30' {
                                attribute POIconv : String = "-";
                                attribute Ipoint : Boolean = false;
                                attribute mass : Real = 0.9436988299102522;
                                attribute sigma_mass : Real = 0.28909372274994966;
                                attribute Cx : Real = -66.92492282018065;
                                attribute sigma_Cx : Real = 28.721044428837228;
                                attribute Cy : Real = 49.732256261631846;
                                attribute sigma_Cy : Real = 28.23690002309109;
                                attribute Cz : Real = 93.86770399287343;
                                attribute sigma_Cz : Real = 29.057750463592832;
                                attribute Ixx : Real = 1.2886768949444425;
                                attribute sigma_Ixx : Real = 0.37074144170588635;
                                attribute Iyy : Real = 1.2217401945586743;
                                attribute sigma_Iyy : Real = 0.3723953238821935;
                                attribute Izz : Real = 1.1206466271500322;
                                attribute sigma_Izz : Real = 0.37017423652493897;
                                attribute Ixy : Real = 0.06072433196133281;
                                attribute sigma_Ixy : Real = 0.02351283871158888;
                                attribute Ixz : Real = -0.08619452278113188;
                                attribute sigma_Ixz : Real = 0.022566176940390956;
                                attribute Iyz : Real = -0.04547609834927677;
                                attribute sigma_Iyz : Real = 0.02209918015384651;
                            }
                            part <'C.1.1.1.1.2.4.2'> 'Part 31' {
                                attribute POIconv : String = "+";
                                attribute Ipoint : Boolean = false;
                                attribute mass : Real = 0.673545587467961;
                                attribute sigma_mass : Real = 0.28909372274994966;
                                attribute Cx : Real = 97.01616941019893;
                                attribute sigma_Cx : Real = 28.721044428837228;
                                attribute Cy : Real = 69.5228427182883;
                                attribute sigma_Cy : Real = 28.23690002309109;
                                attribute Cz : Real = 35.328703513368964;
                                attribute sigma_Cz : Real = 29.057750463592832;
                                attribute Ixx : Real = 0.8473901395472749;
                                attribute sigma_Ixx : Real = 0.37074144170588635;
                                attribute Iyy : Real = 0.8234551849261366;
                                attribute sigma_Iyy : Real = 0.3723953238821935;
                                attribute Izz : Real = 0.7668203241750924;
                                attribute sigma_Izz : Real = 0.37017423652493897;
                                attribute Ixy : Real = 0.041488819265171846;
                                attribute sigma_Ixy : Real = 0.02351283871158888;
                                attribute Ixz : Real = 0.050520560228710466;
                                attribute sigma_Ixz : Real = 0.022566176940390956;
                                attribute Iyz : Real = -0.021624172208190406;
                                attribute sigma_Iyz : Real = 0.02209918015384651;
                            }
                            part <'C.1.1.1.1.2.4.3'> 'Part 32' {
                                attribute POIconv : String = "+";
                                attribute Ipoint : Boolean = false;
                                attribute mass : Real = 0.11553020319505594;
                                attribute sigma_mass : Real = 0.28909372274994966;
                                attribute Cx : Real = -0.730050215497613;
                                attribute sigma_Cx : Real = 28.721044428837228;
                                attribute Cy : Real = 24.466659035533667;
                                attribute sigma_Cy : Real = 28.23690002309109;
                                attribute Cz : Real = 57.09592984057963;
                                attribute sigma_Cz : Real = 29.057750463592832;
                                attribute Ixx : Real = 0.13509820083969448;
                                attribute sigma_Ixx : Real = 0.37074144170588635;
                                attribute Iyy : Real = 0.1452609027797815;
                                attribute sigma_Iyy : Real = 0.3723953238821935;
                                attribute Izz : Real = 0.1495497763298617;
                                attribute sigma_Izz : Real = 0.37017423652493897;
                                attribute Ixy : Real = -0.0026632551093619668;
                                attribute sigma_Ixy : Real = 0.02351283871158888;
                                attribute Ixz : Real = 0.0023267850009609675;
                                attribute sigma_Ixz : Real = 0.022566176940390956;
                                attribute Iyz : Real = -0.0008189717595237061;
                                attribute sigma_Iyz : Real = 0.02209918015384651;
                            }
                            part <'C.1.1.1.1.2.4.4'> 'Part 33' {
                                attribute POIconv : String = "+";
                                attribute Ipoint : Boolean = false;
                                attribute mass : Real = 0.34857530738203785;
                                attribute sigma_mass : Real = 0.28909372274994966;
                                attribute Cx : Real = -63.98548884317279;
                                attribute sigma_Cx : Real = 28.721044428837228;
                                attribute Cy : Real = -74.24236019141972;
                                attribute sigma_Cy : Real = 28.23690002309109;
                                attribute Cz : Real = 76.13917263224721;
                                attribute sigma_Cz : Real = 29.057750463592832;
                                attribute Ixx : Real = 0.4715985839694769;
                                attribute sigma_Ixx : Real = 0.37074144170588635;
                                attribute Iyy : Real = 0.41674429063310514;
                                attribute sigma_Iyy : Real = 0.3723953238821935;
                                attribute Izz : Real = 0.43622683259144296;
                                attribute sigma_Izz : Real = 0.37017423652493897;
                                attribute Ixy : Real = 0.019312334336277263;
                                attribute sigma_Ixy : Real = 0.02351283871158888;
                                attribute Ixz : Real = 0.0041147134064364824;
                                attribute sigma_Ixz : Real = 0.022566176940390956;
                                attribute Iyz : Real = -0.007185592006803824;
                                attribute sigma_Iyz : Real = 0.02209918015384651;
                            }
                        }
                        part <'C.1.1.1.1.2.5'> 'Subassembly 10' {
                            attribute POIconv : String = "-";
                            attribute Ipoint : Boolean = false;
                            attribute mass : Real = 2.246058847882785;
                            attribute sigma_mass : Real = 0.5781874454998993;
                            attribute Cx : Real = 17.190497795478468;
                            attribute sigma_Cx : Real = 18.96068847516762;
                            attribute Cy : Real = -37.926648770705;
                            attribute sigma_Cy : Real = 17.433613275493915;
                            attribute Cz : Real = -46.816936828050814;
                            attribute sigma_Cz : Real = 19.53754119716155;
                            attribute Ixx : Real = 3489.5646225625783;
                            attribute sigma_Ixx : Real = 2973.750872571652;
                            attribute Iyy : Real = 5042.448160571208;
                            attribute sigma_Iyy : Real = 3893.394337173969;
                            attribute Izz : Real = 3489.1382742123437;
                            attribute sigma_Izz : Real = 2917.411214385568;
                            attribute Ixy : Real = 963.6521155999734;
                            attribute sigma_Ixy : Real = 1379.355827270808;
                            attribute Ixz : Real = 1839.0437649630926;
                            attribute sigma_Ixz : Real = 1916.0568842643063;
                            attribute Iyz : Real = -411.7191156395129;
                            attribute sigma_Iyz : Real = 1267.2871679701261;
                            part <'C.1.1.1.1.2.5.1'> 'Part 34' {
                                attribute POIconv : String = "+";
                                attribute Ipoint : Boolean = false;
                                attribute mass : Real = 0.8280004888649565;
                                attribute sigma_mass : Real = 0.28909372274994966;
                                attribute Cx : Real = 51.439374685287476;
                                attribute sigma_Cx : Real = 28.721044428837228;
                                attribute Cy : Real = -62.66789431683719;
                                attribute sigma_Cy : Real = 28.23690002309109;
                                attribute Cz : Real = -57.598067820072174;
                                attribute sigma_Cz : Real = 29.057750463592832;
                                attribute Ixx : Real = 0.9017238691922955;
                                attribute sigma_Ixx : Real = 0.37074144170588635;
                                attribute Iyy : Real = 0.9002202716176154;
                                attribute sigma_Iyy : Real = 0.3723953238821935;
                                attribute Izz : Real = 0.9105615537368861;
                                attribute sigma_Izz : Real = 0.37017423652493897;
                                attribute Ixy : Real = -0.021639086044565475;
                                attribute sigma_Ixy : Real = 0.02351283871158888;
                                attribute Ixz : Real = -0.018413166917529266;
                                attribute sigma_Ixz : Real = 0.022566176940390956;
                                attribute Iyz : Real = -0.004759512616736874;
                                attribute sigma_Iyz : Real = 0.02209918015384651;
                            }
                            part <'C.1.1.1.1.2.5.2'> 'Part 35' {
                                attribute POIconv : String = "-";
                                attribute Ipoint : Boolean = false;
                                attribute mass : Real = 0.15809483261196874;
                                attribute sigma_mass : Real = 0.28909372274994966;
                                attribute Cx : Real = 48.91085121780634;
                                attribute sigma_Cx : Real = 28.721044428837228;
                                attribute Cy : Real = 4.567188955843449;
                                attribute sigma_Cy : Real = 28.23690002309109;
                                attribute Cz : Real = -73.94922659732401;
                                attribute sigma_Cz : Real = 29.057750463592832;
                                attribute Ixx : Real = 0.16368212381628913;
                                attribute sigma_Ixx : Real = 0.37074144170588635;
                                attribute Iyy : Real = 0.18943937654425835;
                                attribute sigma_Iyy : Real = 0.3723953238821935;
                                attribute Izz : Real = 0.18782810692943028;
                                attribute sigma_Izz : Real = 0.37017423652493897;
                                attribute Ixy : Real = 0.014759018051930757;
                                attribute sigma_Ixy : Real = 0.02351283871158888;
                                attribute Ixz : Real = 0.001260635244357189;
                                attribute sigma_Ixz : Real = 0.022566176940390956;
                                attribute Iyz : Real = 0.005826912991183145;
                                attribute sigma_Iyz : Real = 0.02209918015384651;
                            }
                            part <'C.1.1.1.1.2.5.3'> 'Part 36' {
                                attribute POIconv : String = "-";
                                attribute Ipoint : Boolean = false;
                                attribute mass : Real = 0.3790072734153364;
                                attribute sigma_mass : Real = 0.28909372274994966;
                                attribute Cx : Real = -39.83527738600969;
                                attribute sigma_Cx : Real = 28.721044428837228;
                                attribute Cy : Real = -20.327910967171192;
                                attribute sigma_Cy : Real = 28.23690002309109;
                                attribute Cz : Real = 26.927303662523627;
                                attribute sigma_Cz : Real = 29.057750463592832;
                                attribute Ixx : Real = 0.3206503236592797;
                                attribute sigma_Ixx : Real = 0.37074144170588635;
                                attribute Iyy : Real = 0.33904506000963136;
                                attribute sigma_Iyy : Real = 0.3723953238821935;
                                attribute Izz : Real = 0.3391154753793135;
                                attribute sigma_Izz : Real = 0.37017423652493897;
                                attribute Ixy : Real = -0.0026212176125589106;
                                attribute sigma_Ixy : Real = 0.02351283871158888;
                                attribute Ixz : Real = 0.000986966653668253;
                                attribute sigma_Ixz : Real = 0.022566176940390956;
                                attribute Iyz : Real = 0.0017618757083064402;
                                attribute sigma_Iyz : Real = 0.02209918015384651;
                            }
                            part <'C.1.1.1.1.2.5.4'> 'Part 37' {
                                attribute POIconv : String = "+";
                                attribute Ipoint : Boolean = false;
                                attribute mass : Real = 0.8809562529905234;
                                attribute sigma_mass : Real = 0.28909372274994966;
                                attribute Cx : Real = 3.8416769355535507;
                                attribute sigma_Cx : Real = 28.721044428837228;
                                attribute Cy : Real = -29.869883647188544;
                                attribute sigma_Cy : Real = 28.23690002309109;
                                attribute Cz : Real = -63.54120313189924;
                                attribute sigma_Cz : Real = 29.057750463592832;
                                attribute Ixx : Real = 1.1398817251819047;
                                attribute sigma_Ixx : Real = 0.37074144170588635;
                                attribute Iyy : Real = 1.0770260638110756;
                                attribute sigma_Iyy : Real = 0.3723953238821935;
                                attribute Izz : Real = 1.0212118495769824;
                                attribute sigma_Izz : Real = 0.37017423652493897;
                                attribute Ixy : Real = 0.007045131470129704;
                                attribute sigma_Ixy : Real = 0.02351283871158888;
                                attribute Ixz : Real = -0.052201494660640384;
                                attribute sigma_Ixz : Real = 0.022566176940390956;
                                attribute Iyz : Real = -0.026616296064105982;
                                attribute sigma_Iyz : Real = 0.02209918015384651;
                            }
                        }
                    }
                    part <'C.1.1.1.1.3'> 'Assembly 3' {
                        attribute POIconv : String = "-";
                        attribute Ipoint : Boolean = false;
                        attribute mass : Real = 5.481709958021529;
                        attribute sigma_mass : Real = 0.958815407608614;
                        attribute Cx : Real = -7.022188599511872;
                        attribute sigma_Cx : Real = 13.968175999182623;
                        attribute Cy : Real = -5.91388029900124;
                        attribute sigma_Cy : Real = 15.458786146279389;
                        attribute Cz : Real = -8.453000992306242;
                        attribute sigma_Cz : Real = 12.284998683790802;
                        attribute Ixx : Real = 33441.57404363527;
                        attribute sigma_Ixx : Real = 11089.889564777519;
                        attribute Iyy : Real = 25100.717477404316;
                        attribute sigma_Iyy : Real = 8973.04762370394;
                        attribute Izz : Real = 43879.48694064652;
                        attribute sigma_Izz : Real = 11847.310900841298;
                        attribute Ixy : Real = -6499.765683798658;
                        attribute sigma_Ixy : Real = 6152.848057545536;
                        attribute Ixz : Real = -2024.4910011056102;
                        attribute sigma_Ixz : Real = 4454.077887965285;
                        attribute Iyz : Real = -5273.680578758149;
                        attribute sigma_Iyz : Real = 5143.648090010029;
                        part <'C.1.1.1.1.3.1'> 'Subassembly 11' {
                            attribute POIconv : String = "-";
                            attribute Ipoint : Boolean = false;
                            attribute mass : Real = 2.620770469765179;
                            attribute sigma_mass : Real = 0.6464332159373649;
                            attribute Cx : Real = 39.00328578592588;
                            attribute sigma_Cx : Real = 17.652814103954004;
                            attribute Cy : Real = 0.25914359369986056;
                            attribute sigma_Cy : Real = 21.403972118825433;
                            attribute Cz : Real = -8.71951435759094;
                            attribute sigma_Cz : Real = 15.225395460209635;
                            attribute Ixx : Real = 9806.29331707361;
                            attribute sigma_Ixx : Real = 5667.723404177646;
                            attribute Iyy : Real = 4814.954732857496;
                            attribute sigma_Iyy : Real = 3690.983538231467;
                            attribute Izz : Real = 13877.665474761725;
                            attribute sigma_Izz : Real = 6893.135207196053;
                            attribute Ixy : Real = -3773.1465910299944;
                            attribute sigma_Ixy : Real = 3287.0892542906736;
                            attribute Ixz : Real = 445.61635159855956;
                            attribute sigma_Ixz : Real = 1771.697612831813;
                            attribute Iyz : Real = 762.6609907730144;
                            attribute sigma_Iyz : Real = 2543.8294341441483;
                            part <'C.1.1.1.1.3.1.1'> 'Part 38' {
                                attribute POIconv : String = "+";
                                attribute Ipoint : Boolean = false;
                                attribute mass : Real = 0.14622153044352307;
                                attribute sigma_mass : Real = 0.28909372274994966;
                                attribute Cx : Real = 99.21634825877845;
                                attribute sigma_Cx : Real = 28.721044428837228;
                                attribute Cy : Real = 93.6696857213974;
                                attribute sigma_Cy : Real = 28.23690002309109;
                                attribute Cz : Real = -56.561761954799294;
                                attribute sigma_Cz : Real = 29.057750463592832;
                                attribute Ixx : Real = 0.19643423394214446;
                                attribute sigma_Ixx : Real = 0.37074144170588635;
                                attribute Iyy : Real = 0.21343720542294503;
                                attribute sigma_Iyy : Real = 0.3723953238821935;
                                attribute Izz : Real = 0.2165462492762795;
                                attribute sigma_Izz : Real = 0.37017423652493897;
                                attribute Ixy : Real = 0.0034981924195316228;
                                attribute sigma_Ixy : Real = 0.02351283871158888;
                                attribute Ixz : Real = 0.0007380366460453652;
                                attribute sigma_Ixz : Real = 0.022566176940390956;
                                attribute Iyz : Real = -0.0025580736595108944;
                                attribute sigma_Iyz : Real = 0.02209918015384651;
                            }
                            part <'C.1.1.1.1.3.1.2'> 'Part 39' {
                                attribute POIconv : String = "+";
                                attribute Ipoint : Boolean = false;
                                attribute mass : Real = 0.816904512305744;
                                attribute sigma_mass : Real = 0.28909372274994966;
                                attribute Cx : Real = 6.2335321214050055;
                                attribute sigma_Cx : Real = 28.721044428837228;
                                attribute Cy : Real = -64.85962145961821;
                                attribute sigma_Cy : Real = 28.23690002309109;
                                attribute Cz : Real = -7.743510697036982;
                                attribute sigma_Cz : Real = 29.057750463592832;
                                attribute Ixx : Real = 1.038350924273957;
                                attribute sigma_Ixx : Real = 0.37074144170588635;
                                attribute Iyy : Real = 1.0347491496685401;
                                attribute sigma_Iyy : Real = 0.3723953238821935;
                                attribute Izz : Real = 0.9761404323672223;
                                attribute sigma_Izz : Real = 0.37017423652493897;
                                attribute Ixy : Real = -0.04433959896401238;
                                attribute sigma_Ixy : Real = 0.02351283871158888;
                                attribute Ixz : Real = 0.05027237609822839;
                                attribute sigma_Ixz : Real = 0.022566176940390956;
                                attribute Iyz : Real = -0.0009845609253663632;
                                attribute sigma_Iyz : Real = 0.02209918015384651;
                            }
                            part <'C.1.1.1.1.3.1.3'> 'Part 40' {
                                attribute POIconv : String = "-";
                                attribute Ipoint : Boolean = false;
                                attribute mass : Real = 0.40549652369623074;
                                attribute sigma_mass : Real = 0.28909372274994966;
                                attribute Cx : Real = 22.764458088204265;
                                attribute sigma_Cx : Real = 28.721044428837228;
                                attribute Cy : Real = -58.645621640607715;
                                attribute sigma_Cy : Real = 28.23690002309109;
                                attribute Cz : Real = -0.36920011043548584;
                                attribute sigma_Cz : Real = 29.057750463592832;
                                attribute Ixx : Real = 0.4741372858970175;
                                attribute sigma_Ixx : Real = 0.37074144170588635;
                                attribute Iyy : Real = 0.47921536567576256;
                                attribute sigma_Iyy : Real = 0.3723953238821935;
                                attribute Izz : Real = 0.4957670874285284;
                                attribute sigma_Izz : Real = 0.37017423652493897;
                                attribute Ixy : Real = -0.02011384283695799;
                                attribute sigma_Ixy : Real = 0.02351283871158888;
                                attribute Ixz : Real = -0.023900615622589542;
                                attribute sigma_Ixz : Real = 0.022566176940390956;
                                attribute Iyz : Real = 0.022832951488102535;
                                attribute sigma_Iyz : Real = 0.02209918015384651;
                            }
                            part <'C.1.1.1.1.3.1.4'> 'Part 41' {
                                attribute POIconv : String = "+";
                                attribute Ipoint : Boolean = false;
                                attribute mass : Real = 0.7099413991076872;
                                attribute sigma_mass : Real = 0.28909372274994966;
                                attribute Cx : Real = 97.23394718021154;
                                attribute sigma_Cx : Real = 28.721044428837228;
                                attribute Cy : Real = 44.218095391988754;
                                attribute sigma_Cy : Real = 28.23690002309109;
                                attribute Cz : Real = -6.449255114421248;
                                attribute sigma_Cz : Real = 29.057750463592832;
                                attribute Ixx : Real = 1.0227921520512584;
                                attribute sigma_Ixx : Real = 0.37074144170588635;
                                attribute Iyy : Real = 0.9486777174797226;
                                attribute sigma_Iyy : Real = 0.3723953238821935;
                                attribute Izz : Real = 0.9175400538101954;
                                attribute sigma_Izz : Real = 0.37017423652493897;
                                attribute Ixy : Real = 0.00217001469178261;
                                attribute sigma_Ixy : Real = 0.02351283871158888;
                                attribute Ixz : Real = -0.02200696957430804;
                                attribute sigma_Ixz : Real = 0.022566176940390956;
                                attribute Iyz : Real = 0.035404389834662875;
                                attribute sigma_Iyz : Real = 0.02209918015384651;
                            }
                            part <'C.1.1.1.1.3.1.5'> 'Part 42' {
                                attribute POIconv : String = "-";
                                attribute Ipoint : Boolean = false;
                                attribute mass : Real = 0.5422065042119939;
                                attribute sigma_mass : Real = 0.28909372274994966;
                                attribute Cx : Real = 8.036752883344889;
                                attribute sigma_Cx : Real = 28.721044428837228;
                                attribute Cy : Real = 59.67299812473357;
                                attribute sigma_Cy : Real = 28.23690002309109;
                                attribute Cz : Real = -6.505430908873677;
                                attribute sigma_Cz : Real = 29.057750463592832;
                                attribute Ixx : Real = 0.7466881832263661;
                                attribute sigma_Ixx : Real = 0.37074144170588635;
                                attribute Iyy : Real = 0.702733627768533;
                                attribute sigma_Iyy : Real = 0.3723953238821935;
                                attribute Izz : Real = 0.7751268247199941;
                                attribute sigma_Izz : Real = 0.37017423652493897;
                                attribute Ixy : Real = 0.05699878736535637;
                                attribute sigma_Ixy : Real = 0.02351283871158888;
                                attribute Ixz : Real = 0.010630338942310573;
                                attribute sigma_Ixz : Real = 0.022566176940390956;
                                attribute Iyz : Real = 0.014773749222682722;
                                attribute sigma_Iyz : Real = 0.02209918015384651;
                            }
                        }
                        part <'C.1.1.1.1.3.2'> 'Subassembly 12' {
                            attribute POIconv : String = "-";
                            attribute Ipoint : Boolean = false;
                            attribute mass : Real = 1.6352078220662662;
                            attribute sigma_mass : Real = 0.5781874454998993;
                            attribute Cx : Real = -70.96924726673208;
                            attribute sigma_Cx : Real = 17.51773732236931;
                            attribute Cy : Real = 8.710084701002675;
                            attribute sigma_Cy : Real = 31.195753075455524;
                            attribute Cz : Real = -16.693989689585724;
                            attribute sigma_Cz : Real = 29.06997432742471;
                            attribute Ixx : Real = 17434.396473962104;
                            attribute sigma_Ixx : Real = 8477.299524559226;
                            attribute Iyy : Real = 7533.69382535386;
                            attribute sigma_Iyy : Real = 5121.488643643707;
                            attribute Izz : Real = 11645.381513790315;
                            attribute sigma_Izz : Real = 5894.885914497751;
                            attribute Ixy : Real = -2851.860852352643;
                            attribute sigma_Ixy : Real = 2484.5161298099133;
                            attribute Ixz : Real = -1835.9547501975635;
                            attribute sigma_Ixz : Real = 1930.8889822464118;
                            attribute Iyz : Real = -7005.051167873903;
                            attribute sigma_Iyz : Real = 4029.448944197678;
                            part <'C.1.1.1.1.3.2.1'> 'Part 43' {
                                attribute POIconv : String = "+";
                                attribute Ipoint : Boolean = false;
                                attribute mass : Real = 0.26679534564120694;
                                attribute sigma_mass : Real = 0.28909372274994966;
                                attribute Cx : Real = -42.3387766815722;
                                attribute sigma_Cx : Real = 28.721044428837228;
                                attribute Cy : Real = 78.68632734753191;
                                attribute sigma_Cy : Real = 28.23690002309109;
                                attribute Cz : Real = 88.77342287451029;
                                attribute sigma_Cz : Real = 29.057750463592832;
                                attribute Ixx : Real = 0.3653197529961761;
                                attribute sigma_Ixx : Real = 0.37074144170588635;
                                attribute Iyy : Real = 0.3586917892626038;
                                attribute sigma_Iyy : Real = 0.3723953238821935;
                                attribute Izz : Real = 0.36761850142652697;
                                attribute sigma_Izz : Real = 0.37017423652493897;
                                attribute Ixy : Real = 0.00039382814022135513;
                                attribute sigma_Ixy : Real = 0.02351283871158888;
                                attribute Ixz : Real = 0.0012502970559738385;
                                attribute sigma_Ixz : Real = 0.022566176940390956;
                                attribute Iyz : Real = 0.004304778296552754;
                                attribute sigma_Iyz : Real = 0.02209918015384651;
                            }
                            part <'C.1.1.1.1.3.2.2'> 'Part 44' {
                                attribute POIconv : String = "+";
                                attribute Ipoint : Boolean = false;
                                attribute mass : Real = 0.6980398972455878;
                                attribute sigma_mass : Real = 0.28909372274994966;
                                attribute Cx : Real = -95.86311224848032;
                                attribute sigma_Cx : Real = 28.721044428837228;
                                attribute Cy : Real = -85.33331966027617;
                                attribute sigma_Cy : Real = 28.23690002309109;
                                attribute Cz : Real = -77.88576940074563;
                                attribute sigma_Cz : Real = 29.057750463592832;
                                attribute Ixx : Real = 1.080027327993266;
                                attribute sigma_Ixx : Real = 0.37074144170588635;
                                attribute Iyy : Real = 1.0201478091470655;
                                attribute sigma_Iyy : Real = 0.3723953238821935;
                                attribute Izz : Real = 0.9847903172482783;
                                attribute sigma_Izz : Real = 0.37017423652493897;
                                attribute Ixy : Real = -0.0490600347873377;
                                attribute sigma_Ixy : Real = 0.02351283871158888;
                                attribute Ixz : Real = -0.004266232778660036;
                                attribute sigma_Ixz : Real = 0.022566176940390956;
                                attribute Iyz : Real = -0.002338528783125025;
                                attribute sigma_Iyz : Real = 0.02209918015384651;
                            }
                            part <'C.1.1.1.1.3.2.3'> 'Part 45' {
                                attribute POIconv : String = "+";
                                attribute Ipoint : Boolean = false;
                                attribute mass : Real = 0.2595371792665683;
                                attribute sigma_mass : Real = 0.28909372274994966;
                                attribute Cx : Real = -70.06597449071705;
                                attribute sigma_Cx : Real = 28.721044428837228;
                                attribute Cy : Real = 78.65505330264568;
                                attribute sigma_Cy : Real = 28.23690002309109;
                                attribute Cz : Real = 47.46227124705911;
                                attribute sigma_Cz : Real = 29.057750463592832;
                                attribute Ixx : Real = 0.3640537628749178;
                                attribute sigma_Ixx : Real = 0.37074144170588635;
                                attribute Iyy : Real = 0.32188428910221606;
                                attribute sigma_Iyy : Real = 0.3723953238821935;
                                attribute Izz : Real = 0.3221347434432082;
                                attribute sigma_Izz : Real = 0.37017423652493897;
                                attribute Ixy : Real = 0.012409809486083848;
                                attribute sigma_Ixy : Real = 0.02351283871158888;
                                attribute Ixz : Real = -0.010835166549848991;
                                attribute sigma_Ixz : Real = 0.022566176940390956;
                                attribute Iyz : Real = -0.02253309996441543;
                                attribute sigma_Iyz : Real = 0.02209918015384651;
                            }
                            part <'C.1.1.1.1.3.2.4'> 'Part 46' {
                                attribute POIconv : String = "-";
                                attribute Ipoint : Boolean = false;
                                attribute mass : Real = 0.4108353999129031;
                                attribute sigma_mass : Real = 0.28909372274994966;
                                attribute Cx : Real = -47.83589071594179;
                                attribute sigma_Cx : Real = 28.721044428837228;
                                attribute Cy : Real = 78.8680911064148;
                                attribute sigma_Cy : Real = 28.23690002309109;
                                attribute Cz : Real = -21.74429977312684;
                                attribute sigma_Cz : Real = 29.057750463592832;
                                attribute Ixx : Real = 0.5047676335272006;
                                attribute sigma_Ixx : Real = 0.37074144170588635;
                                attribute Iyy : Real = 0.4809239587456611;
                                attribute sigma_Iyy : Real = 0.3723953238821935;
                                attribute Izz : Real = 0.4511124983651898;
                                attribute sigma_Izz : Real = 0.37017423652493897;
                                attribute Ixy : Real = -0.022156578472749162;
                                attribute sigma_Ixy : Real = 0.02351283871158888;
                                attribute Ixz : Real = 0.008016888608753586;
                                attribute sigma_Ixz : Real = 0.022566176940390956;
                                attribute Iyz : Real = 0.01539359014453958;
                                attribute sigma_Iyz : Real = 0.02209918015384651;
                            }
                        }
                        part <'C.1.1.1.1.3.3'> 'Subassembly 13' {
                            attribute POIconv : String = "-";
                            attribute Ipoint : Boolean = false;
                            attribute mass : Real = 1.2257316661900841;
                            attribute sigma_mass : Real = 0.40884026350990615;
                            attribute Cx : Real = -20.120874093560413;
                            attribute sigma_Cx : Real = 20.331788941232666;
                            attribute Cy : Real = -38.6219368750303;
                            attribute sigma_Cy : Real = 27.857223249478377;
                            attribute Cz : Real = 3.1108672896843412;
                            attribute sigma_Cz : Real = 20.609552923713427;
                            attribute Ixx : Real = 4164.853874141567;
                            attribute sigma_Ixx : Real = 3174.6109867294067;
                            attribute Iyy : Real = 28.18624189981862;
                            attribute sigma_Iyy : Real = 234.31122079649708;
                            attribute Izz : Real = 4146.823016318118;
                            attribute sigma_Izz : Real = 3166.0892167090306;
                            attribute Ixy : Real = -134.19136108376608;
                            attribute sigma_Ixy : Real = 1447.3854709747302;
                            attribute Ixz : Real = 9.769830495603525;
                            attribute sigma_Ixz : Real = 116.20141514133152;
                            attribute Iyz : Real = 303.7188118965407;
                            attribute sigma_Iyz : Real = 1470.1481484820754;
                            part <'C.1.1.1.1.3.3.1'> 'Part 47' {
                                attribute POIconv : String = "-";
                                attribute Ipoint : Boolean = false;
                                attribute mass : Real = 0.634985460388707;
                                attribute sigma_mass : Real = 0.28909372274994966;
                                attribute Cx : Real = -18.305410584434867;
                                attribute sigma_Cx : Real = 28.721044428837228;
                                attribute Cy : Real = 17.44096572510898;
                                attribute sigma_Cy : Real = 28.23690002309109;
                                attribute Cz : Real = -1.0011337231844664;
                                attribute sigma_Cz : Real = 29.057750463592832;
                                attribute Ixx : Real = 0.8913730410721291;
                                attribute sigma_Ixx : Real = 0.37074144170588635;
                                attribute Iyy : Real = 0.8316278723741327;
                                attribute sigma_Iyy : Real = 0.3723953238821935;
                                attribute Izz : Real = 0.7318105744566464;
                                attribute sigma_Izz : Real = 0.37017423652493897;
                                attribute Ixy : Real = -0.0914367115521594;
                                attribute sigma_Ixy : Real = 0.02351283871158888;
                                attribute Ixz : Real = -0.006115827586336267;
                                attribute sigma_Ixz : Real = 0.022566176940390956;
                                attribute Iyz : Real = -0.04307338553088562;
                                attribute sigma_Iyz : Real = 0.02209918015384651;
                            }
                            part <'C.1.1.1.1.3.3.2'> 'Part 48' {
                                attribute POIconv : String = "+";
                                attribute Ipoint : Boolean = false;
                                attribute mass : Real = 0.590746205801377;
                                attribute sigma_mass : Real = 0.28909372274994966;
                                attribute Cx : Real = -22.072292352095246;
                                attribute sigma_Cx : Real = 28.721044428837228;
                                attribute Cy : Real = -98.88322618789971;
                                attribute sigma_Cy : Real = 28.23690002309109;
                                attribute Cz : Real = 7.5308040250092745;
                                attribute sigma_Cz : Real = 29.057750463592832;
                                attribute Ixx : Real = 0.6452928842272114;
                                attribute sigma_Ixx : Real = 0.37074144170588635;
                                attribute Iyy : Real = 0.7347706669129337;
                                attribute sigma_Iyy : Real = 0.3723953238821935;
                                attribute Izz : Real = 0.7089715318353176;
                                attribute sigma_Izz : Real = 0.37017423652493897;
                                attribute Ixy : Real = 0.0022180955597196797;
                                attribute sigma_Ixy : Real = 0.02351283871158888;
                                attribute Ixz : Real = 0.05961121056537379;
                                attribute sigma_Ixz : Real = 0.022566176940390956;
                                attribute Iyz : Real = -0.03234114015540693;
                                attribute sigma_Iyz : Real = 0.02209918015384651;
                            }
                        }
                    }
                }
                part <'C.1.1.1.2'> 'Subsystem 2' {
                    attribute POIconv : String = "-";
                    attribute Ipoint : Boolean = false;
                    attribute mass : Real = 20.765187150602692;
                    attribute sigma_mass : Real = 1.8053897199229771;
                    attribute Cx : Real = 7.346564845402945;
                    attribute sigma_Cx : Real = 8.202037857204802;
                    attribute Cy : Real = -3.031625770596665;
                    attribute sigma_Cy : Real = 7.38420822337847;
                    attribute Cz : Real = 3.5972901564061033;
                    attribute sigma_Cz : Real = 7.078039939131441;
                    attribute Ixx : Real = 118832.92888107891;
                    attribute sigma_Ixx : Real = 20912.06595230567;
                    attribute Iyy : Real = 134644.13226739175;
                    attribute sigma_Iyy : Real = 25107.952978768983;
                    attribute Izz : Real = 150046.85317150003;
                    attribute sigma_Izz : Real = 26261.50126139635;
                    attribute Ixy : Real = -10938.748622282397;
                    attribute sigma_Ixy : Real = 12225.387215450302;
                    attribute Ixz : Real = -12353.407121747648;
                    attribute sigma_Ixz : Real = 11600.546877308472;
                    attribute Iyz : Real = 17955.244345167932;
                    attribute sigma_Iyz : Real = 9987.415481546399;
                    part <'C.1.1.1.2.1'> 'Assembly 4' {
                        attribute POIconv : String = "-";
                        attribute Ipoint : Boolean = false;
                        attribute mass : Real = 8.21065077304677;
                        attribute sigma_mass : Real = 1.1196551737036593;
                        attribute Cx : Real = 8.908060023453897;
                        attribute sigma_Cx : Real = 12.202246240457594;
                        attribute Cy : Real = 3.5667544456179403;
                        attribute sigma_Cy : Real = 11.82309852026525;
                        attribute Cz : Real = 1.4896982694315462;
                        attribute sigma_Cz : Real = 11.382521826194512;
                        attribute Ixx : Real = 58487.88862493308;
                        attribute sigma_Ixx : Real = 14329.335920819969;
                        attribute Iyy : Real = 64310.45948257967;
                        attribute sigma_Iyy : Real = 15495.601153310698;
                        attribute Izz : Real = 66352.93452240502;
                        attribute sigma_Izz : Real = 15421.109150406788;
                        attribute Ixy : Real = 334.4598144058632;
                        attribute sigma_Ixy : Real = 7389.354153864084;
                        attribute Ixz : Real = -13574.197976660973;
                        attribute sigma_Ixz : Real = 7626.862649566574;
                        attribute Iyz : Real = 12455.283654704968;
                        attribute sigma_Iyz : Real = 6864.6924671195875;
                        part <'C.1.1.1.2.1.1'> 'Subassembly 14' {
                            attribute POIconv : String = "-";
                            attribute Ipoint : Boolean = false;
                            attribute mass : Real = 1.5526917460332625;
                            attribute sigma_mass : Real = 0.5007250159521434;
                            attribute Cx : Real = -74.04471682958226;
                            attribute sigma_Cx : Real = 18.264418644810835;
                            attribute Cy : Real = 37.73174032524145;
                            attribute sigma_Cy : Real = 22.032005136709948;
                            attribute Cz : Real = -77.56026723540329;
                            attribute sigma_Cz : Real = 18.058263348417785;
                            attribute Ixx : Real = 3004.579230462329;
                            attribute sigma_Ixx : Real = 2584.2658806097857;
                            attribute Iyy : Real = 497.05853460987896;
                            attribute sigma_Iyy : Real = 1018.8715233393635;
                            attribute Izz : Real = 3259.0170941521087;
                            attribute sigma_Izz : Real = 2709.717809239691;
                            attribute Ixy : Real = -937.2832562144358;
                            attribute sigma_Ixy : Real = 1312.672271783018;
                            attribute Ixz : Real = -212.24421927994544;
                            attribute sigma_Ixz : Real = 510.30382401090117;
                            attribute Iyz : Real = -526.0272862918122;
                            attribute sigma_Iyz : Real = 1250.4680396231365;
                            part <'C.1.1.1.2.1.1.1'> 'Part 49' {
                                attribute POIconv : String = "+";
                                attribute Ipoint : Boolean = false;
                                attribute mass : Real = 0.5218669216977433;
                                attribute sigma_mass : Real = 0.28909372274994966;
                                attribute Cx : Real = -94.74931973963976;
                                attribute sigma_Cx : Real = 28.721044428837228;
                                attribute Cy : Real = -5.726963002234697;
                                attribute sigma_Cy : Real = 28.23690002309109;
                                attribute Cz : Real = -89.35355059802532;
                                attribute sigma_Cz : Real = 29.057750463592832;
                                attribute Ixx : Real = 0.7684898093613619;
                                attribute sigma_Ixx : Real = 0.37074144170588635;
                                attribute Iyy : Real = 0.7282929874850371;
                                attribute sigma_Iyy : Real = 0.3723953238821935;
                                attribute Izz : Real = 0.7585793360053665;
                                attribute sigma_Izz : Real = 0.37017423652493897;
                                attribute Ixy : Real = 0.006459898419936109;
                                attribute sigma_Ixy : Real = 0.02351283871158888;
                                attribute Ixz : Real = 0.00018921784647928908;
                                attribute sigma_Ixz : Real = 0.022566176940390956;
                                attribute Iyz : Real = -0.009041759965398723;
                                attribute sigma_Iyz : Real = 0.02209918015384651;
                            }
                            part <'C.1.1.1.2.1.1.2'> 'Part 50' {
                                attribute POIconv : String = "+";
                                attribute Ipoint : Boolean = false;
                                attribute mass : Real = 0.7470984810600058;
                                attribute sigma_mass : Real = 0.28909372274994966;
                                attribute Cx : Real = -59.83006777241826;
                                attribute sigma_Cx : Real = 28.721044428837228;
                                attribute Cy : Real = 82.42514738813043;
                                attribute sigma_Cy : Real = 28.23690002309109;
                                attribute Cz : Real = -69.5905792992562;
                                attribute sigma_Cz : Real = 29.057750463592832;
                                attribute Ixx : Real = 0.9216839362577209;
                                attribute sigma_Ixx : Real = 0.37074144170588635;
                                attribute Iyy : Real = 0.9411256344934409;
                                attribute sigma_Iyy : Real = 0.3723953238821935;
                                attribute Izz : Real = 0.7732515990727997;
                                attribute sigma_Izz : Real = 0.37017423652493897;
                                attribute Ixy : Real = 0.06294775827641705;
                                attribute sigma_Ixy : Real = 0.02351283871158888;
                                attribute Ixz : Real = 0.0447360618638525;
                                attribute sigma_Ixz : Real = 0.022566176940390956;
                                attribute Iyz : Real = 0.01937433844389028;
                                attribute sigma_Iyz : Real = 0.02209918015384651;
                            }
                            part <'C.1.1.1.2.1.1.3'> 'Part 51' {
                                attribute POIconv : String = "+";
                                attribute Ipoint : Boolean = false;
                                attribute mass : Real = 0.2837263432755135;
                                attribute sigma_mass : Real = 0.28909372274994966;
                                attribute Cx : Real = -73.3916062861681;
                                attribute sigma_Cx : Real = 28.721044428837228;
                                attribute Cy : Real = -0.018426543101668358;
                                attribute sigma_Cy : Real = 28.23690002309109;
                                attribute Cz : Real = -76.85401369817555;
                                attribute sigma_Cz : Real = 29.057750463592832;
                                attribute Ixx : Real = 0.42319231989813316;
                                attribute sigma_Ixx : Real = 0.37074144170588635;
                                attribute Iyy : Real = 0.42173626068599446;
                                attribute sigma_Iyy : Real = 0.3723953238821935;
                                attribute Izz : Real = 0.40446692907991805;
                                attribute sigma_Izz : Real = 0.37017423652493897;
                                attribute Ixy : Real = 0.003297595921162696;
                                attribute sigma_Ixy : Real = 0.02351283871158888;
                                attribute Ixz : Real = 0.0054009229062743766;
                                attribute sigma_Ixz : Real = 0.022566176940390956;
                                attribute Iyz : Real = 0.002900604633331045;
                                attribute sigma_Iyz : Real = 0.02209918015384651;
                            }
                        }
                        part <'C.1.1.1.2.1.2'> 'Subassembly 15' {
                            attribute POIconv : String = "-";
                            attribute Ipoint : Boolean = false;
                            attribute mass : Real = 2.8471113407665394;
                            attribute sigma_mass : Real = 0.5781874454998993;
                            attribute Cx : Real = 47.70702160662566;
                            attribute sigma_Cx : Real = 18.242004233870425;
                            attribute Cy : Real = 40.19501006641823;
                            attribute sigma_Cy : Real = 19.566577382884173;
                            attribute Cz : Real = 11.36637242542981;
                            attribute sigma_Cz : Real = 19.177747002405678;
                            attribute Ixx : Real = 15887.471217722283;
                            attribute sigma_Ixx : Real = 7975.580917724341;
                            attribute Iyy : Real = 17375.915773245943;
                            attribute sigma_Iyy : Real = 7753.9859922571895;
                            attribute Izz : Real = 14667.730679673085;
                            attribute sigma_Izz : Real = 7417.112134598098;
                            attribute Ixy : Real = -587.1153289608428;
                            attribute sigma_Ixy : Real = 3202.9387853201833;
                            attribute Ixz : Real = 3277.425114554817;
                            attribute sigma_Ixz : Real = 3715.4838616573857;
                            attribute Iyz : Real = 2377.63704813731;
                            attribute sigma_Iyz : Real = 3635.8322752339946;
                            part <'C.1.1.1.2.1.2.1'> 'Part 52' {
                                attribute POIconv : String = "-";
                                attribute Ipoint : Boolean = false;
                                attribute mass : Real = 0.3497393322051503;
                                attribute sigma_mass : Real = 0.28909372274994966;
                                attribute Cx : Real = 90.42232581414282;
                                attribute sigma_Cx : Real = 28.721044428837228;
                                attribute Cy : Real = -73.29918104223907;
                                attribute sigma_Cy : Real = 28.23690002309109;
                                attribute Cz : Real = 70.73393822647631;
                                attribute sigma_Cz : Real = 29.057750463592832;
                                attribute Ixx : Real = 0.48129434662801535;
                                attribute sigma_Ixx : Real = 0.37074144170588635;
                                attribute Iyy : Real = 0.42940927822364294;
                                attribute sigma_Iyy : Real = 0.3723953238821935;
                                attribute Izz : Real = 0.44369393395620965;
                                attribute sigma_Izz : Real = 0.37017423652493897;
                                attribute Ixy : Real = -0.059034113629182816;
                                attribute sigma_Ixy : Real = 0.02351283871158888;
                                attribute Ixz : Real = 0.0015432537273156236;
                                attribute sigma_Ixz : Real = 0.022566176940390956;
                                attribute Iyz : Real = 0.003548681987400733;
                                attribute sigma_Iyz : Real = 0.02209918015384651;
                            }
                            part <'C.1.1.1.2.1.2.2'> 'Part 53' {
                                attribute POIconv : String = "+";
                                attribute Ipoint : Boolean = false;
                                attribute mass : Real = 0.8794165587418247;
                                attribute sigma_mass : Real = 0.28909372274994966;
                                attribute Cx : Real = -29.14036763831973;
                                attribute sigma_Cx : Real = 28.721044428837228;
                                attribute Cy : Real = 26.189054362475872;
                                attribute sigma_Cy : Real = 28.23690002309109;
                                attribute Cz : Real = 27.455057902261615;
                                attribute sigma_Cz : Real = 29.057750463592832;
                                attribute Ixx : Real = 1.2116122134738396;
                                attribute sigma_Ixx : Real = 0.37074144170588635;
                                attribute Iyy : Real = 1.2426066559451039;
                                attribute sigma_Iyy : Real = 0.3723953238821935;
                                attribute Izz : Real = 1.2076981166633518;
                                attribute sigma_Izz : Real = 0.37017423652493897;
                                attribute Ixy : Real = -0.02881338669679237;
                                attribute sigma_Ixy : Real = 0.02351283871158888;
                                attribute Ixz : Real = 0.02638315617137038;
                                attribute sigma_Ixz : Real = 0.022566176940390956;
                                attribute Iyz : Real = 0.038840310391896185;
                                attribute sigma_Iyz : Real = 0.02209918015384651;
                            }
                            part <'C.1.1.1.2.1.2.3'> 'Part 54' {
                                attribute POIconv : String = "-";
                                attribute Ipoint : Boolean = false;
                                attribute mass : Real = 0.669483742558863;
                                attribute sigma_mass : Real = 0.28909372274994966;
                                attribute Cx : Real = 58.65882928483188;
                                attribute sigma_Cx : Real = 28.721044428837228;
                                attribute Cy : Real = 86.78798843175173;
                                attribute sigma_Cy : Real = 28.23690002309109;
                                attribute Cz : Real = 68.53770180605352;
                                attribute sigma_Cz : Real = 29.057750463592832;
                                attribute Ixx : Real = 0.8660795315379488;
                                attribute sigma_Ixx : Real = 0.37074144170588635;
                                attribute Iyy : Real = 0.789060856532035;
                                attribute sigma_Iyy : Real = 0.3723953238821935;
                                attribute Izz : Real = 0.8011005056184142;
                                attribute sigma_Izz : Real = 0.37017423652493897;
                                attribute Ixy : Real = -0.0047560944535491225;
                                attribute sigma_Ixy : Real = 0.02351283871158888;
                                attribute Ixz : Real = 0.04915970114870735;
                                attribute sigma_Ixz : Real = 0.022566176940390956;
                                attribute Iyz : Real = -0.02358444629675939;
                                attribute sigma_Iyz : Real = 0.02209918015384651;
                            }
                            part <'C.1.1.1.2.1.2.4'> 'Part 55' {
                                attribute POIconv : String = "+";
                                attribute Ipoint : Boolean = false;
                                attribute mass : Real = 0.9484717072607018;
                                attribute sigma_mass : Real = 0.28909372274994966;
                                attribute Cx : Real = 95.47817502170801;
                                attribute sigma_Cx : Real = 28.721044428837228;
                                attribute Cy : Real = 62.14317181147635;
                                attribute sigma_Cy : Real = 28.23690002309109;
                                attribute Cz : Real = -65.79681993462145;
                                attribute sigma_Cz : Real = 29.057750463592832;
                                attribute Ixx : Real = 1.2546791853375412;
                                attribute sigma_Ixx : Real = 0.37074144170588635;
                                attribute Iyy : Real = 1.226248233993727;
                                attribute sigma_Iyy : Real = 0.3723953238821935;
                                attribute Izz : Real = 1.1748731285389662;
                                attribute sigma_Izz : Real = 0.37017423652493897;
                                attribute Ixy : Real = -0.023894569743970417;
                                attribute sigma_Ixy : Real = 0.02351283871158888;
                                attribute Ixz : Real = 0.030223377798457254;
                                attribute sigma_Ixz : Real = 0.022566176940390956;
                                attribute Iyz : Real = -0.06763778130919393;
                                attribute sigma_Iyz : Real = 0.02209918015384651;
                            }
                        }
                        part <'C.1.1.1.2.1.3'> 'Subassembly 16' {
                            attribute POIconv : String = "-";
                            attribute Ipoint : Boolean = false;
                            attribute mass : Real = 2.6924735811015124;
                            attribute sigma_mass : Real = 0.6464332159373649;
                            attribute Cx : Real = 30.09364963072606;
                            attribute sigma_Cx : Real = 20.62515721872572;
                            attribute Cy : Real = -30.705677780263795;
                            attribute sigma_Cy : Real = 19.03809550247939;
                            attribute Cz : Real = 34.89543500907022;
                            attribute sigma_Cz : Real = 18.18465897832986;
                            attribute Ixx : Real = 13032.584740850727;
                            attribute sigma_Ixx : Real = 6483.08080174694;
                            attribute Iyy : Real = 13519.890910141468;
                            attribute sigma_Iyy : Real = 7075.045741806723;
                            attribute Izz : Real = 16208.70573536101;
                            attribute sigma_Izz : Real = 7654.25530665745;
                            attribute Ixy : Real = 1695.5886675148336;
                            attribute sigma_Ixy : Real = 3580.241805701887;
                            attribute Ixz : Real = -4674.933956298586;
                            attribute sigma_Ixz : Real = 3420.0841569147233;
                            attribute Iyz : Real = 4140.90242643402;
                            attribute sigma_Iyz : Real = 3097.046504987942;
                            part <'C.1.1.1.2.1.3.1'> 'Part 56' {
                                attribute POIconv : String = "-";
                                attribute Ipoint : Boolean = false;
                                attribute mass : Real = 0.4260679590126965;
                                attribute sigma_mass : Real = 0.28909372274994966;
                                attribute Cx : Real = 19.299472263082862;
                                attribute sigma_Cx : Real = 28.721044428837228;
                                attribute Cy : Real = -37.00572685338557;
                                attribute sigma_Cy : Real = 28.23690002309109;
                                attribute Cz : Real = 11.499222228303552;
                                attribute sigma_Cz : Real = 29.057750463592832;
                                attribute Ixx : Real = 0.5624370538017689;
                                attribute sigma_Ixx : Real = 0.37074144170588635;
                                attribute Iyy : Real = 0.5036909703258995;
                                attribute sigma_Iyy : Real = 0.3723953238821935;
                                attribute Izz : Real = 0.5368108141322708;
                                attribute sigma_Izz : Real = 0.37017423652493897;
                                attribute Ixy : Real = -0.013077850299350869;
                                attribute sigma_Ixy : Real = 0.02351283871158888;
                                attribute Ixz : Real = -0.004149335543551784;
                                attribute sigma_Ixz : Real = 0.022566176940390956;
                                attribute Iyz : Real = 0.03063573249296033;
                                attribute sigma_Iyz : Real = 0.02209918015384651;
                            }
                            part <'C.1.1.1.2.1.3.2'> 'Part 57' {
                                attribute POIconv : String = "-";
                                attribute Ipoint : Boolean = false;
                                attribute mass : Real = 0.7554786639297381;
                                attribute sigma_mass : Real = 0.28909372274994966;
                                attribute Cx : Real = 5.929126497358084;
                                attribute sigma_Cx : Real = 28.721044428837228;
                                attribute Cy : Real = 52.547507267445326;
                                attribute sigma_Cy : Real = 28.23690002309109;
                                attribute Cz : Real = -4.727424122393131;
                                attribute sigma_Cz : Real = 29.057750463592832;
                                attribute Ixx : Real = 1.0251652487671645;
                                attribute sigma_Ixx : Real = 0.37074144170588635;
                                attribute Iyy : Real = 0.9811623597373842;
                                attribute sigma_Iyy : Real = 0.3723953238821935;
                                attribute Izz : Real = 1.002838146866474;
                                attribute sigma_Izz : Real = 0.37017423652493897;
                                attribute Ixy : Real = -0.07430656772976525;
                                attribute sigma_Ixy : Real = 0.02351283871158888;
                                attribute Ixz : Real = 0.08615317106975548;
                                attribute sigma_Ixz : Real = 0.022566176940390956;
                                attribute Iyz : Real = -0.06522962006746337;
                                attribute sigma_Iyz : Real = 0.02209918015384651;
                            }
                            part <'C.1.1.1.2.1.3.3'> 'Part 58' {
                                attribute POIconv : String = "-";
                                attribute Ipoint : Boolean = false;
                                attribute mass : Real = 0.2523808718936052;
                                attribute sigma_mass : Real = 0.28909372274994966;
                                attribute Cx : Real = -51.382982172071934;
                                attribute sigma_Cx : Real = 28.721044428837228;
                                attribute Cy : Real = -96.5985853690654;
                                attribute sigma_Cy : Real = 28.23690002309109;
                                attribute Cz : Real = 71.31787086836994;
                                attribute sigma_Cz : Real = 29.057750463592832;
                                attribute Ixx : Real = 0.3371728688082054;
                                attribute sigma_Ixx : Real = 0.37074144170588635;
                                attribute Iyy : Real = 0.28081668905200063;
                                attribute sigma_Iyy : Real = 0.3723953238821935;
                                attribute Izz : Real = 0.2850610195326052;
                                attribute sigma_Izz : Real = 0.37017423652493897;
                                attribute Ixy : Real = 0.02310969099420511;
                                attribute sigma_Ixy : Real = 0.02351283871158888;
                                attribute Ixz : Real = -0.006070164475370973;
                                attribute sigma_Ixz : Real = 0.022566176940390956;
                                attribute Iyz : Real = -0.00019415714886170636;
                                attribute sigma_Iyz : Real = 0.02209918015384651;
                            }
                            part <'C.1.1.1.2.1.3.4'> 'Part 59' {
                                attribute POIconv : String = "-";
                                attribute Ipoint : Boolean = false;
                                attribute mass : Real = 0.9880897538557183;
                                attribute sigma_mass : Real = 0.28909372274994966;
                                attribute Cx : Real = 96.5033090673387;
                                attribute sigma_Cx : Real = 28.721044428837228;
                                attribute Cy : Real = -65.71766454726458;
                                attribute sigma_Cy : Real = 28.23690002309109;
                                attribute Cz : Real = 83.37932345457375;
                                attribute sigma_Cz : Real = 29.057750463592832;
                                attribute Ixx : Real = 1.2902819703811412;
                                attribute sigma_Ixx : Real = 0.37074144170588635;
                                attribute Iyy : Real = 1.311263679631395;
                                attribute sigma_Iyy : Real = 0.3723953238821935;
                                attribute Izz : Real = 1.3765730656949615;
                                attribute sigma_Izz : Real = 0.37017423652493897;
                                attribute Ixy : Real = -0.020929296776081862;
                                attribute sigma_Ixy : Real = 0.02351283871158888;
                                attribute Ixz : Real = -0.004299549732964904;
                                attribute sigma_Ixz : Real = 0.022566176940390956;
                                attribute Iyz : Real = 0.0003507446615881047;
                                attribute sigma_Iyz : Real = 0.02209918015384651;
                            }
                            part <'C.1.1.1.2.1.3.5'> 'Part 60' {
                                attribute POIconv : String = "-";
                                attribute Ipoint : Boolean = false;
                                attribute mass : Real = 0.2704563324097544;
                                attribute sigma_mass : Real = 0.28909372274994966;
                                attribute Cx : Real = -51.99252562597394;
                                attribute sigma_Cx : Real = 28.721044428837228;
                                attribute Cy : Real = -63.93344886600971;
                                attribute sigma_Cy : Real = 28.23690002309109;
                                attribute Cz : Real = -28.686578618362546;
                                attribute sigma_Cz : Real = 29.057750463592832;
                                attribute Ixx : Real = 0.3486090266200291;
                                attribute sigma_Ixx : Real = 0.37074144170588635;
                                attribute Iyy : Real = 0.359321042096914;
                                attribute sigma_Iyy : Real = 0.3723953238821935;
                                attribute Izz : Real = 0.35927295925538605;
                                attribute sigma_Izz : Real = 0.37017423652493897;
                                attribute Ixy : Real = 0.000910367688005906;
                                attribute sigma_Ixy : Real = 0.02351283871158888;
                                attribute Ixz : Real = -0.0018871768727899488;
                                attribute sigma_Ixz : Real = 0.022566176940390956;
                                attribute Iyz : Real = 8.024887626780901e-05;
                                attribute sigma_Iyz : Real = 0.02209918015384651;
                            }
                        }
                        part <'C.1.1.1.2.1.4'> 'Subassembly 17' {
                            attribute POIconv : String = "-";
                            attribute Ipoint : Boolean = false;
                            attribute mass : Real = 1.1183741051454563;
                            attribute sigma_mass : Real = 0.5007250159521434;
                            attribute Cx : Real = -25.701568134710733;
                            attribute sigma_Cx : Real = 24.253507856624356;
                            attribute Cy : Real = -54.6023277260145;
                            attribute sigma_Cy : Real = 18.79965213879746;
                            attribute Cz : Real = 5.67092377773785;
                            attribute sigma_Cz : Real = 19.985602219769284;
                            attribute Ixx : Real = 979.8134952287387;
                            attribute sigma_Ixx : Real = 1199.8853288491546;
                            attribute Iyy : Real = 2394.7216321701962;
                            attribute sigma_Iyy : Real = 2104.122638409167;
                            attribute Izz : Real = 2120.253848694896;
                            attribute sigma_Izz : Real = 1914.3983399880071;
                            attribute Ixy : Real = 105.5218520785518;
                            attribute sigma_Ixy : Real = 879.9117194697393;
                            attribute Ixz : Real = 1051.9017236095635;
                            attribute sigma_Ixz : Real = 1023.2028046469718;
                            attribute Iyz : Real = -55.27109867576762;
                            attribute sigma_Iyz : Real = 578.9158884051922;
                            part <'C.1.1.1.2.1.4.1'> 'Part 61' {
                                attribute POIconv : String = "+";
                                attribute Ipoint : Boolean = false;
                                attribute mass : Real = 0.271978923043469;
                                attribute sigma_mass : Real = 0.28909372274994966;
                                attribute Cx : Real = -60.715602710843086;
                                attribute sigma_Cx : Real = 28.721044428837228;
                                attribute Cy : Real = -25.645897444337606;
                                attribute sigma_Cy : Real = 28.23690002309109;
                                attribute Cz : Real = 25.933133577927947;
                                attribute sigma_Cz : Real = 29.057750463592832;
                                attribute Ixx : Real = 0.34442468234819473;
                                attribute sigma_Ixx : Real = 0.37074144170588635;
                                attribute Iyy : Real = 0.34263607584570394;
                                attribute sigma_Iyy : Real = 0.3723953238821935;
                                attribute Izz : Real = 0.35338258294955327;
                                attribute sigma_Izz : Real = 0.37017423652493897;
                                attribute Ixy : Real = 0.0006889441683797253;
                                attribute sigma_Ixy : Real = 0.02351283871158888;
                                attribute Ixz : Real = 0.008059866703174554;
                                attribute sigma_Ixz : Real = 0.022566176940390956;
                                attribute Iyz : Real = -0.00022100830910817712;
                                attribute sigma_Iyz : Real = 0.02209918015384651;
                            }
                            part <'C.1.1.1.2.1.4.2'> 'Part 62' {
                                attribute POIconv : String = "+";
                                attribute Ipoint : Boolean = false;
                                attribute mass : Real = 0.3950687476214953;
                                attribute sigma_mass : Real = 0.28909372274994966;
                                attribute Cx : Real = -56.759323040023446;
                                attribute sigma_Cx : Real = 28.721044428837228;
                                attribute Cy : Real = -72.16552658937871;
                                attribute sigma_Cy : Real = 28.23690002309109;
                                attribute Cz : Real = 24.581784661859274;
                                attribute sigma_Cz : Real = 29.057750463592832;
                                attribute Ixx : Real = 0.5900102928380874;
                                attribute sigma_Ixx : Real = 0.37074144170588635;
                                attribute Iyy : Real = 0.5960194067137053;
                                attribute sigma_Iyy : Real = 0.3723953238821935;
                                attribute Izz : Real = 0.6086748960895008;
                                attribute sigma_Izz : Real = 0.37017423652493897;
                                attribute Ixy : Real = -0.002011022898645948;
                                attribute sigma_Ixy : Real = 0.02351283871158888;
                                attribute Ixz : Real = -0.012879150202092043;
                                attribute sigma_Ixz : Real = 0.022566176940390956;
                                attribute Iyz : Real = -0.01806574977154448;
                                attribute sigma_Iyz : Real = 0.02209918015384651;
                            }
                            part <'C.1.1.1.2.1.4.3'> 'Part 63' {
                                attribute POIconv : String = "-";
                                attribute Ipoint : Boolean = false;
                                attribute mass : Real = 0.45132643448049203;
                                attribute sigma_mass : Real = 0.28909372274994966;
                                attribute Cx : Real = 22.585051227360964;
                                attribute sigma_Cx : Real = 28.721044428837228;
                                attribute Cy : Real = -56.67813732288778;
                                attribute sigma_Cy : Real = 28.23690002309109;
                                attribute Cz : Real = -23.093143943697214;
                                attribute sigma_Cz : Real = 29.057750463592832;
                                attribute Ixx : Real = 0.6592479832442258;
                                attribute sigma_Ixx : Real = 0.37074144170588635;
                                attribute Iyy : Real = 0.5905540003939;
                                attribute sigma_Iyy : Real = 0.3723953238821935;
                                attribute Izz : Real = 0.604170243779568;
                                attribute sigma_Izz : Real = 0.37017423652493897;
                                attribute Ixy : Real = 0.02751133215598491;
                                attribute sigma_Ixy : Real = 0.02351283871158888;
                                attribute Ixz : Real = 0.046859209745853336;
                                attribute sigma_Ixz : Real = 0.022566176940390956;
                                attribute Iyz : Real = 0.018318092065488015;
                                attribute sigma_Iyz : Real = 0.02209918015384651;
                            }
                        }
                    }
                    part <'C.1.1.1.2.2'> 'Assembly 5' {
                        attribute POIconv : String = "-";
                        attribute Ipoint : Boolean = false;
                        attribute mass : Real = 3.4763262885541186;
                        attribute sigma_mass : Real = 0.7648700959862226;
                        attribute Cx : Real = -32.341721733882515;
                        attribute sigma_Cx : Real = 16.266063009752006;
                        attribute Cy : Real = -1.9999412590368226;
                        attribute sigma_Cy : Real = 19.406419905056246;
                        attribute Cz : Real = 18.004996448672703;
                        attribute sigma_Cz : Real = 17.326579410092467;
                        attribute Ixx : Real = 22132.93171131268;
                        attribute sigma_Ixx : Real = 8828.700376081164;
                        attribute Iyy : Real = 10358.683744173937;
                        attribute sigma_Iyy : Real = 7075.367114585388;
                        attribute Izz : Real = 16279.860644248276;
                        attribute sigma_Izz : Real = 8002.224904277505;
                        attribute Ixy : Real = -951.930949869887;
                        attribute sigma_Ixy : Real = 3438.9897326489872;
                        attribute Ixz : Real = 33.71696378453504;
                        attribute sigma_Ixz : Real = 3339.1674164534347;
                        attribute Iyz : Real = 5751.233857458236;
                        attribute sigma_Iyz : Real = 4331.1888233602;
                        part <'C.1.1.1.2.2.1'> 'Subassembly 18' {
                            attribute POIconv : String = "-";
                            attribute Ipoint : Boolean = false;
                            attribute mass : Real = 2.985719107903307;
                            attribute sigma_mass : Real = 0.6464332159373649;
                            attribute Cx : Real = -31.084849544878402;
                            attribute sigma_Cx : Real = 18.134388240250463;
                            attribute Cy : Real = -15.535978476584054;
                            attribute sigma_Cy : Real = 18.91635372902149;
                            attribute Cz : Real = 19.656136124276816;
                            attribute sigma_Cz : Real = 18.65745434947184;
                            attribute Ixx : Real = 17467.803890834628;
                            attribute sigma_Ixx : Real = 7825.17483366294;
                            attribute Iyy : Real = 9357.522824038075;
                            attribute sigma_Iyy : Real = 6827.3721967713545;
                            attribute Izz : Real = 12080.376637543657;
                            attribute sigma_Izz : Real = 7018.116155529494;
                            attribute Ixy : Real = -1198.312495535922;
                            attribute sigma_Ixy : Real = 3064.795484020402;
                            attribute Ixz : Real = 475.27013938978985;
                            attribute sigma_Ixz : Real = 3232.8750756886825;
                            attribute Iyz : Real = 5471.256026452589;
                            attribute sigma_Iyz : Real = 3793.3127223728998;
                            part <'C.1.1.1.2.2.1.1'> 'Part 64' {
                                attribute POIconv : String = "-";
                                attribute Ipoint : Boolean = false;
                                attribute mass : Real = 0.9828562500306871;
                                attribute sigma_mass : Real = 0.28909372274994966;
                                attribute Cx : Real = -33.119674399495125;
                                attribute sigma_Cx : Real = 28.721044428837228;
                                attribute Cy : Real = 59.440611535683274;
                                attribute sigma_Cy : Real = 28.23690002309109;
                                attribute Cz : Real = -31.26640967093408;
                                attribute sigma_Cz : Real = 29.057750463592832;
                                attribute Ixx : Real = 0.9128730607994954;
                                attribute sigma_Ixx : Real = 0.37074144170588635;
                                attribute Iyy : Real = 1.0531611829184802;
                                attribute sigma_Iyy : Real = 0.3723953238821935;
                                attribute Izz : Real = 0.9831509706365098;
                                attribute sigma_Izz : Real = 0.37017423652493897;
                                attribute Ixy : Real = 0.03615669069591548;
                                attribute sigma_Ixy : Real = 0.02351283871158888;
                                attribute Ixz : Real = -0.00039552185897018824;
                                attribute sigma_Ixz : Real = 0.022566176940390956;
                                attribute Iyz : Real = -0.005404154703424167;
                                attribute sigma_Iyz : Real = 0.02209918015384651;
                            }
                            part <'C.1.1.1.2.2.1.2'> 'Part 65' {
                                attribute POIconv : String = "-";
                                attribute Ipoint : Boolean = false;
                                attribute mass : Real = 0.12627824692009018;
                                attribute sigma_mass : Real = 0.28909372274994966;
                                attribute Cx : Real = 76.15239098668098;
                                attribute sigma_Cx : Real = 28.721044428837228;
                                attribute Cy : Real = 30.404927721247077;
                                attribute sigma_Cy : Real = 28.23690002309109;
                                attribute Cz : Real = -55.07273371331394;
                                attribute sigma_Cz : Real = 29.057750463592832;
                                attribute Ixx : Real = 0.17865814493628002;
                                attribute sigma_Ixx : Real = 0.37074144170588635;
                                attribute Iyy : Real = 0.18449415187102183;
                                attribute sigma_Iyy : Real = 0.3723953238821935;
                                attribute Izz : Real = 0.17750760496726264;
                                attribute sigma_Izz : Real = 0.37017423652493897;
                                attribute Ixy : Real = 0.0001241612111880214;
                                attribute sigma_Ixy : Real = 0.02351283871158888;
                                attribute Ixz : Real = -0.0037461530554957737;
                                attribute sigma_Ixz : Real = 0.022566176940390956;
                                attribute Iyz : Real = 0.00039726211620278037;
                                attribute sigma_Iyz : Real = 0.02209918015384651;
                            }
                            part <'C.1.1.1.2.2.1.3'> 'Part 66' {
                                attribute POIconv : String = "-";
                                attribute Ipoint : Boolean = false;
                                attribute mass : Real = 0.7898205938499887;
                                attribute sigma_mass : Real = 0.28909372274994966;
                                attribute Cx : Real = -38.762542232871056;
                                attribute sigma_Cx : Real = 28.721044428837228;
                                attribute Cy : Real = -34.38987135887146;
                                attribute sigma_Cy : Real = 28.23690002309109;
                                attribute Cz : Real = 73.17715771496296;
                                attribute sigma_Cz : Real = 29.057750463592832;
                                attribute Ixx : Real = 0.9091259717832947;
                                attribute sigma_Ixx : Real = 0.37074144170588635;
                                attribute Iyy : Real = 0.9063963777014893;
                                attribute sigma_Iyy : Real = 0.3723953238821935;
                                attribute Izz : Real = 1.009195772290123;
                                attribute sigma_Izz : Real = 0.37017423652493897;
                                attribute Ixy : Real = -0.017849097830616653;
                                attribute sigma_Ixy : Real = 0.02351283871158888;
                                attribute Ixz : Real = 0.004864170464651306;
                                attribute sigma_Ixz : Real = 0.022566176940390956;
                                attribute Iyz : Real = -0.03145188336427279;
                                attribute sigma_Iyz : Real = 0.02209918015384651;
                            }
                            part <'C.1.1.1.2.2.1.4'> 'Part 67' {
                                attribute POIconv : String = "+";
                                attribute Ipoint : Boolean = false;
                                attribute mass : Real = 0.36688056779210454;
                                attribute sigma_mass : Real = 0.28909372274994966;
                                attribute Cx : Real = -64.71347692422569;
                                attribute sigma_Cx : Real = 28.721044428837228;
                                attribute Cy : Real = -93.05689525790513;
                                attribute sigma_Cy : Real = 28.23690002309109;
                                attribute Cz : Real = -17.94682159088552;
                                attribute sigma_Cz : Real = 29.057750463592832;
                                attribute Ixx : Real = 0.47382907252434264;
                                attribute sigma_Ixx : Real = 0.37074144170588635;
                                attribute Iyy : Real = 0.455105099554942;
                                attribute sigma_Iyy : Real = 0.3723953238821935;
                                attribute Izz : Real = 0.5438434321860209;
                                attribute sigma_Izz : Real = 0.37017423652493897;
                                attribute Ixy : Real = -0.03237732142462442;
                                attribute sigma_Ixy : Real = 0.02351283871158888;
                                attribute Ixz : Real = 0.012749409023009622;
                                attribute sigma_Ixz : Real = 0.022566176940390956;
                                attribute Iyz : Real = 0.011452654694815215;
                                attribute sigma_Iyz : Real = 0.02209918015384651;
                            }
                            part <'C.1.1.1.2.2.1.5'> 'Part 68' {
                                attribute POIconv : String = "+";
                                attribute Ipoint : Boolean = false;
                                attribute mass : Real = 0.7198834493104368;
                                attribute sigma_mass : Real = 0.28909372274994966;
                                attribute Cx : Real = -21.555669093504548;
                                attribute sigma_Cx : Real = 28.721044428837228;
                                attribute Cy : Real = -65.7669379375875;
                                attribute sigma_Cy : Real = 28.23690002309109;
                                attribute Cz : Real = 62.732501514256;
                                attribute sigma_Cz : Real = 29.057750463592832;
                                attribute Ixx : Real = 0.9597635211222975;
                                attribute sigma_Ixx : Real = 0.37074144170588635;
                                attribute Iyy : Real = 1.011073047390852;
                                attribute sigma_Iyy : Real = 0.3723953238821935;
                                attribute Izz : Real = 1.0585198933053375;
                                attribute sigma_Izz : Real = 0.37017423652493897;
                                attribute Ixy : Real = 0.012916934232068049;
                                attribute sigma_Ixy : Real = 0.02351283871158888;
                                attribute Ixz : Real = -0.04768159311665033;
                                attribute sigma_Ixz : Real = 0.022566176940390956;
                                attribute Iyz : Real = -0.04316320045199108;
                                attribute sigma_Iyz : Real = 0.02209918015384651;
                            }
                        }
                        part <'C.1.1.1.2.2.2'> 'Subassembly 19' {
                            attribute POIconv : String = "-";
                            attribute Ipoint : Boolean = false;
                            attribute mass : Real = 0.49060718065081166;
                            attribute sigma_mass : Real = 0.40884026350990615;
                            attribute Cx : Real = -39.990748203335635;
                            attribute sigma_Cx : Real = 32.576530957761534;
                            attribute Cy : Real = 80.37717542341592;
                            attribute sigma_Cy : Real = 25.009496978879476;
                            attribute Cz : Real = 7.9565514325829865;
                            attribute sigma_Cz : Real = 45.88778035450143;
                            attribute Ixx : Real = 731.1393397981255;
                            attribute sigma_Ixx : Real = 1451.6473476884273;
                            attribute Iyy : Real = 910.0629732018259;
                            attribute sigma_Iyy : Real = 1768.2492080044963;
                            attribute Izz : Real = 289.7517234191343;
                            attribute sigma_Izz : Real = 658.9522448077521;
                            attribute Ixy : Real = -113.54861165999105;
                            attribute sigma_Ixy : Real = 287.8194510217785;
                            attribute Ixz : Real = -397.64852658160794;
                            attribute sigma_Ixz : Real = 793.2397520855385;
                            attribute Iyz : Real = -192.85860248909557;
                            attribute sigma_Iyz : Real = 472.6807849421308;
                            part <'C.1.1.1.2.2.2.1'> 'Part 69' {
                                attribute POIconv : String = "+";
                                attribute Ipoint : Boolean = false;
                                attribute mass : Real = 0.1236639610095881;
                                attribute sigma_mass : Real = 0.28909372274994966;
                                attribute Cx : Real = -2.366035059094429;
                                attribute sigma_Cx : Real = 28.721044428837228;
                                attribute Cy : Real = 98.62749241292477;
                                attribute sigma_Cy : Real = 28.23690002309109;
                                attribute Cz : Real = 71.87450714409351;
                                attribute sigma_Cz : Real = 29.057750463592832;
                                attribute Ixx : Real = 0.15674375452644598;
                                attribute sigma_Ixx : Real = 0.37074144170588635;
                                attribute Iyy : Real = 0.13430617816724458;
                                attribute sigma_Iyy : Real = 0.3723953238821935;
                                attribute Izz : Real = 0.17271513635151836;
                                attribute sigma_Izz : Real = 0.37017423652493897;
                                attribute Ixy : Real = 0.005734368938563279;
                                attribute sigma_Ixy : Real = 0.02351283871158888;
                                attribute Ixz : Real = -0.0003335246358656305;
                                attribute sigma_Ixz : Real = 0.022566176940390956;
                                attribute Iyz : Real = -0.00021345377969578402;
                                attribute sigma_Iyz : Real = 0.02209918015384651;
                            }
                            part <'C.1.1.1.2.2.2.2'> 'Part 70' {
                                attribute POIconv : String = "+";
                                attribute Ipoint : Boolean = false;
                                attribute mass : Real = 0.36694321964122356;
                                attribute sigma_mass : Real = 0.28909372274994966;
                                attribute Cx : Real = -52.6706965174526;
                                attribute sigma_Cx : Real = 28.721044428837228;
                                attribute Cy : Real = 74.22661487944424;
                                attribute sigma_Cy : Real = 28.23690002309109;
                                attribute Cz : Real = -13.584513124078512;
                                attribute sigma_Cz : Real = 29.057750463592832;
                                attribute Ixx : Real = 0.41429691516717526;
                                attribute sigma_Ixx : Real = 0.37074144170588635;
                                attribute Iyy : Real = 0.3722785154372464;
                                attribute sigma_Iyy : Real = 0.3723953238821935;
                                attribute Izz : Real = 0.449921237142715;
                                attribute sigma_Izz : Real = 0.37017423652493897;
                                attribute Ixy : Real = 0.009960438694383851;
                                attribute sigma_Ixy : Real = 0.02351283871158888;
                                attribute Ixz : Real = 0.02333089822050821;
                                attribute sigma_Ixz : Real = 0.022566176940390956;
                                attribute Iyz : Real = -0.014201410038346945;
                                attribute sigma_Iyz : Real = 0.02209918015384651;
                            }
                        }
                    }
                    part <'C.1.1.1.2.3'> 'Assembly 6' {
                        attribute POIconv : String = "-";
                        attribute Ipoint : Boolean = false;
                        attribute mass : Real = 9.078210089001804;
                        attribute sigma_mass : Real = 1.1919639546010696;
                        attribute Cx : Real = 21.13216147354041;
                        attribute sigma_Cx : Real = 13.299946126511072;
                        attribute Cy : Real = -9.394495438278035;
                        attribute sigma_Cy : Real = 10.69335400396562;
                        attribute Cz : Real = -0.013684569243000455;
                        attribute sigma_Cz : Real = 10.504703782383464;
                        attribute Ixx : Real = 36606.92055369168;
                        attribute sigma_Ixx : Real = 12131.678943674167;
                        attribute Iyy : Real = 51877.48546963403;
                        attribute sigma_Iyy : Real = 17416.920147098397;
                        attribute Izz : Real = 59464.298545653706;
                        attribute sigma_Izz : Real = 18755.695183552423;
                        attribute Ixy : Real = -11175.325161844336;
                        attribute sigma_Ixy : Real = 8544.31520947407;
                        attribute Ixz : Real = -1279.6786216435105;
                        attribute sigma_Ixz : Real = 7529.682074582618;
                        attribute Iyz : Real = -105.20090677451788;
                        attribute sigma_Iyz : Real = 5657.05863367521;
                        part <'C.1.1.1.2.3.1'> 'Subassembly 20' {
                            attribute POIconv : String = "-";
                            attribute Ipoint : Boolean = false;
                            attribute mass : Real = 1.8514878613401669;
                            attribute sigma_mass : Real = 0.5781874454998993;
                            attribute Cx : Real = 72.05424026448807;
                            attribute sigma_Cx : Real = 31.159689696155628;
                            attribute Cy : Real = 28.26223767171621;
                            attribute sigma_Cy : Real = 27.10377436795543;
                            attribute Cz : Real = 23.59519717958013;
                            attribute sigma_Cz : Real = 27.967025267744503;
                            attribute Ixx : Real = 8504.390835046788;
                            attribute sigma_Ixx : Real = 6719.422067733626;
                            attribute Iyy : Real = 2306.3915835198895;
                            attribute sigma_Iyy : Real = 7847.50104916943;
                            attribute Izz : Real = 7589.675204297273;
                            attribute sigma_Izz : Real = 7858.350145023858;
                            attribute Ixy : Real = -1846.2738272614974;
                            attribute sigma_Ixy : Real = 3513.4871070389377;
                            attribute Ixz : Real = 681.778685282549;
                            attribute sigma_Ixz : Real = 3648.538152068693;
                            attribute Iyz : Real = 3178.053231592501;
                            attribute sigma_Iyz : Real = 3030.365204195869;
                            part <'C.1.1.1.2.3.1.1'> 'Part 71' {
                                attribute POIconv : String = "-";
                                attribute Ipoint : Boolean = false;
                                attribute mass : Real = 0.007822998428484426;
                                attribute sigma_mass : Real = 0.28909372274994966;
                                attribute Cx : Real = -40.83584323525429;
                                attribute sigma_Cx : Real = 28.721044428837228;
                                attribute Cy : Real = -44.801608100533485;
                                attribute sigma_Cy : Real = 28.23690002309109;
                                attribute Cz : Real = -29.819833021610975;
                                attribute sigma_Cz : Real = 29.057750463592832;
                                attribute Ixx : Real = 0.011551502738626424;
                                attribute sigma_Ixx : Real = 0.37074144170588635;
                                attribute Iyy : Real = 0.009992170720280432;
                                attribute sigma_Iyy : Real = 0.3723953238821935;
                                attribute Izz : Real = 0.01109635881646229;
                                attribute sigma_Izz : Real = 0.37017423652493897;
                                attribute Ixy : Real = -0.0005143711310470591;
                                attribute sigma_Ixy : Real = 0.02351283871158888;
                                attribute Ixz : Real = 0.00012237390421771047;
                                attribute sigma_Ixz : Real = 0.022566176940390956;
                                attribute Iyz : Real = 0.00011134597662428806;
                                attribute sigma_Iyz : Real = 0.02209918015384651;
                            }
                            part <'C.1.1.1.2.3.1.2'> 'Part 72' {
                                attribute POIconv : String = "+";
                                attribute Ipoint : Boolean = false;
                                attribute mass : Real = 0.011006234406260775;
                                attribute sigma_mass : Real = 0.28909372274994966;
                                attribute Cx : Real = -27.485495479777455;
                                attribute sigma_Cx : Real = 28.721044428837228;
                                attribute Cy : Real = 62.73811003193259;
                                attribute sigma_Cy : Real = 28.23690002309109;
                                attribute Cz : Real = -79.21771402470767;
                                attribute sigma_Cz : Real = 29.057750463592832;
                                attribute Ixx : Real = 0.0095934949163012;
                                attribute sigma_Ixx : Real = 0.37074144170588635;
                                attribute Iyy : Real = 0.009551116869749752;
                                attribute sigma_Iyy : Real = 0.3723953238821935;
                                attribute Izz : Real = 0.009548968077839387;
                                attribute sigma_Izz : Real = 0.37017423652493897;
                                attribute Ixy : Real = -7.056898905150784e-05;
                                attribute sigma_Ixy : Real = 0.02351283871158888;
                                attribute Ixz : Real = 3.202951665268411e-06;
                                attribute sigma_Ixz : Real = 0.022566176940390956;
                                attribute Iyz : Real = 3.877224547558983e-06;
                                attribute sigma_Iyz : Real = 0.02209918015384651;
                            }
                            part <'C.1.1.1.2.3.1.3'> 'Part 73' {
                                attribute POIconv : String = "+";
                                attribute Ipoint : Boolean = false;
                                attribute mass : Real = 0.9737113904533907;
                                attribute sigma_mass : Real = 0.28909372274994966;
                                attribute Cx : Real = 88.39750867336988;
                                attribute sigma_Cx : Real = 28.721044428837228;
                                attribute Cy : Real = 85.73678876273334;
                                attribute sigma_Cy : Real = 28.23690002309109;
                                attribute Cz : Real = -2.154058776795864;
                                attribute sigma_Cz : Real = 29.057750463592832;
                                attribute Ixx : Real = 1.3340938923761394;
                                attribute sigma_Ixx : Real = 0.37074144170588635;
                                attribute Iyy : Real = 1.1372455338629872;
                                attribute sigma_Iyy : Real = 0.3723953238821935;
                                attribute Izz : Real = 1.1498063946713875;
                                attribute sigma_Izz : Real = 0.37017423652493897;
                                attribute Ixy : Real = 0.039170954392874296;
                                attribute sigma_Ixy : Real = 0.02351283871158888;
                                attribute Ixz : Real = 0.09851781162341479;
                                attribute sigma_Ixz : Real = 0.022566176940390956;
                                attribute Iyz : Real = -0.01302421448174621;
                                attribute sigma_Iyz : Real = 0.02209918015384651;
                            }
                            part <'C.1.1.1.2.3.1.4'> 'Part 74' {
                                attribute POIconv : String = "-";
                                attribute Ipoint : Boolean = false;
                                attribute mass : Real = 0.858947238052031;
                                attribute sigma_mass : Real = 0.28909372274994966;
                                attribute Cx : Real = 55.83097371272743;
                                attribute sigma_Cx : Real = 28.721044428837228;
                                attribute Cy : Real = -36.66782295331359;
                                attribute sigma_Cy : Real = 28.23690002309109;
                                attribute Cz : Real = 54.58871033042669;
                                attribute sigma_Cz : Real = 29.057750463592832;
                                attribute Ixx : Real = 1.1024439505074801;
                                attribute sigma_Ixx : Real = 0.37074144170588635;
                                attribute Iyy : Real = 0.9761638561988891;
                                attribute sigma_Iyy : Real = 0.3723953238821935;
                                attribute Izz : Real = 1.0304223115500033;
                                attribute sigma_Izz : Real = 0.37017423652493897;
                                attribute Ixy : Real = -0.05459600758184348;
                                attribute sigma_Ixy : Real = 0.02351283871158888;
                                attribute Ixz : Real = 0.03096943892350617;
                                attribute sigma_Ixz : Real = 0.022566176940390956;
                                attribute Iyz : Real = -0.017644373721022545;
                                attribute sigma_Iyz : Real = 0.02209918015384651;
                            }
                        }
                        part <'C.1.1.1.2.3.2'> 'Subassembly 21' {
                            attribute POIconv : String = "-";
                            attribute Ipoint : Boolean = false;
                            attribute mass : Real = 1.8174182377355175;
                            attribute sigma_mass : Real = 0.5007250159521434;
                            attribute Cx : Real = 35.36941141038079;
                            attribute sigma_Cx : Real = 23.063407807046175;
                            attribute Cy : Real = -1.7156771758569205;
                            attribute sigma_Cy : Real = 19.70953450909464;
                            attribute Cz : Real = 25.83548492908735;
                            attribute sigma_Cz : Real = 20.298372743967107;
                            attribute Ixx : Real = 3612.0123295327608;
                            attribute sigma_Ixx : Real = 3040.718289328053;
                            attribute Iyy : Real = 4639.029774812941;
                            attribute sigma_Iyy : Real = 3835.5716850659333;
                            attribute Izz : Real = 3887.4072259395502;
                            attribute sigma_Izz : Real = 3725.8790394283455;
                            attribute Ixy : Real = -1251.3459493584523;
                            attribute sigma_Ixy : Real = 1654.0635540419582;
                            attribute Ixz : Real = -721.0999790716147;
                            attribute sigma_Ixz : Real = 1587.1601554893616;
                            attribute Iyz : Real = 881.1484968601814;
                            attribute sigma_Iyz : Real = 1481.2070528600518;
                            part <'C.1.1.1.2.3.2.1'> 'Part 75' {
                                attribute POIconv : String = "+";
                                attribute Ipoint : Boolean = false;
                                attribute mass : Real = 0.26481551376148127;
                                attribute sigma_mass : Real = 0.28909372274994966;
                                attribute Cx : Real = -53.63753028213978;
                                attribute sigma_Cx : Real = 28.721044428837228;
                                attribute Cy : Real = -46.66466596536338;
                                attribute sigma_Cy : Real = 28.23690002309109;
                                attribute Cz : Real = -0.9244846645742655;
                                attribute sigma_Cz : Real = 29.057750463592832;
                                attribute Ixx : Real = 0.31155615203788484;
                                attribute sigma_Ixx : Real = 0.37074144170588635;
                                attribute Iyy : Real = 0.3374063449454626;
                                attribute sigma_Iyy : Real = 0.3723953238821935;
                                attribute Izz : Real = 0.2642084792059911;
                                attribute sigma_Izz : Real = 0.37017423652493897;
                                attribute Ixy : Real = -0.0028651342545981395;
                                attribute sigma_Ixy : Real = 0.02351283871158888;
                                attribute Ixz : Real = 0.004376458327808952;
                                attribute sigma_Ixz : Real = 0.022566176940390956;
                                attribute Iyz : Real = 0.00671981313787727;
                                attribute sigma_Iyz : Real = 0.02209918015384651;
                            }
                            part <'C.1.1.1.2.3.2.2'> 'Part 76' {
                                attribute POIconv : String = "-";
                                attribute Ipoint : Boolean = false;
                                attribute mass : Real = 0.7251628128180746;
                                attribute sigma_mass : Real = 0.28909372274994966;
                                attribute Cx : Real = 50.216217106208205;
                                attribute sigma_Cx : Real = 28.721044428837228;
                                attribute Cy : Real = -18.339439621195197;
                                attribute sigma_Cy : Real = 28.23690002309109;
                                attribute Cz : Real = 68.33912990987301;
                                attribute sigma_Cz : Real = 29.057750463592832;
                                attribute Ixx : Real = 0.9231240841585072;
                                attribute sigma_Ixx : Real = 0.37074144170588635;
                                attribute Iyy : Real = 1.030388570836557;
                                attribute sigma_Iyy : Real = 0.3723953238821935;
                                attribute Izz : Real = 0.912180235028248;
                                attribute sigma_Izz : Real = 0.37017423652493897;
                                attribute Ixy : Real = -0.08272681975307605;
                                attribute sigma_Ixy : Real = 0.02351283871158888;
                                attribute Ixz : Real = 0.019280188350300147;
                                attribute sigma_Ixz : Real = 0.022566176940390956;
                                attribute Iyz : Real = 0.07808673286905413;
                                attribute sigma_Iyz : Real = 0.02209918015384651;
                            }
                            part <'C.1.1.1.2.3.2.3'> 'Part 77' {
                                attribute POIconv : String = "+";
                                attribute Ipoint : Boolean = false;
                                attribute mass : Real = 0.8274399111559615;
                                attribute sigma_mass : Real = 0.28909372274994966;
                                attribute Cx : Real = 50.84372856654227;
                                attribute sigma_Cx : Real = 28.721044428837228;
                                attribute Cy : Real = 27.238840935751796;
                                attribute sigma_Cy : Real = 28.23690002309109;
                                attribute Cz : Real = -2.8501118533313274;
                                attribute sigma_Cz : Real = 29.057750463592832;
                                attribute Ixx : Real = 1.0936122645996538;
                                attribute sigma_Ixx : Real = 0.37074144170588635;
                                attribute Iyy : Real = 1.197534737156608;
                                attribute sigma_Iyy : Real = 0.3723953238821935;
                                attribute Izz : Real = 1.1891672224475878;
                                attribute sigma_Izz : Real = 0.37017423652493897;
                                attribute Ixy : Real = 0.041248748883859945;
                                attribute sigma_Ixy : Real = 0.02351283871158888;
                                attribute Ixz : Real = 0.05433118366225956;
                                attribute sigma_Ixz : Real = 0.022566176940390956;
                                attribute Iyz : Real = 0.02561028488680142;
                                attribute sigma_Iyz : Real = 0.02209918015384651;
                            }
                        }
                        part <'C.1.1.1.2.3.3'> 'Subassembly 22' {
                            attribute POIconv : String = "-";
                            attribute Ipoint : Boolean = false;
                            attribute mass : Real = 2.882101709661074;
                            attribute sigma_mass : Real = 0.5781874454998993;
                            attribute Cx : Real = -36.34442441882406;
                            attribute sigma_Cx : Real = 17.99918938615993;
                            attribute Cy : Real = -9.336834895780001;
                            attribute sigma_Cy : Real = 16.80052372759336;
                            attribute Cz : Real = -3.5877965699131753;
                            attribute sigma_Cz : Real = 15.85042651716645;
                            attribute Ixx : Real = 8773.803635088723;
                            attribute sigma_Ixx : Real = 4948.881578802702;
                            attribute Iyy : Real = 11583.708031497588;
                            attribute sigma_Iyy : Real = 6028.0223349016;
                            attribute Izz : Real = 15171.986432781168;
                            attribute sigma_Izz : Real = 7293.065036752874;
                            attribute Ixy : Real = -6921.955140371799;
                            attribute sigma_Ixy : Real = 3596.908176220078;
                            attribute Ixz : Real = -474.92016113499324;
                            attribute sigma_Ixz : Real = 2796.1278681046338;
                            attribute Iyz : Real = 144.48870520711114;
                            attribute sigma_Iyz : Real = 2359.0190499853015;
                            part <'C.1.1.1.2.3.3.1'> 'Part 78' {
                                attribute POIconv : String = "+";
                                attribute Ipoint : Boolean = false;
                                attribute mass : Real = 0.7546356687473599;
                                attribute sigma_mass : Real = 0.28909372274994966;
                                attribute Cx : Real = -88.97826941683888;
                                attribute sigma_Cx : Real = 28.721044428837228;
                                attribute Cy : Real = -42.908964306116104;
                                attribute sigma_Cy : Real = 28.23690002309109;
                                attribute Cz : Real = 26.664093229919672;
                                attribute sigma_Cz : Real = 29.057750463592832;
                                attribute Ixx : Real = 0.9921469082791691;
                                attribute sigma_Ixx : Real = 0.37074144170588635;
                                attribute Iyy : Real = 0.8911001917120183;
                                attribute sigma_Iyy : Real = 0.3723953238821935;
                                attribute Izz : Real = 0.9996333147935802;
                                attribute sigma_Izz : Real = 0.37017423652493897;
                                attribute Ixy : Real = 0.03243077703484606;
                                attribute sigma_Ixy : Real = 0.02351283871158888;
                                attribute Ixz : Real = -0.03418935154774299;
                                attribute sigma_Ixz : Real = 0.022566176940390956;
                                attribute Iyz : Real = -0.02459281388571486;
                                attribute sigma_Iyz : Real = 0.02209918015384651;
                            }
                            part <'C.1.1.1.2.3.3.2'> 'Part 79' {
                                attribute POIconv : String = "+";
                                attribute Ipoint : Boolean = false;
                                attribute mass : Real = 0.6828366940831766;
                                attribute sigma_mass : Real = 0.28909372274994966;
                                attribute Cx : Real = -60.35300688818097;
                                attribute sigma_Cx : Real = 28.721044428837228;
                                attribute Cy : Real = -56.18043448776007;
                                attribute sigma_Cy : Real = 28.23690002309109;
                                attribute Cz : Real = -3.304198244586587;
                                attribute sigma_Cz : Real = 29.057750463592832;
                                attribute Ixx : Real = 0.9102177883118019;
                                attribute sigma_Ixx : Real = 0.37074144170588635;
                                attribute Iyy : Real = 0.7294773717185047;
                                attribute sigma_Iyy : Real = 0.3723953238821935;
                                attribute Izz : Real = 0.9001911488394024;
                                attribute sigma_Izz : Real = 0.37017423652493897;
                                attribute Ixy : Real = -0.03685921735404289;
                                attribute sigma_Ixy : Real = 0.02351283871158888;
                                attribute Ixz : Real = -0.013568581638424355;
                                attribute sigma_Ixz : Real = 0.022566176940390956;
                                attribute Iyz : Real = 0.03117987508106529;
                                attribute sigma_Iyz : Real = 0.02209918015384651;
                            }
                            part <'C.1.1.1.2.3.3.3'> 'Part 80' {
                                attribute POIconv : String = "+";
                                attribute Ipoint : Boolean = false;
                                attribute mass : Real = 0.8028958896433469;
                                attribute sigma_mass : Real = 0.28909372274994966;
                                attribute Cx : Real = 51.41779645346105;
                                attribute sigma_Cx : Real = 28.721044428837228;
                                attribute Cy : Real = 59.67926140874624;
                                attribute sigma_Cy : Real = 28.23690002309109;
                                attribute Cz : Real = 9.603276010602713;
                                attribute sigma_Cz : Real = 29.057750463592832;
                                attribute Ixx : Real = 1.0079054880811766;
                                attribute sigma_Ixx : Real = 0.37074144170588635;
                                attribute Iyy : Real = 1.1149655243882572;
                                attribute sigma_Iyy : Real = 0.3723953238821935;
                                attribute Izz : Real = 1.0768822499710498;
                                attribute sigma_Izz : Real = 0.37017423652493897;
                                attribute Ixy : Real = 0.06785926147745266;
                                attribute sigma_Ixy : Real = 0.02351283871158888;
                                attribute Ixz : Real = -0.000293820157681978;
                                attribute sigma_Ixz : Real = 0.022566176940390956;
                                attribute Iyz : Real = 0.0012403797470538157;
                                attribute sigma_Iyz : Real = 0.02209918015384651;
                            }
                            part <'C.1.1.1.2.3.3.4'> 'Part 81' {
                                attribute POIconv : String = "+";
                                attribute Ipoint : Boolean = false;
                                attribute mass : Real = 0.6417334571871907;
                                attribute sigma_mass : Real = 0.28909372274994966;
                                attribute Cx : Real = -58.70668143033981;
                                attribute sigma_Cx : Real = 28.721044428837228;
                                attribute Cy : Real = -6.36283541098237;
                                attribute sigma_Cy : Real = 28.23690002309109;
                                attribute Cz : Real = -55.96758760511875;
                                attribute sigma_Cz : Real = 29.057750463592832;
                                attribute Ixx : Real = 0.8669762979884124;
                                attribute sigma_Ixx : Real = 0.37074144170588635;
                                attribute Iyy : Real = 0.7364008855226749;
                                attribute sigma_Iyy : Real = 0.3723953238821935;
                                attribute Izz : Real = 0.8964697487583941;
                                attribute sigma_Izz : Real = 0.37017423652493897;
                                attribute Ixy : Real = 0.010010641488802109;
                                attribute sigma_Ixy : Real = 0.02351283871158888;
                                attribute Ixz : Real = 0.02707546893380521;
                                attribute sigma_Ixz : Real = 0.022566176940390956;
                                attribute Iyz : Real = 0.012281919114728987;
                                attribute sigma_Iyz : Real = 0.02209918015384651;
                            }
                        }
                        part <'C.1.1.1.2.3.4'> 'Subassembly 23' {
                            attribute POIconv : String = "-";
                            attribute Ipoint : Boolean = false;
                            attribute mass : Real = 1.5022481430880725;
                            attribute sigma_mass : Real = 0.5781874454998993;
                            attribute Cx : Real = 57.85590998876837;
                            attribute sigma_Cx : Real = 40.99915623560246;
                            attribute Cy : Real = -47.29694613143733;
                            attribute sigma_Cy : Real = 27.483165890442557;
                            attribute Cz : Real = -45.983433066512475;
                            attribute sigma_Cz : Real = 23.859849424272813;
                            attribute Ixx : Real = 3353.984831390561;
                            attribute sigma_Ixx : Real = 3701.0909517210875;
                            attribute Iyy : Real = 9677.69241445043;
                            attribute sigma_Iyy : Real = 8002.155180246913;
                            attribute Izz : Real = 9605.152890421672;
                            attribute sigma_Izz : Real = 9586.220341510149;
                            attribute Ixy : Real = 347.462302541331;
                            attribute sigma_Ixy : Real = 3902.740968732921;
                            attribute Ixz : Real = 902.9778215439426;
                            attribute sigma_Ixz : Real = 1976.3836921640095;
                            attribute Iyz : Real = 71.25956817181839;
                            attribute sigma_Iyz : Real = 1063.3063471832702;
                            part <'C.1.1.1.2.3.4.1'> 'Part 82' {
                                attribute POIconv : String = "+";
                                attribute Ipoint : Boolean = false;
                                attribute mass : Real = 0.218199021138018;
                                attribute sigma_mass : Real = 0.28909372274994966;
                                attribute Cx : Real = -84.89080280996859;
                                attribute sigma_Cx : Real = 28.721044428837228;
                                attribute Cy : Real = -87.14131964370608;
                                attribute sigma_Cy : Real = 28.23690002309109;
                                attribute Cz : Real = -35.78796214424074;
                                attribute sigma_Cz : Real = 29.057750463592832;
                                attribute Ixx : Real = 0.26089645683230894;
                                attribute sigma_Ixx : Real = 0.37074144170588635;
                                attribute Iyy : Real = 0.24367161848884702;
                                attribute sigma_Iyy : Real = 0.3723953238821935;
                                attribute Izz : Real = 0.23179783658841557;
                                attribute sigma_Izz : Real = 0.37017423652493897;
                                attribute Ixy : Real = -0.002261864155376762;
                                attribute sigma_Ixy : Real = 0.02351283871158888;
                                attribute Ixz : Real = -0.010163627779620796;
                                attribute sigma_Ixz : Real = 0.022566176940390956;
                                attribute Iyz : Real = -0.0007032633569100514;
                                attribute sigma_Iyz : Real = 0.02209918015384651;
                            }
                            part <'C.1.1.1.2.3.4.2'> 'Part 83' {
                                attribute POIconv : String = "+";
                                attribute Ipoint : Boolean = false;
                                attribute mass : Real = 0.24151459474605508;
                                attribute sigma_mass : Real = 0.28909372274994966;
                                attribute Cx : Real = 91.12854218110442;
                                attribute sigma_Cx : Real = 28.721044428837228;
                                attribute Cy : Real = -60.79755173996091;
                                attribute sigma_Cy : Real = 28.23690002309109;
                                attribute Cz : Real = 23.188514169305563;
                                attribute sigma_Cz : Real = 29.057750463592832;
                                attribute Ixx : Real = 0.2507853333779884;
                                attribute sigma_Ixx : Real = 0.37074144170588635;
                                attribute Iyy : Real = 0.24790091248970633;
                                attribute sigma_Iyy : Real = 0.3723953238821935;
                                attribute Izz : Real = 0.2495395381580272;
                                attribute sigma_Izz : Real = 0.37017423652493897;
                                attribute Ixy : Real = -0.00641294803320176;
                                attribute sigma_Ixy : Real = 0.02351283871158888;
                                attribute Ixz : Real = -0.006484474832168237;
                                attribute sigma_Ixz : Real = 0.022566176940390956;
                                attribute Iyz : Real = 0.004517412851417688;
                                attribute sigma_Iyz : Real = 0.02209918015384651;
                            }
                            part <'C.1.1.1.2.3.4.3'> 'Part 84' {
                                attribute POIconv : String = "-";
                                attribute Ipoint : Boolean = false;
                                attribute mass : Real = 0.13108227028069086;
                                attribute sigma_mass : Real = 0.28909372274994966;
                                attribute Cx : Real = -55.105545883998275;
                                attribute sigma_Cx : Real = 28.721044428837228;
                                attribute Cy : Real = 50.29907142743468;
                                attribute sigma_Cy : Real = 28.23690002309109;
                                attribute Cz : Real = -28.523652302101254;
                                attribute sigma_Cz : Real = 29.057750463592832;
                                attribute Ixx : Real = 0.17823414938489507;
                                attribute sigma_Ixx : Real = 0.37074144170588635;
                                attribute Iyy : Real = 0.16899774076443264;
                                attribute sigma_Iyy : Real = 0.3723953238821935;
                                attribute Izz : Real = 0.1773958050477111;
                                attribute sigma_Izz : Real = 0.37017423652493897;
                                attribute Ixy : Real = 0.005422380925786991;
                                attribute sigma_Ixy : Real = 0.02351283871158888;
                                attribute Ixz : Real = 0.0007495704353869361;
                                attribute sigma_Ixz : Real = 0.022566176940390956;
                                attribute Iyz : Real = -0.0008682237867695884;
                                attribute sigma_Iyz : Real = 0.02209918015384651;
                            }
                            part <'C.1.1.1.2.3.4.4'> 'Part 85' {
                                attribute POIconv : String = "-";
                                attribute Ipoint : Boolean = false;
                                attribute mass : Real = 0.9114522569233086;
                                attribute sigma_mass : Real = 0.28909372274994966;
                                attribute Cx : Real = 99.45832034572959;
                                attribute sigma_Cx : Real = 28.721044428837228;
                                attribute Cy : Real = -48.21691857650876;
                                attribute sigma_Cy : Real = 28.23690002309109;
                                attribute Cz : Real = -69.26424028351903;
                                attribute sigma_Cz : Real = 29.057750463592832;
                                attribute Ixx : Real = 1.3067320479293425;
                                attribute sigma_Ixx : Real = 0.37074144170588635;
                                attribute Iyy : Real = 1.1125524444129244;
                                attribute sigma_Iyy : Real = 0.3723953238821935;
                                attribute Izz : Real = 1.0533387588658123;
                                attribute sigma_Izz : Real = 0.37017423652493897;
                                attribute Ixy : Real = -0.012055424370845285;
                                attribute sigma_Ixy : Real = 0.02351283871158888;
                                attribute Ixz : Real = -0.05322908217825536;
                                attribute sigma_Ixz : Real = 0.022566176940390956;
                                attribute Iyz : Real = -0.030729263493735334;
                                attribute sigma_Iyz : Real = 0.02209918015384651;
                            }
                        }
                        part <'C.1.1.1.2.3.5'> 'Subassembly 24' {
                            attribute POIconv : String = "-";
                            attribute Ipoint : Boolean = false;
                            attribute mass : Real = 1.0249541371769737;
                            attribute sigma_mass : Real = 0.40884026350990615;
                            attribute Cx : Real = 11.696163662880164;
                            attribute sigma_Cx : Real = 22.258830767331236;
                            attribute Cy : Real = -35.64338307650004;
                            attribute sigma_Cy : Real = 21.57651326033222;
                            attribute Cz : Real = -11.069190388901637;
                            attribute sigma_Cz : Real = 23.808089488672305;
                            attribute Ixx : Real = 1182.7600274392516;
                            attribute sigma_Ixx : Real = 1493.1232768735767;
                            attribute Iyy : Real = 1279.8151446810884;
                            attribute sigma_Iyy : Real = 1566.760319508233;
                            attribute Izz : Real = 805.2817421628522;
                            attribute sigma_Izz : Real = 1196.3248252913454;
                            attribute Ixy : Real = 399.1188164003304;
                            attribute sigma_Ixy : Real = 596.6653104478131;
                            attribute Ixz : Real = -610.7642294576864;
                            attribute sigma_Ixz : Real = 776.6758313089089;
                            attribute Iyz : Real = 540.9334709623716;
                            attribute sigma_Iyz : Real = 731.7529172346012;
                            part <'C.1.1.1.2.3.5.1'> 'Part 86' {
                                attribute POIconv : String = "-";
                                attribute Ipoint : Boolean = false;
                                attribute mass : Real = 0.4338953122391831;
                                attribute sigma_mass : Real = 0.28909372274994966;
                                attribute Cx : Real = -12.77408441528678;
                                attribute sigma_Cx : Real = 28.721044428837228;
                                attribute Cy : Real = -13.969493936747313;
                                attribute sigma_Cy : Real = 28.23690002309109;
                                attribute Cz : Real = -44.24185575917363;
                                attribute sigma_Cz : Real = 29.057750463592832;
                                attribute Ixx : Real = 0.49270015055474464;
                                attribute sigma_Ixx : Real = 0.37074144170588635;
                                attribute Iyy : Real = 0.5016157042249995;
                                attribute sigma_Iyy : Real = 0.3723953238821935;
                                attribute Izz : Real = 0.5268220749094653;
                                attribute sigma_Izz : Real = 0.37017423652493897;
                                attribute Ixy : Real = 0.0433617550509799;
                                attribute sigma_Ixy : Real = 0.02351283871158888;
                                attribute Ixz : Real = -0.004072994004007659;
                                attribute sigma_Ixz : Real = 0.022566176940390956;
                                attribute Iyz : Real = -0.03862226545273363;
                                attribute sigma_Iyz : Real = 0.02209918015384651;
                            }
                            part <'C.1.1.1.2.3.5.2'> 'Part 87' {
                                attribute POIconv : String = "+";
                                attribute Ipoint : Boolean = false;
                                attribute mass : Real = 0.5910588249377906;
                                attribute sigma_mass : Real = 0.28909372274994966;
                                attribute Cx : Real = 29.65973257087171;
                                attribute sigma_Cx : Real = 28.721044428837228;
                                attribute Cy : Real = -51.554149482399225;
                                attribute sigma_Cy : Real = 28.23690002309109;
                                attribute Cz : Real = 13.282808754593134;
                                attribute sigma_Cz : Real = 29.057750463592832;
                                attribute Ixx : Real = 0.8345633971161253;
                                attribute sigma_Ixx : Real = 0.37074144170588635;
                                attribute Iyy : Real = 0.7921890857522789;
                                attribute sigma_Iyy : Real = 0.3723953238821935;
                                attribute Izz : Real = 0.7591917307542413;
                                attribute sigma_Izz : Real = 0.37017423652493897;
                                attribute Ixy : Real = -0.019399802419791883;
                                attribute sigma_Ixy : Real = 0.02351283871158888;
                                attribute Ixz : Real = -0.009460651472754125;
                                attribute sigma_Ixz : Real = 0.022566176940390956;
                                attribute Iyz : Real = 0.001293269805567248;
                                attribute sigma_Iyz : Real = 0.02209918015384651;
                            }
                        }
                    }
                }
            }
            part <'C.1.1.2'> 'Element 2' {
                attribute POIconv : String = "-";
                attribute Ipoint : Boolean = false;
                attribute mass : Real = 80.99185942596594;
                attribute sigma_mass : Real = 3.713476105755238;
                attribute Cx : Real = -2.7716296078292766;
                attribute sigma_Cx : Real = 3.8608774079146126;
                attribute Cy : Real = -6.994142999578976;
                attribute sigma_Cy : Real = 3.7626781091737014;
                attribute Cz : Real = 9.626801525301602;
                attribute sigma_Cz : Real = 3.823836682579441;
                attribute Ixx : Real = 511059.8604143616;
                attribute sigma_Ixx : Real = 46332.539980558606;
                attribute Iyy : Real = 523528.98069935397;
                attribute sigma_Iyy : Real = 47971.897218634476;
                attribute Izz : Real = 517922.75207171356;
                attribute sigma_Izz : Real = 47733.255899024065;
                attribute Ixy : Real = -15190.682347913236;
                attribute sigma_Ixy : Real = 22636.14787099054;
                attribute Ixz : Real = -23899.498111684985;
                attribute sigma_Ixz : Real = 22041.19677462406;
                attribute Iyz : Real = -5257.653253892004;
                attribute sigma_Iyz : Real = 21974.979272893903;
                part <'C.1.1.2.1'> 'Subsystem 3' {
                    attribute POIconv : String = "-";
                    attribute Ipoint : Boolean = false;
                    attribute mass : Real = 31.10208924586093;
                    attribute sigma_mass : Real = 2.330748106225254;
                    attribute Cx : Real = -7.243284935740914;
                    attribute sigma_Cx : Real = 5.954391808303331;
                    attribute Cy : Real = -13.175801016532661;
                    attribute sigma_Cy : Real = 6.09019070174313;
                    attribute Cz : Real = 7.635114260644034;
                    attribute sigma_Cz : Real = 6.282540012754396;
                    attribute Ixx : Real = 195549.51497256552;
                    attribute sigma_Ixx : Real = 29927.030824992693;
                    attribute Iyy : Real = 184230.70198091198;
                    attribute sigma_Iyy : Real = 28072.320695870618;
                    attribute Izz : Real = 179362.85316143982;
                    attribute sigma_Izz : Real = 27273.675733182685;
                    attribute Ixy : Real = -22130.60635752217;
                    attribute sigma_Ixy : Real = 12437.517011405063;
                    attribute Ixz : Real = -6675.170600048159;
                    attribute sigma_Ixz : Real = 12573.104035937455;
                    attribute Iyz : Real = -3065.568975264808;
                    attribute sigma_Iyz : Real = 14546.540357747157;
                    part <'C.1.1.2.1.1'> 'Assembly 7' {
                        attribute POIconv : String = "-";
                        attribute Ipoint : Boolean = false;
                        attribute mass : Real = 3.926830982407788;
                        attribute sigma_mass : Real = 0.8176805270198123;
                        attribute Cx : Real = 18.448372189787772;
                        attribute sigma_Cx : Real = 14.120187213473823;
                        attribute Cy : Real = -15.186517698996226;
                        attribute sigma_Cy : Real = 15.558616423059577;
                        attribute Cz : Real = -7.2240905612289845;
                        attribute sigma_Cz : Real = 16.559655613591726;
                        attribute Ixx : Real = 21537.101639913795;
                        attribute sigma_Ixx : Real = 8164.1913399039;
                        attribute Iyy : Real = 17264.883767524072;
                        attribute sigma_Iyy : Real = 7575.993922064101;
                        attribute Izz : Real = 17408.458931132638;
                        attribute sigma_Izz : Real = 7240.567803171479;
                        attribute Ixy : Real = -134.33673353767585;
                        attribute sigma_Ixy : Real = 3403.4720618139913;
                        attribute Ixz : Real = 4440.57764451798;
                        attribute sigma_Ixz : Real = 3591.630337194447;
                        attribute Iyz : Real = -2771.2966590152364;
                        attribute sigma_Iyz : Real = 3808.557354285215;
                        part <'C.1.1.2.1.1.1'> 'Subassembly 25' {
                            attribute POIconv : String = "-";
                            attribute Ipoint : Boolean = false;
                            attribute mass : Real = 2.092671863288153;
                            attribute sigma_mass : Real = 0.5781874454998993;
                            attribute Cx : Real = 3.659592419533546;
                            attribute sigma_Cx : Real = 19.943743613940008;
                            attribute Cy : Real = -38.073714231253106;
                            attribute sigma_Cy : Real = 19.964634714056007;
                            attribute Cz : Real = 0.28647126359020153;
                            attribute sigma_Cz : Real = 20.30080988965288;
                            attribute Ixx : Real = 10608.722225651241;
                            attribute sigma_Ixx : Real = 5543.050150325134;
                            attribute Iyy : Real = 10005.542161035408;
                            attribute sigma_Iyy : Real = 5914.358757953528;
                            attribute Izz : Real = 10070.71587295416;
                            attribute sigma_Izz : Real = 5546.9086010978335;
                            attribute Ixy : Real = 2641.958148167829;
                            attribute sigma_Ixy : Real = 2528.9045792505535;
                            attribute Ixz : Real = 4377.2862058626615;
                            attribute sigma_Ixz : Real = 2913.333134576498;
                            attribute Iyz : Real = -373.0271571602024;
                            attribute sigma_Iyz : Real = 2335.924091842963;
                            part <'C.1.1.2.1.1.1.1'> 'Part 88' {
                                attribute POIconv : String = "+";
                                attribute Ipoint : Boolean = false;
                                attribute mass : Real = 0.6574666414444801;
                                attribute sigma_mass : Real = 0.28909372274994966;
                                attribute Cx : Real = -9.622719464823604;
                                attribute sigma_Cx : Real = 28.721044428837228;
                                attribute Cy : Real = -82.01006525196135;
                                attribute sigma_Cy : Real = 28.23690002309109;
                                attribute Cz : Real = 46.11129076220095;
                                attribute sigma_Cz : Real = 29.057750463592832;
                                attribute Ixx : Real = 0.7924319434190586;
                                attribute sigma_Ixx : Real = 0.37074144170588635;
                                attribute Iyy : Real = 0.7951552296965433;
                                attribute sigma_Iyy : Real = 0.3723953238821935;
                                attribute Izz : Real = 0.8517165241991727;
                                attribute sigma_Izz : Real = 0.37017423652493897;
                                attribute Ixy : Real = 0.018472004886994693;
                                attribute sigma_Ixy : Real = 0.02351283871158888;
                                attribute Ixz : Real = 0.02031593818065161;
                                attribute sigma_Ixz : Real = 0.022566176940390956;
                                attribute Iyz : Real = -0.0405560443178258;
                                attribute sigma_Iyz : Real = 0.02209918015384651;
                            }
                            part <'C.1.1.2.1.1.1.2'> 'Part 89' {
                                attribute POIconv : String = "+";
                                attribute Ipoint : Boolean = false;
                                attribute mass : Real = 0.4924646405968815;
                                attribute sigma_mass : Real = 0.28909372274994966;
                                attribute Cx : Real = -52.681920398026705;
                                attribute sigma_Cx : Real = 28.721044428837228;
                                attribute Cy : Real = 50.23396322503686;
                                attribute sigma_Cy : Real = 28.23690002309109;
                                attribute Cz : Real = 24.14228324778378;
                                attribute sigma_Cz : Real = 29.057750463592832;
                                attribute Ixx : Real = 0.5381535340322877;
                                attribute sigma_Ixx : Real = 0.37074144170588635;
                                attribute Iyy : Real = 0.5285273533443069;
                                attribute sigma_Iyy : Real = 0.3723953238821935;
                                attribute Izz : Real = 0.5669012014808583;
                                attribute sigma_Izz : Real = 0.37017423652493897;
                                attribute Ixy : Real = -0.05549247648288142;
                                attribute sigma_Ixy : Real = 0.02351283871158888;
                                attribute Ixz : Real = -0.02178819035792537;
                                attribute sigma_Ixz : Real = 0.022566176940390956;
                                attribute Iyz : Real = 0.02070791522660934;
                                attribute sigma_Iyz : Real = 0.02209918015384651;
                            }
                            part <'C.1.1.2.1.1.1.3'> 'Part 90' {
                                attribute POIconv : String = "+";
                                attribute Ipoint : Boolean = false;
                                attribute mass : Real = 0.46895969050144776;
                                attribute sigma_mass : Real = 0.28909372274994966;
                                attribute Cx : Real = 0.40842434391379356;
                                attribute sigma_Cx : Real = 28.721044428837228;
                                attribute Cy : Real = -53.29704228788614;
                                attribute sigma_Cy : Real = 28.23690002309109;
                                attribute Cz : Real = -0.8331109769642353;
                                attribute sigma_Cz : Real = 29.057750463592832;
                                attribute Ixx : Real = 0.4546870890483837;
                                attribute sigma_Ixx : Real = 0.37074144170588635;
                                attribute Iyy : Real = 0.4412517242475275;
                                attribute sigma_Iyy : Real = 0.3723953238821935;
                                attribute Izz : Real = 0.487322858126521;
                                attribute sigma_Izz : Real = 0.37017423652493897;
                                attribute Ixy : Real = -0.024311548527731784;
                                attribute sigma_Ixy : Real = 0.02351283871158888;
                                attribute Ixz : Real = -0.017274549465124384;
                                attribute sigma_Ixz : Real = 0.022566176940390956;
                                attribute Iyz : Real = 0.004452458694065321;
                                attribute sigma_Iyz : Real = 0.02209918015384651;
                            }
                            part <'C.1.1.2.1.1.1.4'> 'Part 91' {
                                attribute POIconv : String = "+";
                                attribute Ipoint : Boolean = false;
                                attribute mass : Real = 0.47378089074534363;
                                attribute sigma_mass : Real = 0.28909372274994966;
                                attribute Cx : Real = 83.87293019331992;
                                attribute sigma_Cx : Real = 28.721044428837228;
                                attribute Cy : Real = -53.82486931048334;
                                attribute sigma_Cy : Real = 28.23690002309109;
                                attribute Cz : Real = -86.99310440570116;
                                attribute sigma_Cz : Real = 29.057750463592832;
                                attribute Ixx : Real = 0.5702519029418239;
                                attribute sigma_Ixx : Real = 0.37074144170588635;
                                attribute Iyy : Real = 0.5707611064209885;
                                attribute sigma_Iyy : Real = 0.3723953238821935;
                                attribute Izz : Real = 0.44679084025344334;
                                attribute sigma_Izz : Real = 0.37017423652493897;
                                attribute Ixy : Real = 0.013209199407745268;
                                attribute sigma_Ixy : Real = 0.02351283871158888;
                                attribute Ixz : Real = 0.0405193281179539;
                                attribute sigma_Ixz : Real = 0.022566176940390956;
                                attribute Iyz : Real = -0.00669167558083413;
                                attribute sigma_Iyz : Real = 0.02209918015384651;
                            }
                        }
                        part <'C.1.1.2.1.1.2'> 'Subassembly 26' {
                            attribute POIconv : String = "-";
                            attribute Ipoint : Boolean = false;
                            attribute mass : Real = 0.44724628169578495;
                            attribute sigma_mass : Real = 0.40884026350990615;
                            attribute Cx : Real = 2.2856479233597664;
                            attribute sigma_Cx : Real = 28.187327777649195;
                            attribute Cy : Real = -60.372735222919104;
                            attribute sigma_Cy : Real = 29.935228107760206;
                            attribute Cz : Real = -75.90150821125144;
                            attribute sigma_Cz : Real = 31.88747766940589;
                            attribute Ixx : Real = 66.43421835895188;
                            attribute sigma_Ixx : Real = 408.25079359378685;
                            attribute Iyy : Real = 51.930145022815054;
                            attribute sigma_Iyy : Real = 323.537214062695;
                            attribute Izz : Real = 42.32794831038103;
                            attribute sigma_Izz : Real = 266.4269415538156;
                            attribute Ixy : Real = -19.672518122464155;
                            attribute sigma_Ixy : Real = 126.3901146066945;
                            attribute Ixz : Real = -22.735693155696953;
                            attribute sigma_Ixz : Real = 145.45809511642162;
                            attribute Iyz : Real = -32.641425492486185;
                            attribute sigma_Iyz : Real = 202.09855774209026;
                            part <'C.1.1.2.1.1.2.1'> 'Part 92' {
                                attribute POIconv : String = "-";
                                attribute Ipoint : Boolean = false;
                                attribute mass : Real = 0.4027995278642047;
                                attribute sigma_mass : Real = 0.28909372274994966;
                                attribute Cx : Real = 0.4480175208300352;
                                attribute sigma_Cx : Real = 28.721044428837228;
                                attribute Cy : Real = -63.00972164608538;
                                attribute sigma_Cy : Real = 28.23690002309109;
                                attribute Cz : Real = -78.95387476310134;
                                attribute sigma_Cz : Real = 29.057750463592832;
                                attribute Ixx : Real = 0.4273179242513523;
                                attribute sigma_Ixx : Real = 0.37074144170588635;
                                attribute Iyy : Real = 0.4206934605165544;
                                attribute sigma_Iyy : Real = 0.3723953238821935;
                                attribute Izz : Real = 0.4108415499291919;
                                attribute sigma_Izz : Real = 0.37017423652493897;
                                attribute Ixy : Real = -0.03166915929328816;
                                attribute sigma_Ixy : Real = 0.02351283871158888;
                                attribute Ixz : Real = -0.001699789323999096;
                                attribute sigma_Ixz : Real = 0.022566176940390956;
                                attribute Iyz : Real = -0.016090761653504978;
                                attribute sigma_Iyz : Real = 0.02209918015384651;
                            }
                            part <'C.1.1.2.1.1.2.2'> 'Part 93' {
                                attribute POIconv : String = "-";
                                attribute Ipoint : Boolean = false;
                                attribute mass : Real = 0.04444675383158028;
                                attribute sigma_mass : Real = 0.28909372274994966;
                                attribute Cx : Real = 18.939207401126623;
                                attribute sigma_Cx : Real = 28.721044428837228;
                                attribute Cy : Real = -36.474997038021684;
                                attribute sigma_Cy : Real = 28.23690002309109;
                                attribute Cz : Real = -48.239379934966564;
                                attribute sigma_Cz : Real = 29.057750463592832;
                                attribute Ixx : Real = 0.05910955818898015;
                                attribute sigma_Ixx : Real = 0.37074144170588635;
                                attribute Iyy : Real = 0.05911488550148282;
                                attribute sigma_Iyy : Real = 0.3723953238821935;
                                attribute Izz : Real = 0.04541863753698516;
                                attribute sigma_Izz : Real = 0.37017423652493897;
                                attribute Ixy : Real = 6.552667550428597e-05;
                                attribute sigma_Ixy : Real = 0.02351283871158888;
                                attribute Ixz : Real = 0.0007730737843838365;
                                attribute sigma_Ixz : Real = 0.022566176940390956;
                                attribute Iyz : Real = -0.0011082519822138797;
                                attribute sigma_Iyz : Real = 0.02209918015384651;
                            }
                        }
                        part <'C.1.1.2.1.1.3'> 'Subassembly 27' {
                            attribute POIconv : String = "-";
                            attribute Ipoint : Boolean = false;
                            attribute mass : Real = 1.3869128374238497;
                            attribute sigma_mass : Real = 0.40884026350990615;
                            attribute Cx : Real = 45.974818421782054;
                            attribute sigma_Cx : Real = 21.990779219641507;
                            attribute Cy : Real = 33.91877439028473;
                            attribute sigma_Cy : Real = 21.49215558349183;
                            attribute Cz : Real = 3.590272005358258;
                            attribute sigma_Cz : Real = 26.91590516160563;
                            attribute Ixx : Real = 3118.5439869239817;
                            attribute sigma_Ixx : Real = 2891.1264374868733;
                            attribute Iyy : Real = 3192.299525646607;
                            attribute sigma_Iyy : Real = 2934.4221842427464;
                            attribute Izz : Real = 316.3438342481182;
                            attribute sigma_Izz : Real = 797.9249160329323;
                            attribute Ixy : Real = 153.0124965926031;
                            attribute sigma_Ixy : Real = 397.0680092431421;
                            attribute Ixz : Real = 762.8970551106598;
                            attribute sigma_Ixz : Real = 1306.0885957361024;
                            attribute Iyz : Real = -600.9126228368458;
                            attribute sigma_Iyz : Real = 1253.8892215561918;
                            part <'C.1.1.2.1.1.3.1'> 'Part 94' {
                                attribute POIconv : String = "-";
                                attribute Ipoint : Boolean = false;
                                attribute mass : Real = 0.9471763216597028;
                                attribute sigma_mass : Real = 0.28909372274994966;
                                attribute Cx : Real = 54.03835880570114;
                                attribute sigma_Cx : Real = 28.721044428837228;
                                attribute Cy : Real = 27.56751603446901;
                                attribute sigma_Cy : Real = 28.23690002309109;
                                attribute Cz : Real = -28.08032790198922;
                                attribute sigma_Cz : Real = 29.057750463592832;
                                attribute Ixx : Real = 0.9798330028301497;
                                attribute sigma_Ixx : Real = 0.37074144170588635;
                                attribute Iyy : Real = 0.9949873229584618;
                                attribute sigma_Iyy : Real = 0.3723953238821935;
                                attribute Izz : Real = 0.9417741044320632;
                                attribute sigma_Izz : Real = 0.37017423652493897;
                                attribute Ixy : Real = 0.01744203300808802;
                                attribute sigma_Ixy : Real = 0.02351283871158888;
                                attribute Ixz : Real = -0.004605669246334959;
                                attribute sigma_Ixz : Real = 0.022566176940390956;
                                attribute Iyz : Real = -0.010021208555445638;
                                attribute sigma_Iyz : Real = 0.02209918015384651;
                            }
                            part <'C.1.1.2.1.1.3.2'> 'Part 95' {
                                attribute POIconv : String = "+";
                                attribute Ipoint : Boolean = false;
                                attribute mass : Real = 0.439736515764147;
                                attribute sigma_mass : Real = 0.28909372274994966;
                                attribute Cx : Real = 28.606248274445534;
                                attribute sigma_Cx : Real = 28.721044428837228;
                                attribute Cy : Real = 47.5991518702358;
                                attribute sigma_Cy : Real = 28.23690002309109;
                                attribute Cz : Real = 71.80758225731552;
                                attribute sigma_Cz : Real = 29.057750463592832;
                                attribute Ixx : Real = 0.6568081797107248;
                                attribute sigma_Ixx : Real = 0.37074144170588635;
                                attribute Iyy : Real = 0.6625887377436849;
                                attribute sigma_Iyy : Real = 0.3723953238821935;
                                attribute Izz : Real = 0.6563679169580535;
                                attribute sigma_Izz : Real = 0.37017423652493897;
                                attribute Ixy : Real = -0.0015424657956183627;
                                attribute sigma_Ixy : Real = 0.02351283871158888;
                                attribute Ixz : Real = 0.0016945065018968268;
                                attribute sigma_Ixz : Real = 0.022566176940390956;
                                attribute Iyz : Real = 0.000754642355537635;
                                attribute sigma_Iyz : Real = 0.02209918015384651;
                            }
                        }
                    }
                    part <'C.1.1.2.1.2'> 'Assembly 8' {
                        attribute POIconv : String = "-";
                        attribute Ipoint : Boolean = false;
                        attribute mass : Real = 6.940011611938011;
                        attribute sigma_mass : Real = 1.1563748909997988;
                        attribute Cx : Real = 12.005671772880175;
                        attribute sigma_Cx : Real = 11.797635855890384;
                        attribute Cy : Real = -7.108156807800963;
                        attribute sigma_Cy : Real = 12.887739740463571;
                        attribute Cz : Real = 3.326826137649392;
                        attribute sigma_Cz : Real = 13.213037119595953;
                        attribute Ixx : Real = 47296.59138885018;
                        attribute sigma_Ixx : Real = 13734.616872859613;
                        attribute Iyy : Real = 41717.271207037964;
                        attribute sigma_Iyy : Real = 12438.536282867508;
                        attribute Izz : Real = 36668.96762867633;
                        attribute sigma_Izz : Real = 12170.093521147583;
                        attribute Ixy : Real = 2914.8484567007736;
                        attribute sigma_Ixy : Real = 5884.160233478635;
                        attribute Ixz : Real = -409.83684279987597;
                        attribute sigma_Ixz : Real = 5612.768569356403;
                        attribute Iyz : Real = 8951.812765591552;
                        attribute sigma_Iyz : Real = 6636.09651885218;
                        part <'C.1.1.2.1.2.1'> 'Subassembly 28' {
                            attribute POIconv : String = "-";
                            attribute Ipoint : Boolean = false;
                            attribute mass : Real = 0.7414431805375498;
                            attribute sigma_mass : Real = 0.40884026350990615;
                            attribute Cx : Real = -25.936361285305612;
                            attribute sigma_Cx : Real = 52.62745910115064;
                            attribute Cy : Real = 70.74356829865289;
                            attribute sigma_Cy : Real = 32.189285281426905;
                            attribute Cz : Real = 58.12528287851918;
                            attribute sigma_Cz : Real = 23.61567143229109;
                            attribute Ixx : Real = 967.1093478100763;
                            attribute sigma_Ixx : Real = 1393.3858329447467;
                            attribute Iyy : Real = 3717.5960456654448;
                            attribute sigma_Iyy : Real = 4343.837344007049;
                            attribute Izz : Real = 4529.588143192426;
                            attribute sigma_Izz : Real = 5198.350284711526;
                            attribute Ixy : Real = 1798.8429238822307;
                            attribute sigma_Ixy : Real = 2154.9532633599847;
                            attribute Ixz : Real = 529.7617384266601;
                            attribute sigma_Ixz : Real = 1110.0335523744059;
                            attribute Iyz : Real = -261.8452744243051;
                            attribute sigma_Iyz : Real = 560.8046942820981;
                            part <'C.1.1.2.1.2.1.1'> 'Part 96' {
                                attribute POIconv : String = "-";
                                attribute Ipoint : Boolean = false;
                                attribute mass : Real = 0.5393943031483796;
                                attribute sigma_mass : Real = 0.28909372274994966;
                                attribute Cx : Real = -68.81726724095643;
                                attribute sigma_Cx : Real = 28.721044428837228;
                                attribute Cy : Real = 91.93735397420824;
                                attribute sigma_Cy : Real = 28.23690002309109;
                                attribute Cz : Real = 64.3666127230972;
                                attribute sigma_Cz : Real = 29.057750463592832;
                                attribute Ixx : Real = 0.6301237938341671;
                                attribute sigma_Ixx : Real = 0.37074144170588635;
                                attribute Iyy : Real = 0.5888884112792817;
                                attribute sigma_Iyy : Real = 0.3723953238821935;
                                attribute Izz : Real = 0.6293742206466112;
                                attribute sigma_Izz : Real = 0.37017423652493897;
                                attribute Ixy : Real = 0.0004626238561429355;
                                attribute sigma_Ixy : Real = 0.02351283871158888;
                                attribute Ixz : Real = 0.012250424958473064;
                                attribute sigma_Ixz : Real = 0.022566176940390956;
                                attribute Iyz : Real = -0.026700290258722614;
                                attribute sigma_Iyz : Real = 0.02209918015384651;
                            }
                            part <'C.1.1.2.1.2.1.2'> 'Part 97' {
                                attribute POIconv : String = "-";
                                attribute Ipoint : Boolean = false;
                                attribute mass : Real = 0.20204887738917024;
                                attribute sigma_mass : Real = 0.28909372274994966;
                                attribute Cx : Real = 88.53948577307165;
                                attribute sigma_Cx : Real = 28.721044428837228;
                                attribute Cy : Real = 14.164153439924121;
                                attribute sigma_Cy : Real = 28.23690002309109;
                                attribute Cz : Real = 41.46328601054847;
                                attribute sigma_Cz : Real = 29.057750463592832;
                                attribute Ixx : Real = 0.28607160305904084;
                                attribute sigma_Ixx : Real = 0.37074144170588635;
                                attribute Iyy : Real = 0.28517430896600515;
                                attribute sigma_Iyy : Real = 0.3723953238821935;
                                attribute Izz : Real = 0.25346213061390016;
                                attribute sigma_Izz : Real = 0.37017423652493897;
                                attribute Ixy : Real = -0.029609555966824234;
                                attribute sigma_Ixy : Real = 0.02351283871158888;
                                attribute Ixz : Real = 0.002036837234827192;
                                attribute sigma_Ixz : Real = 0.022566176940390956;
                                attribute Iyz : Real = 0.00784235452367836;
                                attribute sigma_Iyz : Real = 0.02209918015384651;
                            }
                        }
                        part <'C.1.1.2.1.2.2'> 'Subassembly 29' {
                            attribute POIconv : String = "-";
                            attribute Ipoint : Boolean = false;
                            attribute mass : Real = 2.6461780288012235;
                            attribute sigma_mass : Real = 0.6464332159373649;
                            attribute Cx : Real = 12.717147972456896;
                            attribute sigma_Cx : Real = 19.065497889817046;
                            attribute Cy : Real = -29.262561765479223;
                            attribute sigma_Cy : Real = 15.427768395345428;
                            attribute Cz : Real = 28.933911444968803;
                            attribute sigma_Cz : Real = 17.751745391388415;
                            attribute Ixx : Real = 7380.618683771712;
                            attribute sigma_Ixx : Real = 4675.5079572783625;
                            attribute Iyy : Real = 15395.482538986864;
                            attribute sigma_Iyy : Real = 7282.441755999258;
                            attribute Izz : Real = 10567.367581379629;
                            attribute sigma_Izz : Real = 5627.617321775604;
                            attribute Ixy : Real = 1527.742683718479;
                            attribute sigma_Ixy : Real = 2541.4624763399315;
                            attribute Ixz : Real = -6559.094056572442;
                            attribute sigma_Ixz : Real = 3536.8034795157055;
                            attribute Iyz : Real = 1561.0088072082247;
                            attribute sigma_Iyz : Real = 2129.06093332823;
                            part <'C.1.1.2.1.2.2.1'> 'Part 98' {
                                attribute POIconv : String = "-";
                                attribute Ipoint : Boolean = false;
                                attribute mass : Real = 0.31876291493442843;
                                attribute sigma_mass : Real = 0.28909372274994966;
                                attribute Cx : Real = 9.423621464520693;
                                attribute sigma_Cx : Real = 28.721044428837228;
                                attribute Cy : Real = -76.59441861324012;
                                attribute sigma_Cy : Real = 28.23690002309109;
                                attribute Cz : Real = 34.241784596815705;
                                attribute sigma_Cz : Real = 29.057750463592832;
                                attribute Ixx : Real = 0.45276553903435485;
                                attribute sigma_Ixx : Real = 0.37074144170588635;
                                attribute Iyy : Real = 0.4477806520181036;
                                attribute sigma_Iyy : Real = 0.3723953238821935;
                                attribute Izz : Real = 0.44939573846567454;
                                attribute sigma_Izz : Real = 0.37017423652493897;
                                attribute Ixy : Real = 0.00038987387953538257;
                                attribute sigma_Ixy : Real = 0.02351283871158888;
                                attribute Ixz : Real = 0.012101613284788024;
                                attribute sigma_Ixz : Real = 0.022566176940390956;
                                attribute Iyz : Real = 0.00096679887112024;
                                attribute sigma_Iyz : Real = 0.02209918015384651;
                            }
                            part <'C.1.1.2.1.2.2.2'> 'Part 99' {
                                attribute POIconv : String = "+";
                                attribute Ipoint : Boolean = false;
                                attribute mass : Real = 0.999165522782132;
                                attribute sigma_mass : Real = 0.28909372274994966;
                                attribute Cx : Real = 82.50024197623134;
                                attribute sigma_Cx : Real = 28.721044428837228;
                                attribute Cy : Real = -33.414676040410995;
                                attribute sigma_Cy : Real = 28.23690002309109;
                                attribute Cz : Real = 81.18700222112238;
                                attribute sigma_Cz : Real = 29.057750463592832;
                                attribute Ixx : Real = 1.1615261593187678;
                                attribute sigma_Ixx : Real = 0.37074144170588635;
                                attribute Iyy : Real = 1.290035689438555;
                                attribute sigma_Iyy : Real = 0.3723953238821935;
                                attribute Izz : Real = 1.168166682415794;
                                attribute sigma_Izz : Real = 0.37017423652493897;
                                attribute Ixy : Real = -0.06772558979515193;
                                attribute sigma_Ixy : Real = 0.02351283871158888;
                                attribute Ixz : Real = -0.028036399076493256;
                                attribute sigma_Ixz : Real = 0.022566176940390956;
                                attribute Iyz : Real = -0.06935514753619343;
                                attribute sigma_Iyz : Real = 0.02209918015384651;
                            }
                            part <'C.1.1.2.1.2.2.3'> 'Part 100' {
                                attribute POIconv : String = "+";
                                attribute Ipoint : Boolean = false;
                                attribute mass : Real = 0.24935771647607907;
                                attribute sigma_mass : Real = 0.28909372274994966;
                                attribute Cx : Real = 11.009952751919627;
                                attribute sigma_Cx : Real = 28.721044428837228;
                                attribute Cy : Real = -39.608294470235705;
                                attribute sigma_Cy : Real = 28.23690002309109;
                                attribute Cz : Real = 17.131019476801157;
                                attribute sigma_Cz : Real = 29.057750463592832;
                                attribute Ixx : Real = 0.33388424797610067;
                                attribute sigma_Ixx : Real = 0.37074144170588635;
                                attribute Iyy : Real = 0.2942537482264843;
                                attribute sigma_Iyy : Real = 0.3723953238821935;
                                attribute Izz : Real = 0.29891979413677994;
                                attribute sigma_Izz : Real = 0.37017423652493897;
                                attribute Ixy : Real = -0.011388587464819112;
                                attribute sigma_Ixy : Real = 0.02351283871158888;
                                attribute Ixz : Real = -0.02256524728127142;
                                attribute sigma_Ixz : Real = 0.022566176940390956;
                                attribute Iyz : Real = -0.005011723668057726;
                                attribute sigma_Iyz : Real = 0.02209918015384651;
                            }
                            part <'C.1.1.2.1.2.2.4'> 'Part 101' {
                                attribute POIconv : String = "-";
                                attribute Ipoint : Boolean = false;
                                attribute mass : Real = 0.5708077931087464;
                                attribute sigma_mass : Real = 0.28909372274994966;
                                attribute Cx : Real = -41.36252854950726;
                                attribute sigma_Cx : Real = 28.721044428837228;
                                attribute Cy : Real = -1.1480579618364573;
                                attribute sigma_Cy : Real = 28.23690002309109;
                                attribute Cz : Real = -45.905264373868704;
                                attribute sigma_Cz : Real = 29.057750463592832;
                                attribute Ixx : Real = 0.7606852600168091;
                                attribute sigma_Ixx : Real = 0.37074144170588635;
                                attribute Iyy : Real = 0.8736279477916913;
                                attribute sigma_Iyy : Real = 0.3723953238821935;
                                attribute Izz : Real = 0.7134443470120105;
                                attribute sigma_Izz : Real = 0.37017423652493897;
                                attribute Ixy : Real = 0.04281651319206434;
                                attribute sigma_Ixy : Real = 0.02351283871158888;
                                attribute Ixz : Real = 0.025386948155731837;
                                attribute sigma_Ixz : Real = 0.022566176940390956;
                                attribute Iyz : Real = 0.010743995688391616;
                                attribute sigma_Iyz : Real = 0.02209918015384651;
                            }
                            part <'C.1.1.2.1.2.2.5'> 'Part 102' {
                                attribute POIconv : String = "+";
                                attribute Ipoint : Boolean = false;
                                attribute mass : Real = 0.5080840814998373;
                                attribute sigma_mass : Real = 0.28909372274994966;
                                attribute Cx : Real = -60.853754449635744;
                                attribute sigma_Cx : Real = 28.721044428837228;
                                attribute Cy : Real = -17.909912252798676;
                                attribute sigma_Cy : Real = 28.23690002309109;
                                attribute Cz : Real = 12.717081978917122;
                                attribute sigma_Cz : Real = 29.057750463592832;
                                attribute Ixx : Real = 0.7214159180406441;
                                attribute sigma_Ixx : Real = 0.37074144170588635;
                                attribute Iyy : Real = 0.8067006977063836;
                                attribute sigma_Iyy : Real = 0.3723953238821935;
                                attribute Izz : Real = 0.7445761369363252;
                                attribute sigma_Izz : Real = 0.37017423652493897;
                                attribute Ixy : Real = 0.02329447671543433;
                                attribute sigma_Ixy : Real = 0.02351283871158888;
                                attribute Ixz : Real = -0.015864256628876652;
                                attribute sigma_Ixz : Real = 0.022566176940390956;
                                attribute Iyz : Real = 0.04908564739978493;
                                attribute sigma_Iyz : Real = 0.02209918015384651;
                            }
                        }
                        part <'C.1.1.2.1.2.3'> 'Subassembly 30' {
                            attribute POIconv : String = "-";
                            attribute Ipoint : Boolean = false;
                            attribute mass : Real = 2.416090603514807;
                            attribute sigma_mass : Real = 0.6464332159373649;
                            attribute Cx : Real = 24.320456071860413;
                            attribute sigma_Cx : Real = 17.378445160194715;
                            attribute Cy : Real = -4.623946652768595;
                            attribute sigma_Cy : Real = 20.93251793554547;
                            attribute Cz : Real = -44.17121513958639;
                            attribute sigma_Cz : Real = 16.593549282693576;
                            attribute Ixx : Real = 7101.225128241741;
                            attribute sigma_Ixx : Real = 4976.930690165969;
                            attribute Iyy : Real = 2207.8639241641536;
                            attribute sigma_Iyy : Real = 2505.746331422166;
                            attribute Izz : Real = 6290.454926209955;
                            attribute sigma_Izz : Real = 5369.064985875599;
                            attribute Ixy : Real = -696.2305699670277;
                            attribute sigma_Ixy : Real = 2538.1217762845954;
                            attribute Ixz : Real = 853.0081492886227;
                            attribute sigma_Ixz : Real = 1115.892825957959;
                            attribute Iyz : Real = 1173.837027690698;
                            attribute sigma_Iyz : Real = 2136.808851176025;
                            part <'C.1.1.2.1.2.3.1'> 'Part 103' {
                                attribute POIconv : String = "+";
                                attribute Ipoint : Boolean = false;
                                attribute mass : Real = 0.581501622005133;
                                attribute sigma_mass : Real = 0.28909372274994966;
                                attribute Cx : Real = 24.297722475603223;
                                attribute sigma_Cx : Real = 28.721044428837228;
                                attribute Cy : Real = -29.563105758279562;
                                attribute sigma_Cy : Real = 28.23690002309109;
                                attribute Cz : Real = -60.83531677722931;
                                attribute sigma_Cz : Real = 29.057750463592832;
                                attribute Ixx : Real = 0.6869823446580784;
                                attribute sigma_Ixx : Real = 0.37074144170588635;
                                attribute Iyy : Real = 0.7357506812592337;
                                attribute sigma_Iyy : Real = 0.3723953238821935;
                                attribute Izz : Real = 0.7255234154866275;
                                attribute sigma_Izz : Real = 0.37017423652493897;
                                attribute Ixy : Real = 0.023871852892238234;
                                attribute sigma_Ixy : Real = 0.02351283871158888;
                                attribute Ixz : Real = 0.02182471828754266;
                                attribute sigma_Ixz : Real = 0.022566176940390956;
                                attribute Iyz : Real = -0.04390258665021367;
                                attribute sigma_Iyz : Real = 0.02209918015384651;
                            }
                            part <'C.1.1.2.1.2.3.2'> 'Part 104' {
                                attribute POIconv : String = "-";
                                attribute Ipoint : Boolean = false;
                                attribute mass : Real = 0.01941261755884625;
                                attribute sigma_mass : Real = 0.28909372274994966;
                                attribute Cx : Real = -39.41521588712931;
                                attribute sigma_Cx : Real = 28.721044428837228;
                                attribute Cy : Real = 86.56577104702592;
                                attribute sigma_Cy : Real = 28.23690002309109;
                                attribute Cz : Real = -61.78977703675628;
                                attribute sigma_Cz : Real = 29.057750463592832;
                                attribute Ixx : Real = 0.0230874765117583;
                                attribute sigma_Ixx : Real = 0.37074144170588635;
                                attribute Iyy : Real = 0.021308903506686388;
                                attribute sigma_Iyy : Real = 0.3723953238821935;
                                attribute Izz : Real = 0.022986244700695838;
                                attribute sigma_Izz : Real = 0.37017423652493897;
                                attribute Ixy : Real = -0.0004941765127886633;
                                attribute sigma_Ixy : Real = 0.02351283871158888;
                                attribute Ixz : Real = -0.001607974957150781;
                                attribute sigma_Ixz : Real = 0.022566176940390956;
                                attribute Iyz : Real = 0.0006699659480864147;
                                attribute sigma_Iyz : Real = 0.02209918015384651;
                            }
                            part <'C.1.1.2.1.2.3.3'> 'Part 105' {
                                attribute POIconv : String = "-";
                                attribute Ipoint : Boolean = false;
                                attribute mass : Real = 0.3169937257275451;
                                attribute sigma_mass : Real = 0.28909372274994966;
                                attribute Cx : Real = 60.75515071861446;
                                attribute sigma_Cx : Real = 28.721044428837228;
                                attribute Cy : Real = 2.8717597015202045;
                                attribute sigma_Cy : Real = 28.23690002309109;
                                attribute Cz : Real = -86.10042594373226;
                                attribute sigma_Cz : Real = 29.057750463592832;
                                attribute Ixx : Real = 0.3780976956715486;
                                attribute sigma_Ixx : Real = 0.37074144170588635;
                                attribute Iyy : Real = 0.38337554064719276;
                                attribute sigma_Iyy : Real = 0.3723953238821935;
                                attribute Izz : Real = 0.430035437146418;
                                attribute sigma_Izz : Real = 0.37017423652493897;
                                attribute Ixy : Real = -0.0010617603542956782;
                                attribute sigma_Ixy : Real = 0.02351283871158888;
                                attribute Ixz : Real = 0.00481900730311614;
                                attribute sigma_Ixz : Real = 0.022566176940390956;
                                attribute Iyz : Real = -0.011816701013258917;
                                attribute sigma_Iyz : Real = 0.02209918015384651;
                            }
                            part <'C.1.1.2.1.2.3.4'> 'Part 106' {
                                attribute POIconv : String = "-";
                                attribute Ipoint : Boolean = false;
                                attribute mass : Real = 0.7171664482057094;
                                attribute sigma_mass : Real = 0.28909372274994966;
                                attribute Cx : Real = 7.859595865011215;
                                attribute sigma_Cx : Real = 28.721044428837228;
                                attribute Cy : Real = -57.86468884907663;
                                attribute sigma_Cy : Real = 28.23690002309109;
                                attribute Cz : Real = -11.13087204284966;
                                attribute sigma_Cz : Real = 29.057750463592832;
                                attribute Ixx : Real = 1.03411822750131;
                                attribute sigma_Ixx : Real = 0.37074144170588635;
                                attribute Iyy : Real = 1.0543906151676048;
                                attribute sigma_Iyy : Real = 0.3723953238821935;
                                attribute Izz : Real = 1.0422294659697258;
                                attribute sigma_Izz : Real = 0.37017423652493897;
                                attribute Ixy : Real = -0.0042345953824020535;
                                attribute sigma_Ixy : Real = 0.02351283871158888;
                                attribute Ixz : Real = 0.05645923623199884;
                                attribute sigma_Ixz : Real = 0.022566176940390956;
                                attribute Iyz : Real = -0.01745081317211243;
                                attribute sigma_Iyz : Real = 0.02209918015384651;
                            }
                            part <'C.1.1.2.1.2.3.5'> 'Part 107' {
                                attribute POIconv : String = "+";
                                attribute Ipoint : Boolean = false;
                                attribute mass : Real = 0.7810161900175735;
                                attribute sigma_mass : Real = 0.28909372274994966;
                                attribute Cx : Real = 26.248844899237156;
                                attribute sigma_Cx : Real = 28.721044428837228;
                                attribute Cy : Real = 57.523692632094026;
                                attribute sigma_Cy : Real = 28.23690002309109;
                                attribute Cz : Real = -44.64739505201578;
                                attribute sigma_Cz : Real = 29.057750463592832;
                                attribute Ixx : Real = 0.9088588251040798;
                                attribute sigma_Ixx : Real = 0.37074144170588635;
                                attribute Iyy : Real = 0.8972887982764585;
                                attribute sigma_Iyy : Real = 0.3723953238821935;
                                attribute Izz : Real = 1.0286008441917176;
                                attribute sigma_Izz : Real = 0.37017423652493897;
                                attribute Ixy : Real = 0.008802699271537838;
                                attribute sigma_Ixy : Real = 0.02351283871158888;
                                attribute Ixz : Real = 0.03897664736977276;
                                attribute sigma_Ixz : Real = 0.022566176940390956;
                                attribute Iyz : Real = 0.004378579248974263;
                                attribute sigma_Iyz : Real = 0.02209918015384651;
                            }
                        }
                        part <'C.1.1.2.1.2.4'> 'Subassembly 31' {
                            attribute POIconv : String = "-";
                            attribute Ipoint : Boolean = false;
                            attribute mass : Real = 1.1362997990844306;
                            attribute sigma_mass : Real = 0.5781874454998993;
                            attribute Cx : Real = 8.921568746095927;
                            attribute sigma_Cx : Real = 20.926006869293722;
                            attribute Cy : Real = -11.596591858066997;
                            attribute sigma_Cy : Real = 39.14125006971471;
                            attribute Cz : Real = 8.931616919142368;
                            attribute sigma_Cz : Real = 44.51814530786015;
                            attribute Ixx : Real = 16569.070931789942;
                            attribute sigma_Ixx : Real = 9057.965603028415;
                            attribute Iyy : Real = 9502.223811808595;
                            attribute sigma_Iyy : Real = 6039.31321472745;
                            attribute Izz : Real = 8005.220082929573;
                            attribute sigma_Izz : Real = 4889.643212853519;
                            attribute Ixy : Real = -1857.6866306002198;
                            attribute sigma_Ixy : Real = 1972.8477431501854;
                            attribute Ixz : Real = 1840.2338311981541;
                            attribute sigma_Ixz : Real = 2168.9069271805943;
                            attribute Iyz : Real = 7827.048231532041;
                            attribute sigma_Iyz : Real = 4450.054497526543;
                            part <'C.1.1.2.1.2.4.1'> 'Part 108' {
                                attribute POIconv : String = "-";
                                attribute Ipoint : Boolean = false;
                                attribute mass : Real = 0.5589087291043252;
                                attribute sigma_mass : Real = 0.28909372274994966;
                                attribute Cx : Real = -11.67716491036117;
                                attribute sigma_Cx : Real = 28.721044428837228;
                                attribute Cy : Real = -92.76235578581691;
                                attribute sigma_Cy : Real = 28.23690002309109;
                                attribute Cz : Real = 88.77333477139473;
                                attribute sigma_Cz : Real = 29.057750463592832;
                                attribute Ixx : Real = 0.737069725504405;
                                attribute sigma_Ixx : Real = 0.37074144170588635;
                                attribute Iyy : Real = 0.7012343186114927;
                                attribute sigma_Iyy : Real = 0.3723953238821935;
                                attribute Izz : Real = 0.698167848653303;
                                attribute sigma_Izz : Real = 0.37017423652493897;
                                attribute Ixy : Real = -0.002877409958384863;
                                attribute sigma_Ixy : Real = 0.02351283871158888;
                                attribute Ixz : Real = -0.0066432327710345355;
                                attribute sigma_Ixz : Real = 0.022566176940390956;
                                attribute Iyz : Real = 0.0011374349917477645;
                                attribute sigma_Iyz : Real = 0.02209918015384651;
                            }
                            part <'C.1.1.2.1.2.4.2'> 'Part 109' {
                                attribute POIconv : String = "+";
                                attribute Ipoint : Boolean = false;
                                attribute mass : Real = 0.4450532393651083;
                                attribute sigma_mass : Real = 0.28909372274994966;
                                attribute Cx : Real = 29.549271566793323;
                                attribute sigma_Cx : Real = 28.721044428837228;
                                attribute Cy : Real = 79.00358750484884;
                                attribute sigma_Cy : Real = 28.23690002309109;
                                attribute Cz : Real = -99.61457783356309;
                                attribute sigma_Cz : Real = 29.057750463592832;
                                attribute Ixx : Real = 0.5222635125076712;
                                attribute sigma_Ixx : Real = 0.37074144170588635;
                                attribute Iyy : Real = 0.4987335501835786;
                                attribute sigma_Iyy : Real = 0.3723953238821935;
                                attribute Izz : Real = 0.5323706972642985;
                                attribute sigma_Izz : Real = 0.37017423652493897;
                                attribute Ixy : Real = -0.04973439046222403;
                                attribute sigma_Ixy : Real = 0.02351283871158888;
                                attribute Ixz : Real = 0.03416611457543074;
                                attribute sigma_Ixz : Real = 0.022566176940390956;
                                attribute Iyz : Real = -0.023478425982874543;
                                attribute sigma_Iyz : Real = 0.02209918015384651;
                            }
                            part <'C.1.1.2.1.2.4.3'> 'Part 110' {
                                attribute POIconv : String = "+";
                                attribute Ipoint : Boolean = false;
                                attribute mass : Real = 0.030119509148411452;
                                attribute sigma_mass : Real = 0.28909372274994966;
                                attribute Cx : Real = 31.330942641943693;
                                attribute sigma_Cx : Real = 28.721044428837228;
                                attribute Cy : Real = 40.80635840073228;
                                attribute sigma_Cy : Real = 28.23690002309109;
                                attribute Cz : Real = 92.96931806020439;
                                attribute sigma_Cz : Real = 29.057750463592832;
                                attribute Ixx : Real = 0.038950297981389014;
                                attribute sigma_Ixx : Real = 0.37074144170588635;
                                attribute Iyy : Real = 0.0348127022016938;
                                attribute sigma_Iyy : Real = 0.3723953238821935;
                                attribute Izz : Real = 0.03807755275498147;
                                attribute sigma_Izz : Real = 0.37017423652493897;
                                attribute Ixy : Real = -0.00024114116855189483;
                                attribute sigma_Ixy : Real = 0.02351283871158888;
                                attribute Ixz : Real = -0.0029343003495598333;
                                attribute sigma_Ixz : Real = 0.022566176940390956;
                                attribute Iyz : Real = 0.0008446988898124146;
                                attribute sigma_Iyz : Real = 0.02209918015384651;
                            }
                            part <'C.1.1.2.1.2.4.4'> 'Part 111' {
                                attribute POIconv : String = "-";
                                attribute Ipoint : Boolean = false;
                                attribute mass : Real = 0.10221832146658562;
                                attribute sigma_mass : Real = 0.28909372274994966;
                                attribute Cx : Real = 25.13614478521049;
                                attribute sigma_Cx : Real = 28.721044428837228;
                                attribute Cy : Real = 22.29165304452181;
                                attribute sigma_Cy : Real = 28.23690002309109;
                                attribute Cz : Real = 20.215584570541978;
                                attribute sigma_Cz : Real = 29.057750463592832;
                                attribute Ixx : Real = 0.1325092216258331;
                                attribute sigma_Ixx : Real = 0.37074144170588635;
                                attribute Iyy : Real = 0.123676805384576;
                                attribute sigma_Iyy : Real = 0.3723953238821935;
                                attribute Izz : Real = 0.13601064976554533;
                                attribute sigma_Izz : Real = 0.37017423652493897;
                                attribute Ixy : Real = -0.002160799402098139;
                                attribute sigma_Ixy : Real = 0.02351283871158888;
                                attribute Ixz : Real = -0.006908083565418185;
                                attribute sigma_Ixz : Real = 0.022566176940390956;
                                attribute Iyz : Real = 0.003984872657702617;
                                attribute sigma_Iyz : Real = 0.02209918015384651;
                            }
                        }
                    }
                    part <'C.1.1.2.1.3'> 'Assembly 9' {
                        attribute POIconv : String = "-";
                        attribute Ipoint : Boolean = false;
                        attribute mass : Real = 5.966892361626495;
                        attribute sigma_mass : Real = 1.0014500319042867;
                        attribute Cx : Real = -6.321583324278089;
                        attribute sigma_Cx : Real = 11.7164001944689;
                        attribute Cy : Real = -17.680570733944467;
                        attribute sigma_Cy : Real = 14.668074442847834;
                        attribute Cz : Real = 22.42538007681673;
                        attribute sigma_Cz : Real = 14.884047862048364;
                        attribute Ixx : Real = 35523.66271630823;
                        attribute sigma_Ixx : Real = 17220.42552775749;
                        attribute Iyy : Real = 23661.132442336413;
                        attribute sigma_Iyy : Real = 11871.04425747594;
                        attribute Izz : Real = 27396.130399111087;
                        attribute sigma_Izz : Real = 11006.512204119554;
                        attribute Ixy : Real = -5314.31086586635;
                        attribute sigma_Ixy : Real = 4146.465983804102;
                        attribute Ixz : Real = -1120.1701344042042;
                        attribute sigma_Ixz : Real = 3952.9576965271685;
                        attribute Iyz : Real = -10243.256024236083;
                        attribute sigma_Iyz : Real = 8541.583246315977;
                        part <'C.1.1.2.1.3.1'> 'Subassembly 32' {
                            attribute POIconv : String = "-";
                            attribute Ipoint : Boolean = false;
                            attribute mass : Real = 1.749881868400844;
                            attribute sigma_mass : Real = 0.5781874454998993;
                            attribute Cx : Real = -7.6690623015879416;
                            attribute sigma_Cx : Real = 24.071417140659026;
                            attribute Cy : Real = 18.17809022971308;
                            attribute sigma_Cy : Real = 20.324995925784766;
                            attribute Cz : Real = 44.77661740883856;
                            attribute sigma_Cz : Real = 26.26936445766005;
                            attribute Ixx : Real = 2057.84558424132;
                            attribute sigma_Ixx : Real = 4259.210664849703;
                            attribute Iyy : Real = 4524.668231467736;
                            attribute sigma_Iyy : Real = 4840.956864868523;
                            attribute Izz : Real = 4240.63849572025;
                            attribute sigma_Izz : Real = 3331.4674087937915;
                            attribute Ixy : Real = -456.3055355201641;
                            attribute sigma_Ixy : Real = 1506.8834261911093;
                            attribute Ixz : Real = -229.49711216940446;
                            attribute sigma_Ixz : Real = 1892.1277092573089;
                            attribute Iyz : Real = 912.7530292384373;
                            attribute sigma_Iyz : Real = 1696.2490804603872;
                            part <'C.1.1.2.1.3.1.1'> 'Part 112' {
                                attribute POIconv : String = "+";
                                attribute Ipoint : Boolean = false;
                                attribute mass : Real = 0.9338561952691525;
                                attribute sigma_mass : Real = 0.28909372274994966;
                                attribute Cx : Real = 5.118827288970351;
                                attribute sigma_Cx : Real = 28.721044428837228;
                                attribute Cy : Real = 38.082514423877;
                                attribute sigma_Cy : Real = 28.23690002309109;
                                attribute Cz : Real = 26.7289356328547;
                                attribute sigma_Cz : Real = 29.057750463592832;
                                attribute Ixx : Real = 1.1653744023503134;
                                attribute sigma_Ixx : Real = 0.37074144170588635;
                                attribute Iyy : Real = 1.0217089291343224;
                                attribute sigma_Iyy : Real = 0.3723953238821935;
                                attribute Izz : Real = 1.1819552403384748;
                                attribute sigma_Izz : Real = 0.37017423652493897;
                                attribute Ixy : Real = 0.024492219948517715;
                                attribute sigma_Ixy : Real = 0.02351283871158888;
                                attribute Ixz : Real = 0.022118243911945664;
                                attribute sigma_Ixz : Real = 0.022566176940390956;
                                attribute Iyz : Real = 0.058857174830539566;
                                attribute sigma_Iyz : Real = 0.02209918015384651;
                            }
                            part <'C.1.1.2.1.3.1.2'> 'Part 113' {
                                attribute POIconv : String = "-";
                                attribute Ipoint : Boolean = false;
                                attribute mass : Real = 0.46186563328118063;
                                attribute sigma_mass : Real = 0.28909372274994966;
                                attribute Cx : Real = -75.57860091328621;
                                attribute sigma_Cx : Real = 28.721044428837228;
                                attribute Cy : Real = -4.03018151409924;
                                attribute sigma_Cy : Real = 28.23690002309109;
                                attribute Cz : Real = 53.984742099419236;
                                attribute sigma_Cz : Real = 29.057750463592832;
                                attribute Ixx : Real = 0.6544389798744261;
                                attribute sigma_Ixx : Real = 0.37074144170588635;
                                attribute Iyy : Real = 0.6051954167904072;
                                attribute sigma_Iyy : Real = 0.3723953238821935;
                                attribute Izz : Real = 0.6569215736905387;
                                attribute sigma_Izz : Real = 0.37017423652493897;
                                attribute Ixy : Real = 0.008806620127162554;
                                attribute sigma_Ixy : Real = 0.02351283871158888;
                                attribute Ixz : Real = 0.05389548984110589;
                                attribute sigma_Ixz : Real = 0.022566176940390956;
                                attribute Iyz : Real = 0.007088110613877704;
                                attribute sigma_Iyz : Real = 0.02209918015384651;
                            }
                            part <'C.1.1.2.1.3.1.3'> 'Part 114' {
                                attribute POIconv : String = "-";
                                attribute Ipoint : Boolean = false;
                                attribute mass : Real = 0.3358498263717629;
                                attribute sigma_mass : Real = 0.28909372274994966;
                                attribute Cx : Real = 48.036784678697586;
                                attribute sigma_Cx : Real = 28.721044428837228;
                                attribute Cy : Real = -9.105567447841167;
                                attribute sigma_Cy : Real = 28.23690002309109;
                                attribute Cz : Real = 87.98765544779599;
                                attribute sigma_Cz : Real = 29.057750463592832;
                                attribute Ixx : Real = 0.4036096597763855;
                                attribute sigma_Ixx : Real = 0.37074144170588635;
                                attribute Iyy : Real = 0.30456547608063844;
                                attribute sigma_Iyy : Real = 0.3723953238821935;
                                attribute Izz : Real = 0.38373968395260816;
                                attribute sigma_Izz : Real = 0.37017423652493897;
                                attribute Ixy : Real = 0.005718439933556093;
                                attribute sigma_Ixy : Real = 0.02351283871158888;
                                attribute Ixz : Real = -0.0019330384034318149;
                                attribute sigma_Ixz : Real = 0.022566176940390956;
                                attribute Iyz : Real = 0.02271026451536909;
                                attribute sigma_Iyz : Real = 0.02209918015384651;
                            }
                            part <'C.1.1.2.1.3.1.4'> 'Part 115' {
                                attribute POIconv : String = "-";
                                attribute Ipoint : Boolean = false;
                                attribute mass : Real = 0.018310213478747756;
                                attribute sigma_mass : Real = 0.28909372274994966;
                                attribute Cx : Real = 31.33829841390252;
                                attribute sigma_Cx : Real = 28.721044428837228;
                                attribute Cy : Real = 63.64885116927326;
                                attribute sigma_Cy : Real = 28.23690002309109;
                                attribute Cz : Real = -59.613018995150924;
                                attribute sigma_Cz : Real = 29.057750463592832;
                                attribute Ixx : Real = 0.019225622157582483;
                                attribute sigma_Ixx : Real = 0.37074144170588635;
                                attribute Iyy : Real = 0.022425787941668107;
                                attribute sigma_Iyy : Real = 0.3723953238821935;
                                attribute Izz : Real = 0.023856757290600834;
                                attribute sigma_Izz : Real = 0.37017423652493897;
                                attribute Ixy : Real = 0.0005787205242036946;
                                attribute sigma_Ixy : Real = 0.02351283871158888;
                                attribute Ixz : Real = 0.0012334291663465362;
                                attribute sigma_Ixz : Real = 0.022566176940390956;
                                attribute Iyz : Real = -0.00033729378829955233;
                                attribute sigma_Iyz : Real = 0.02209918015384651;
                            }
                        }
                        part <'C.1.1.2.1.3.2'> 'Subassembly 33' {
                            attribute POIconv : String = "-";
                            attribute Ipoint : Boolean = false;
                            attribute mass : Real = 1.6961654523094185;
                            attribute sigma_mass : Real = 0.5007250159521434;
                            attribute Cx : Real = 2.1100759138696272;
                            attribute sigma_Cx : Real = 21.66683725625312;
                            attribute Cy : Real = -51.349370181503815;
                            attribute sigma_Cy : Real = 19.054274112699964;
                            attribute Cz : Real = 9.907759222590665;
                            attribute sigma_Cz : Real = 18.953663577901832;
                            attribute Ixx : Real = 2041.2310418837362;
                            attribute sigma_Ixx : Real = 2049.2257741197404;
                            attribute Iyy : Real = 3389.4523885549897;
                            attribute sigma_Iyy : Real = 2872.0103889218944;
                            attribute Izz : Real = 3737.8788265312987;
                            attribute sigma_Izz : Real = 3133.3967628713735;
                            attribute Ixy : Real = -1587.3778978871935;
                            attribute sigma_Ixy : Real = 1509.3803417215563;
                            attribute Ixz : Real = 1358.0725782616196;
                            attribute sigma_Ixz : Real = 1341.6556000262308;
                            attribute Iyz : Real = 692.1001214233353;
                            attribute sigma_Iyz : Real = 1012.5626036643738;
                            part <'C.1.1.2.1.3.2.1'> 'Part 116' {
                                attribute POIconv : String = "-";
                                attribute Ipoint : Boolean = false;
                                attribute mass : Real = 0.3936766101690009;
                                attribute sigma_mass : Real = 0.28909372274994966;
                                attribute Cx : Real = -67.25974958389997;
                                attribute sigma_Cx : Real = 28.721044428837228;
                                attribute Cy : Real = -98.08319783769548;
                                attribute sigma_Cy : Real = 28.23690002309109;
                                attribute Cz : Real = 44.33659543283284;
                                attribute sigma_Cz : Real = 29.057750463592832;
                                attribute Ixx : Real = 0.5036420194160385;
                                attribute sigma_Ixx : Real = 0.37074144170588635;
                                attribute Iyy : Real = 0.4364101412128482;
                                attribute sigma_Iyy : Real = 0.3723953238821935;
                                attribute Izz : Real = 0.40619304174458926;
                                attribute sigma_Izz : Real = 0.37017423652493897;
                                attribute Ixy : Real = -0.01574896619593659;
                                attribute sigma_Ixy : Real = 0.02351283871158888;
                                attribute Ixz : Real = -0.003018634211898349;
                                attribute sigma_Ixz : Real = 0.022566176940390956;
                                attribute Iyz : Real = 0.012361048749388657;
                                attribute sigma_Iyz : Real = 0.02209918015384651;
                            }
                            part <'C.1.1.2.1.3.2.2'> 'Part 117' {
                                attribute POIconv : String = "-";
                                attribute Ipoint : Boolean = false;
                                attribute mass : Real = 0.5246422383305617;
                                attribute sigma_mass : Real = 0.28909372274994966;
                                attribute Cx : Real = 32.32352756895125;
                                attribute sigma_Cx : Real = 28.721044428837228;
                                attribute Cy : Real = -46.409074077382684;
                                attribute sigma_Cy : Real = 28.23690002309109;
                                attribute Cz : Real = -16.949916956946254;
                                attribute sigma_Cz : Real = 29.057750463592832;
                                attribute Ixx : Real = 0.6436906708469579;
                                attribute sigma_Ixx : Real = 0.37074144170588635;
                                attribute Iyy : Real = 0.6149535511979446;
                                attribute sigma_Iyy : Real = 0.3723953238821935;
                                attribute Izz : Real = 0.7098660760803621;
                                attribute sigma_Izz : Real = 0.37017423652493897;
                                attribute Ixy : Real = 0.011890361589308753;
                                attribute sigma_Ixy : Real = 0.02351283871158888;
                                attribute Ixz : Real = -0.0021314587259172865;
                                attribute sigma_Ixz : Real = 0.022566176940390956;
                                attribute Iyz : Real = 0.0028707870176387803;
                                attribute sigma_Iyz : Real = 0.02209918015384651;
                            }
                            part <'C.1.1.2.1.3.2.3'> 'Part 118' {
                                attribute POIconv : String = "-";
                                attribute Ipoint : Boolean = false;
                                attribute mass : Real = 0.7778466038098559;
                                attribute sigma_mass : Real = 0.28909372274994966;
                                attribute Cx : Real = 16.84051863849163;
                                attribute sigma_Cx : Real = 28.721044428837228;
                                attribute Cy : Real = -31.029005255550146;
                                attribute sigma_Cy : Real = 28.23690002309109;
                                attribute Cz : Real = 10.597925912588835;
                                attribute sigma_Cz : Real = 29.057750463592832;
                                attribute Ixx : Real = 0.8273860842706021;
                                attribute sigma_Ixx : Real = 0.37074144170588635;
                                attribute Iyy : Real = 0.8026428459334166;
                                attribute sigma_Iyy : Real = 0.3723953238821935;
                                attribute Izz : Real = 0.8194783115407178;
                                attribute sigma_Izz : Real = 0.37017423652493897;
                                attribute Ixy : Real = 0.03416966765977332;
                                attribute sigma_Ixy : Real = 0.02351283871158888;
                                attribute Ixz : Real = 0.031207226482758837;
                                attribute sigma_Ixz : Real = 0.022566176940390956;
                                attribute Iyz : Real = -0.04057685660210353;
                                attribute sigma_Iyz : Real = 0.02209918015384651;
                            }
                        }
                        part <'C.1.1.2.1.3.3'> 'Subassembly 34' {
                            attribute POIconv : String = "-";
                            attribute Ipoint : Boolean = false;
                            attribute mass : Real = 1.3894437424989883;
                            attribute sigma_mass : Real = 0.5007250159521434;
                            attribute Cx : Real = -2.443398947419296;
                            attribute sigma_Cx : Real = 21.442037792241926;
                            attribute Cy : Real = 5.345178308115871;
                            attribute sigma_Cy : Real = 29.022499095213114;
                            attribute Cz : Real = 66.92340456056074;
                            attribute sigma_Cz : Real = 18.887773372674808;
                            attribute Ixx : Real = 6990.08338578325;
                            attribute sigma_Ixx : Real = 4388.765180732865;
                            attribute Iyy : Real = 1625.883998580981;
                            attribute sigma_Iyy : Real = 1822.0330027973232;
                            attribute Izz : Real = 8121.360754743575;
                            attribute sigma_Izz : Real = 4797.845944904423;
                            attribute Ixy : Real = -2524.8656926147896;
                            attribute sigma_Ixy : Real = 2186.256525446597;
                            attribute Ixz : Real = -443.7676224295219;
                            attribute sigma_Ixz : Real = 890.8737315595885;
                            attribute Iyz : Real = -1281.024845702742;
                            attribute sigma_Iyz : Real = 1904.9295649589171;
                            part <'C.1.1.2.1.3.3.1'> 'Part 119' {
                                attribute POIconv : String = "-";
                                attribute Ipoint : Boolean = false;
                                attribute mass : Real = 0.18373120276862756;
                                attribute sigma_mass : Real = 0.28909372274994966;
                                attribute Cx : Real = 31.09825341962278;
                                attribute sigma_Cx : Real = 28.721044428837228;
                                attribute Cy : Real = -24.085907684639096;
                                attribute sigma_Cy : Real = 28.23690002309109;
                                attribute Cz : Real = 57.6162351295352;
                                attribute sigma_Cz : Real = 29.057750463592832;
                                attribute Ixx : Real = 0.27372510531737737;
                                attribute sigma_Ixx : Real = 0.37074144170588635;
                                attribute Iyy : Real = 0.23628389847206127;
                                attribute sigma_Iyy : Real = 0.3723953238821935;
                                attribute Izz : Real = 0.24874276083070115;
                                attribute sigma_Izz : Real = 0.37017423652493897;
                                attribute Ixy : Real = 0.01729516478271456;
                                attribute sigma_Ixy : Real = 0.02351283871158888;
                                attribute Ixz : Real = -0.006797130441033234;
                                attribute sigma_Ixz : Real = 0.022566176940390956;
                                attribute Iyz : Real = 0.00623895865617146;
                                attribute sigma_Iyz : Real = 0.02209918015384651;
                            }
                            part <'C.1.1.2.1.3.3.2'> 'Part 120' {
                                attribute POIconv : String = "-";
                                attribute Ipoint : Boolean = false;
                                attribute mass : Real = 0.6625305184298195;
                                attribute sigma_mass : Real = 0.28909372274994966;
                                attribute Cx : Real = -35.391599126160145;
                                attribute sigma_Cx : Real = 28.721044428837228;
                                attribute Cy : Real = -56.95078456774354;
                                attribute sigma_Cy : Real = 28.23690002309109;
                                attribute Cz : Real = 55.88827421888709;
                                attribute sigma_Cz : Real = 29.057750463592832;
                                attribute Ixx : Real = 0.6410104854477704;
                                attribute sigma_Ixx : Real = 0.37074144170588635;
                                attribute Iyy : Real = 0.7055550495293766;
                                attribute sigma_Iyy : Real = 0.3723953238821935;
                                attribute Izz : Real = 0.6513105721243234;
                                attribute sigma_Izz : Real = 0.37017423652493897;
                                attribute Ixy : Real = -0.004701371570255442;
                                attribute sigma_Ixy : Real = 0.02351283871158888;
                                attribute Ixz : Real = -0.052928650254065304;
                                attribute sigma_Ixz : Real = 0.022566176940390956;
                                attribute Iyz : Real = 0.020656573819666957;
                                attribute sigma_Iyz : Real = 0.02209918015384651;
                            }
                            part <'C.1.1.2.1.3.3.3'> 'Part 121' {
                                attribute POIconv : String = "-";
                                attribute Ipoint : Boolean = false;
                                attribute mass : Real = 0.5431820213005413;
                                attribute sigma_mass : Real = 0.28909372274994966;
                                attribute Cx : Real = 26.398755982518196;
                                attribute sigma_Cx : Real = 28.721044428837228;
                                attribute Cy : Real = 91.28393102437258;
                                attribute sigma_Cy : Real = 28.23690002309109;
                                attribute Cz : Real = 83.53133285418153;
                                attribute sigma_Cz : Real = 29.057750463592832;
                                attribute Ixx : Real = 0.8120921944048798;
                                attribute sigma_Ixx : Real = 0.37074144170588635;
                                attribute Iyy : Real = 0.7307946289592773;
                                attribute sigma_Iyy : Real = 0.3723953238821935;
                                attribute Izz : Real = 0.7262356898771161;
                                attribute sigma_Izz : Real = 0.37017423652493897;
                                attribute Ixy : Real = -0.018511053224840215;
                                attribute sigma_Ixy : Real = 0.02351283871158888;
                                attribute Ixz : Real = 0.01200263532458008;
                                attribute sigma_Ixz : Real = 0.022566176940390956;
                                attribute Iyz : Real = -0.006901353997963102;
                                attribute sigma_Iyz : Real = 0.02209918015384651;
                            }
                        }
                        part <'C.1.1.2.1.3.4'> 'Subassembly 35' {
                            attribute POIconv : String = "-";
                            attribute Ipoint : Boolean = false;
                            attribute mass : Real = 1.1314012984172441;
                            attribute sigma_mass : Real = 0.40884026350990615;
                            attribute Cx : Real = -21.640709361941397;
                            attribute sigma_Cx : Real = 25.21059993728186;
                            attribute Cy : Real = -50.94334776738303;
                            attribute sigma_Cy : Real = 45.864454651104005;
                            attribute Cz : Real = -48.02492848266029;
                            attribute sigma_Cz : Real = 44.36757137706029;
                            attribute Ixx : Real = 8766.616362255403;
                            attribute sigma_Ixx : Real = 12600.083352889742;
                            attribute Iyy : Real = 4204.3549542002165;
                            attribute sigma_Iyy : Real = 6224.36204862821;
                            attribute Izz : Real = 4724.793815785539;
                            attribute sigma_Izz : Real = 6934.827925508937;
                            attribute Ixy : Real = -611.2401171894594;
                            attribute sigma_Ixy : Real = 1371.867583816278;
                            attribute Ixz : Real = -575.8724568224042;
                            attribute sigma_Ixz : Real = 1293.9342055003924;
                            attribute Iyz : Real = -4374.805331990363;
                            attribute sigma_Iyz : Real = 6290.093547703817;
                            part <'C.1.1.2.1.3.4.1'> 'Part 122' {
                                attribute POIconv : String = "+";
                                attribute Ipoint : Boolean = false;
                                attribute mass : Real = 0.1748610637704842;
                                attribute sigma_mass : Real = 0.28909372274994966;
                                attribute Cx : Real = -1.9168300554156303;
                                attribute sigma_Cx : Real = 28.721044428837228;
                                attribute Cy : Real = 98.88286697678268;
                                attribute sigma_Cy : Real = 28.23690002309109;
                                attribute Cz : Real = 93.15288970246911;
                                attribute sigma_Cz : Real = 29.057750463592832;
                                attribute Ixx : Real = 0.2098309765660314;
                                attribute sigma_Ixx : Real = 0.37074144170588635;
                                attribute Iyy : Real = 0.20114654134717325;
                                attribute sigma_Iyy : Real = 0.3723953238821935;
                                attribute Izz : Real = 0.197896232797806;
                                attribute sigma_Izz : Real = 0.37017423652493897;
                                attribute Ixy : Real = -0.0029645845771882505;
                                attribute sigma_Ixy : Real = 0.02351283871158888;
                                attribute Ixz : Real = -0.0036342567532666125;
                                attribute sigma_Ixz : Real = 0.022566176940390956;
                                attribute Iyz : Real = 0.015297162709185689;
                                attribute sigma_Iyz : Real = 0.02209918015384651;
                            }
                            part <'C.1.1.2.1.3.4.2'> 'Part 123' {
                                attribute POIconv : String = "+";
                                attribute Ipoint : Boolean = false;
                                attribute mass : Real = 0.95654023464676;
                                attribute sigma_mass : Real = 0.28909372274994966;
                                attribute Cx : Real = -25.246348092332482;
                                attribute sigma_Cx : Real = 28.721044428837228;
                                attribute Cy : Real = -78.3324426971376;
                                attribute sigma_Cy : Real = 28.23690002309109;
                                attribute Cz : Real = -73.83304671384394;
                                attribute sigma_Cz : Real = 29.057750463592832;
                                attribute Ixx : Real = 1.2842653344273014;
                                attribute sigma_Ixx : Real = 0.37074144170588635;
                                attribute Iyy : Real = 1.3928357564714327;
                                attribute sigma_Iyy : Real = 0.3723953238821935;
                                attribute Izz : Real = 1.3104788193380403;
                                attribute sigma_Izz : Real = 0.37017423652493897;
                                attribute Ixy : Real = 0.03837439862975049;
                                attribute sigma_Ixy : Real = 0.02351283871158888;
                                attribute Ixz : Real = -0.04813686107031087;
                                attribute sigma_Ixz : Real = 0.022566176940390956;
                                attribute Iyz : Real = -0.03632213506196913;
                                attribute sigma_Iyz : Real = 0.02209918015384651;
                            }
                        }
                    }
                    part <'C.1.1.2.1.4'> 'Assembly 10' {
                        attribute POIconv : String = "-";
                        attribute Ipoint : Boolean = false;
                        attribute mass : Real = 3.2158284589499235;
                        attribute sigma_mass : Real = 0.8176805270198123;
                        attribute Cx : Real = -14.988946121972784;
                        attribute sigma_Cx : Real = 20.355542099891167;
                        attribute Cy : Real = -49.40569323877145;
                        attribute sigma_Cy : Real = 20.29056291137664;
                        attribute Cz : Real = 14.04044060506893;
                        attribute sigma_Cz : Real = 20.5274844643313;
                        attribute Ixx : Real = 21066.71489019577;
                        attribute sigma_Ixx : Real = 9167.976372226178;
                        attribute Iyy : Real = 21006.8159760326;
                        attribute sigma_Iyy : Real = 9628.146821891425;
                        attribute Izz : Real = 21622.8021604335;
                        attribute sigma_Izz : Real = 9678.240577056215;
                        attribute Ixy : Real = -4600.871269204705;
                        attribute sigma_Ixy : Real = 4378.590881273634;
                        attribute Ixz : Real = -7434.329197668341;
                        attribute sigma_Ixz : Real = 4639.570968278899;
                        attribute Iyz : Real = 749.2605621419307;
                        attribute sigma_Iyz : Real = 4590.08979405475;
                        part <'C.1.1.2.1.4.1'> 'Subassembly 36' {
                            attribute POIconv : String = "-";
                            attribute Ipoint : Boolean = false;
                            attribute mass : Real = 1.1858441858624573;
                            attribute sigma_mass : Real = 0.5007250159521434;
                            attribute Cx : Real = -41.27032250926029;
                            attribute sigma_Cx : Real = 35.756286634107134;
                            attribute Cy : Real = -30.962317966441137;
                            attribute sigma_Cy : Real = 34.20101505273474;
                            attribute Cz : Real = -37.609584907195504;
                            attribute sigma_Cz : Real = 23.721220430144246;
                            attribute Ixx : Real = 7126.066631023257;
                            attribute sigma_Ixx : Real = 4488.777118966491;
                            attribute Iyy : Real = 5895.751153059144;
                            attribute sigma_Iyy : Real = 5533.974546609789;
                            attribute Izz : Real = 10354.932087120611;
                            attribute sigma_Izz : Real = 6689.564786812297;
                            attribute Ixy : Real = -3264.8917885635465;
                            attribute sigma_Ixy : Real = 2673.582550509902;
                            attribute Ixz : Real = -2252.2252001513025;
                            attribute sigma_Ixz : Real = 2202.4987870103023;
                            attribute Iyz : Real = -2484.9890858998206;
                            attribute sigma_Iyz : Real = 1962.070078047627;
                            part <'C.1.1.2.1.4.1.1'> 'Part 124' {
                                attribute POIconv : String = "-";
                                attribute Ipoint : Boolean = false;
                                attribute mass : Real = 0.23447460628300906;
                                attribute sigma_mass : Real = 0.28909372274994966;
                                attribute Cx : Real = 77.25934558548033;
                                attribute sigma_Cx : Real = 28.721044428837228;
                                attribute Cy : Real = 19.524044264107943;
                                attribute sigma_Cy : Real = 28.23690002309109;
                                attribute Cz : Real = 12.23496524617076;
                                attribute sigma_Cz : Real = 29.057750463592832;
                                attribute Ixx : Real = 0.33760943682442096;
                                attribute sigma_Ixx : Real = 0.37074144170588635;
                                attribute Iyy : Real = 0.3257122136181345;
                                attribute sigma_Iyy : Real = 0.3723953238821935;
                                attribute Izz : Real = 0.3508556112357001;
                                attribute sigma_Izz : Real = 0.37017423652493897;
                                attribute Ixy : Real = 0.018267723266434745;
                                attribute sigma_Ixy : Real = 0.02351283871158888;
                                attribute Ixz : Real = -0.0025852143004990906;
                                attribute sigma_Ixz : Real = 0.022566176940390956;
                                attribute Iyz : Real = 0.003166833910781492;
                                attribute sigma_Iyz : Real = 0.02209918015384651;
                            }
                            part <'C.1.1.2.1.4.1.2'> 'Part 125' {
                                attribute POIconv : String = "+";
                                attribute Ipoint : Boolean = false;
                                attribute mass : Real = 0.6192206798119004;
                                attribute sigma_mass : Real = 0.28909372274994966;
                                attribute Cx : Real = -86.5062297321856;
                                attribute sigma_Cx : Real = 28.721044428837228;
                                attribute Cy : Real = -96.74830525182188;
                                attribute sigma_Cy : Real = 28.23690002309109;
                                attribute Cz : Real = -68.38606670498848;
                                attribute sigma_Cz : Real = 29.057750463592832;
                                attribute Ixx : Real = 0.9871806816772882;
                                attribute sigma_Ixx : Real = 0.37074144170588635;
                                attribute Iyy : Real = 0.9941350619349281;
                                attribute sigma_Iyy : Real = 0.3723953238821935;
                                attribute Izz : Real = 0.9835767364973861;
                                attribute sigma_Izz : Real = 0.37017423652493897;
                                attribute Ixy : Real = 0.006783720605849883;
                                attribute sigma_Ixy : Real = 0.02351283871158888;
                                attribute Ixz : Real = 0.006824846766921822;
                                attribute sigma_Ixz : Real = 0.022566176940390956;
                                attribute Iyz : Real = -0.010056441023861532;
                                attribute sigma_Iyz : Real = 0.02209918015384651;
                            }
                            part <'C.1.1.2.1.4.1.3'> 'Part 126' {
                                attribute POIconv : String = "-";
                                attribute Ipoint : Boolean = false;
                                attribute mass : Real = 0.33214889976754786;
                                attribute sigma_mass : Real = 0.28909372274994966;
                                attribute Cx : Real = -40.611545788124204;
                                attribute sigma_Cx : Real = 28.721044428837228;
                                attribute Cy : Real = 56.04165489785373;
                                attribute sigma_Cy : Real = 28.23690002309109;
                                attribute Cz : Real = -15.420281514525414;
                                attribute sigma_Cz : Real = 29.057750463592832;
                                attribute Ixx : Real = 0.3638069389480099;
                                attribute sigma_Ixx : Real = 0.37074144170588635;
                                attribute Iyy : Real = 0.3772242942786602;
                                attribute sigma_Iyy : Real = 0.3723953238821935;
                                attribute Izz : Real = 0.37874346984864543;
                                attribute sigma_Izz : Real = 0.37017423652493897;
                                attribute Ixy : Real = -0.006927884021614925;
                                attribute sigma_Ixy : Real = 0.02351283871158888;
                                attribute Ixz : Real = 0.009380585960091711;
                                attribute sigma_Ixz : Real = 0.022566176940390956;
                                attribute Iyz : Real = -0.009317533936621646;
                                attribute sigma_Iyz : Real = 0.02209918015384651;
                            }
                        }
                        part <'C.1.1.2.1.4.2'> 'Subassembly 37' {
                            attribute POIconv : String = "-";
                            attribute Ipoint : Boolean = false;
                            attribute mass : Real = 1.8650571135808716;
                            attribute sigma_mass : Real = 0.5007250159521434;
                            attribute Cx : Real = 6.417740151970341;
                            attribute sigma_Cx : Real = 21.44270571597451;
                            attribute Cy : Real = -67.75402781944764;
                            attribute sigma_Cy : Real = 20.596213935133008;
                            attribute Cz : Real = 54.30968193137387;
                            attribute sigma_Cz : Real = 19.198932565872713;
                            attribute Ixx : Real = 4624.598149056641;
                            attribute sigma_Ixx : Real = 3371.3850810992126;
                            attribute Iyy : Real = 5581.849814093202;
                            attribute sigma_Iyy : Real = 3840.3659568689427;
                            attribute Izz : Real = 7133.846002694636;
                            attribute sigma_Izz : Real = 4710.35891331623;
                            attribute Ixy : Real = -3287.0124914483613;
                            attribute sigma_Ixy : Real = 2344.628660976575;
                            attribute Ixz : Real = -1240.0000673867075;
                            attribute sigma_Ixz : Real = 1780.9449646511723;
                            attribute Iyz : Real = -314.8605269061391;
                            attribute sigma_Iyz : Real = 1542.410948311979;
                            part <'C.1.1.2.1.4.2.1'> 'Part 127' {
                                attribute POIconv : String = "-";
                                attribute Ipoint : Boolean = false;
                                attribute mass : Real = 0.4957759951716289;
                                attribute sigma_mass : Real = 0.28909372274994966;
                                attribute Cx : Real = 18.431154219433665;
                                attribute sigma_Cx : Real = 28.721044428837228;
                                attribute Cy : Real = -82.50533048994839;
                                attribute sigma_Cy : Real = 28.23690002309109;
                                attribute Cz : Real = 98.84459828026593;
                                attribute sigma_Cz : Real = 29.057750463592832;
                                attribute Ixx : Real = 0.5286776004907918;
                                attribute sigma_Ixx : Real = 0.37074144170588635;
                                attribute Iyy : Real = 0.5708044860358918;
                                attribute sigma_Iyy : Real = 0.3723953238821935;
                                attribute Izz : Real = 0.52383640923802;
                                attribute sigma_Izz : Real = 0.37017423652493897;
                                attribute Ixy : Real = 0.017712193363592185;
                                attribute sigma_Ixy : Real = 0.02351283871158888;
                                attribute Ixz : Real = -0.0035164365329158434;
                                attribute sigma_Ixz : Real = 0.022566176940390956;
                                attribute Iyz : Real = -0.007319028275059267;
                                attribute sigma_Iyz : Real = 0.02209918015384651;
                            }
                            part <'C.1.1.2.1.4.2.2'> 'Part 128' {
                                attribute POIconv : String = "-";
                                attribute Ipoint : Boolean = false;
                                attribute mass : Real = 0.8807608322163578;
                                attribute sigma_mass : Real = 0.28909372274994966;
                                attribute Cx : Real = -37.91659162379801;
                                attribute sigma_Cx : Real = 28.721044428837228;
                                attribute Cy : Real = -96.924460073933;
                                attribute sigma_Cy : Real = 28.23690002309109;
                                attribute Cz : Real = 29.28264937363565;
                                attribute sigma_Cz : Real = 29.057750463592832;
                                attribute Ixx : Real = 1.1063320662331158;
                                attribute sigma_Ixx : Real = 0.37074144170588635;
                                attribute Iyy : Real = 1.2682195369159506;
                                attribute sigma_Iyy : Real = 0.3723953238821935;
                                attribute Izz : Real = 1.049335223667783;
                                attribute sigma_Izz : Real = 0.37017423652493897;
                                attribute Ixy : Real = -0.08539073804645332;
                                attribute sigma_Ixy : Real = 0.02351283871158888;
                                attribute Ixz : Real = 0.0179739801162003;
                                attribute sigma_Ixz : Real = 0.022566176940390956;
                                attribute Iyz : Real = -0.003457029164869484;
                                attribute sigma_Iyz : Real = 0.02209918015384651;
                            }
                            part <'C.1.1.2.1.4.2.3'> 'Part 129' {
                                attribute POIconv : String = "-";
                                attribute Ipoint : Boolean = false;
                                attribute mass : Real = 0.4885202861928847;
                                attribute sigma_mass : Real = 0.28909372274994966;
                                attribute Cx : Real = 74.1569550242275;
                                attribute sigma_Cx : Real = 28.721044428837228;
                                attribute Cy : Real = -0.19180597737431526;
                                attribute sigma_Cy : Real = 28.23690002309109;
                                attribute Cz : Real = 54.23494102433324;
                                attribute sigma_Cz : Real = 29.057750463592832;
                                attribute Ixx : Real = 0.7329805623354415;
                                attribute sigma_Ixx : Real = 0.37074144170588635;
                                attribute Iyy : Real = 0.6990801407418776;
                                attribute sigma_Iyy : Real = 0.3723953238821935;
                                attribute Izz : Real = 0.6730097009794579;
                                attribute sigma_Izz : Real = 0.37017423652493897;
                                attribute Ixy : Real = 0.01009572963695184;
                                attribute sigma_Ixy : Real = 0.02351283871158888;
                                attribute Ixz : Real = 0.014573420691217233;
                                attribute sigma_Ixz : Real = 0.022566176940390956;
                                attribute Iyz : Real = -0.016796732980520805;
                                attribute sigma_Iyz : Real = 0.02209918015384651;
                            }
                        }
                        part <'C.1.1.2.1.4.3'> 'Subassembly 38' {
                            attribute POIconv : String = "-";
                            attribute Ipoint : Boolean = false;
                            attribute mass : Real = 0.16492715950659476;
                            attribute sigma_mass : Real = 0.40884026350990615;
                            attribute Cx : Real = -68.09769518603234;
                            attribute sigma_Cx : Real = 68.66476605357506;
                            attribute Cy : Real = 25.47416666196201;
                            attribute sigma_Cy : Real = 33.3967404714165;
                            attribute Cz : Real = -69.96969200265025;
                            attribute sigma_Cz : Real = 32.72363287704766;
                            attribute Ixx : Real = 8.125646962479921;
                            attribute sigma_Ixx : Real = 91.78572733185703;
                            attribute Iyy : Real = 38.389032734146774;
                            attribute sigma_Iyy : Real = 420.24164859213255;
                            attribute Izz : Real = 39.09716146119096;
                            attribute sigma_Izz : Real = 427.57026169233535;
                            attribute Ixy : Real = -12.196100941871396;
                            attribute sigma_Ixy : Real = 136.87291486503162;
                            attribute Ixz : Real = 11.189143659713034;
                            attribute sigma_Ixz : Real = 126.55269912995415;
                            attribute Iyz : Real = 3.930915985046254;
                            attribute sigma_Iyz : Real = 45.75799665395567;
                            part <'C.1.1.2.1.4.3.1'> 'Part 130' {
                                attribute POIconv : String = "+";
                                attribute Ipoint : Boolean = false;
                                attribute mass : Real = 0.14198284141719342;
                                attribute sigma_mass : Real = 0.28909372274994966;
                                attribute Cx : Real = -73.916393565014;
                                attribute sigma_Cx : Real = 28.721044428837228;
                                attribute Cy : Real = 23.420857964083552;
                                attribute sigma_Cy : Real = 28.23690002309109;
                                attribute Cz : Real = -68.08523307554424;
                                attribute sigma_Cz : Real = 29.057750463592832;
                                attribute Ixx : Real = 0.17459145689449226;
                                attribute sigma_Ixx : Real = 0.37074144170588635;
                                attribute Iyy : Real = 0.18512921711189126;
                                attribute sigma_Iyy : Real = 0.3723953238821935;
                                attribute Izz : Real = 0.2117745645151967;
                                attribute sigma_Izz : Real = 0.37017423652493897;
                                attribute Ixy : Real = -0.0007834183456654027;
                                attribute sigma_Ixy : Real = 0.02351283871158888;
                                attribute Ixz : Real = 0.002452268902502458;
                                attribute sigma_Ixz : Real = 0.022566176940390956;
                                attribute Iyz : Real = 0.01859493967813753;
                                attribute sigma_Iyz : Real = 0.02209918015384651;
                            }
                            part <'C.1.1.2.1.4.3.2'> 'Part 131' {
                                attribute POIconv : String = "-";
                                attribute Ipoint : Boolean = false;
                                attribute mass : Real = 0.02294431808940135;
                                attribute sigma_mass : Real = 0.28909372274994966;
                                attribute Cx : Real = -32.0907271001488;
                                attribute sigma_Cx : Real = 28.721044428837228;
                                attribute Cy : Real = 38.18034525029361;
                                attribute sigma_Cy : Real = 28.23690002309109;
                                attribute Cz : Real = -81.63100318051875;
                                attribute sigma_Cz : Real = 29.057750463592832;
                                attribute Ixx : Real = 0.023836702726453995;
                                attribute sigma_Ixx : Real = 0.37074144170588635;
                                attribute Iyy : Real = 0.025088736877533106;
                                attribute sigma_Iyy : Real = 0.3723953238821935;
                                attribute Izz : Real = 0.02798837960848096;
                                attribute sigma_Izz : Real = 0.37017423652493897;
                                attribute Ixy : Real = -0.0032552824928376786;
                                attribute sigma_Ixy : Real = 0.02351283871158888;
                                attribute Ixz : Real = 0.0006857683075510088;
                                attribute sigma_Ixz : Real = 0.022566176940390956;
                                attribute Iyz : Real = 0.0004502117066058381;
                                attribute sigma_Iyz : Real = 0.02209918015384651;
                            }
                        }
                    }
                    part <'C.1.1.2.1.5'> 'Assembly 11' {
                        attribute POIconv : String = "-";
                        attribute Ipoint : Boolean = false;
                        attribute mass : Real = 11.052525830938713;
                        attribute sigma_mass : Real = 1.3247938674382216;
                        attribute Cx : Real = -26.70180131328178;
                        attribute sigma_Cx : Real = 10.591612912799578;
                        attribute Cy : Real = -3.297984899161226;
                        attribute sigma_Cy : Real = 9.535587172123687;
                        attribute Cz : Real = 5.771178385922059;
                        attribute sigma_Cz : Real = 10.265664598294764;
                        attribute Ixx : Real = 61962.00239895747;
                        attribute sigma_Ixx : Real = 14754.520013088066;
                        attribute Iyy : Real = 68562.90344515508;
                        attribute sigma_Iyy : Real = 17008.218060271443;
                        attribute Izz : Real = 61028.26258218259;
                        attribute sigma_Izz : Real = 16060.108992097283;
                        attribute Ixy : Real = -15634.941035432897;
                        attribute sigma_Ixy : Real = 7400.439706993476;
                        attribute Ixz : Real = -3903.3828929858882;
                        attribute sigma_Ixz : Real = 7954.415527361973;
                        attribute Iyz : Real = -1163.5134650783702;
                        attribute sigma_Iyz : Real = 6975.990064159383;
                        part <'C.1.1.2.1.5.1'> 'Subassembly 39' {
                            attribute POIconv : String = "-";
                            attribute Ipoint : Boolean = false;
                            attribute mass : Real = 2.848190835721092;
                            attribute sigma_mass : Real = 0.6464332159373649;
                            attribute Cx : Real = -24.34399254437216;
                            attribute sigma_Cx : Real = 19.731456374564054;
                            attribute Cy : Real = 3.287728305288172;
                            attribute sigma_Cy : Real = 19.26603584956629;
                            attribute Cz : Real = 22.674906407993053;
                            attribute sigma_Cz : Real = 15.458570723112018;
                            attribute Ixx : Real = 10633.872822070707;
                            attribute sigma_Ixx : Real = 5520.412047873524;
                            attribute Iyy : Real = 14284.805355168144;
                            attribute sigma_Iyy : Real = 7322.318146710639;
                            attribute Izz : Real = 19967.70759803769;
                            attribute sigma_Izz : Real = 8820.953853436064;
                            attribute Ixy : Real = -5642.220845658072;
                            attribute sigma_Ixy : Real = 4010.8042470520977;
                            attribute Ixz : Real = -4496.405278975375;
                            attribute sigma_Ixz : Real = 3196.6160812913818;
                            attribute Iyz : Real = -2867.333548504591;
                            attribute sigma_Iyz : Real = 2439.3391654770635;
                            part <'C.1.1.2.1.5.1.1'> 'Part 132' {
                                attribute POIconv : String = "-";
                                attribute Ipoint : Boolean = false;
                                attribute mass : Real = 0.5447481498254929;
                                attribute sigma_mass : Real = 0.28909372274994966;
                                attribute Cx : Real = -20.864103361964226;
                                attribute sigma_Cx : Real = 28.721044428837228;
                                attribute Cy : Real = -81.62685362622142;
                                attribute sigma_Cy : Real = 28.23690002309109;
                                attribute Cz : Real = 17.97395357862115;
                                attribute sigma_Cz : Real = 29.057750463592832;
                                attribute Ixx : Real = 0.5130627845459527;
                                attribute sigma_Ixx : Real = 0.37074144170588635;
                                attribute Iyy : Real = 0.4968297851749982;
                                attribute sigma_Iyy : Real = 0.3723953238821935;
                                attribute Izz : Real = 0.5109684194588667;
                                attribute sigma_Izz : Real = 0.37017423652493897;
                                attribute Ixy : Real = 0.0036725636275820503;
                                attribute sigma_Ixy : Real = 0.02351283871158888;
                                attribute Ixz : Real = -0.006936378657597641;
                                attribute sigma_Ixz : Real = 0.022566176940390956;
                                attribute Iyz : Real = 0.01882163310990817;
                                attribute sigma_Iyz : Real = 0.02209918015384651;
                            }
                            part <'C.1.1.2.1.5.1.2'> 'Part 133' {
                                attribute POIconv : String = "-";
                                attribute Ipoint : Boolean = false;
                                attribute mass : Real = 0.8436234026858583;
                                attribute sigma_mass : Real = 0.28909372274994966;
                                attribute Cx : Real = -49.32384677231312;
                                attribute sigma_Cx : Real = 28.721044428837228;
                                attribute Cy : Real = 18.329235026612878;
                                attribute sigma_Cy : Real = 28.23690002309109;
                                attribute Cz : Real = 36.198614398017526;
                                attribute sigma_Cz : Real = 29.057750463592832;
                                attribute Ixx : Real = 1.38693099467527;
                                attribute sigma_Ixx : Real = 0.37074144170588635;
                                attribute Iyy : Real = 1.3063913980778492;
                                attribute sigma_Iyy : Real = 0.3723953238821935;
                                attribute Izz : Real = 1.3178038998415318;
                                attribute sigma_Izz : Real = 0.37017423652493897;
                                attribute Ixy : Real = -0.015861692037110478;
                                attribute sigma_Ixy : Real = 0.02351283871158888;
                                attribute Ixz : Real = 0.02828794807666528;
                                attribute sigma_Ixz : Real = 0.022566176940390956;
                                attribute Iyz : Real = -0.00411327201991964;
                                attribute sigma_Iyz : Real = 0.02209918015384651;
                            }
                            part <'C.1.1.2.1.5.1.3'> 'Part 134' {
                                attribute POIconv : String = "+";
                                attribute Ipoint : Boolean = false;
                                attribute mass : Real = 0.5824006713996641;
                                attribute sigma_mass : Real = 0.28909372274994966;
                                attribute Cx : Real = 93.24663882143795;
                                attribute sigma_Cx : Real = 28.721044428837228;
                                attribute Cy : Real = 76.3129263650626;
                                attribute sigma_Cy : Real = 28.23690002309109;
                                attribute Cz : Real = 61.39633618295193;
                                attribute sigma_Cz : Real = 29.057750463592832;
                                attribute Ixx : Real = 0.7129259852741276;
                                attribute sigma_Ixx : Real = 0.37074144170588635;
                                attribute Iyy : Real = 0.686126297392601;
                                attribute sigma_Iyy : Real = 0.3723953238821935;
                                attribute Izz : Real = 0.6654475053164781;
                                attribute sigma_Izz : Real = 0.37017423652493897;
                                attribute Ixy : Real = 0.010834347812575203;
                                attribute sigma_Ixy : Real = 0.02351283871158888;
                                attribute Ixz : Real = 0.03531242626553843;
                                attribute sigma_Ixz : Real = 0.022566176940390956;
                                attribute Iyz : Real = 0.0061909824000929;
                                attribute sigma_Iyz : Real = 0.02209918015384651;
                            }
                            part <'C.1.1.2.1.5.1.4'> 'Part 135' {
                                attribute POIconv : String = "+";
                                attribute Ipoint : Boolean = false;
                                attribute mass : Real = 0.12478426721296274;
                                attribute sigma_mass : Real = 0.28909372274994966;
                                attribute Cx : Real = -24.885624833405018;
                                attribute sigma_Cx : Real = 28.721044428837228;
                                attribute Cy : Real = 69.08309417776763;
                                attribute sigma_Cy : Real = 28.23690002309109;
                                attribute Cz : Real = 33.07829308323562;
                                attribute sigma_Cz : Real = 29.057750463592832;
                                attribute Ixx : Real = 0.16729162841915973;
                                attribute sigma_Ixx : Real = 0.37074144170588635;
                                attribute Iyy : Real = 0.1675720632074804;
                                attribute sigma_Iyy : Real = 0.3723953238821935;
                                attribute Izz : Real = 0.1788596220331902;
                                attribute sigma_Izz : Real = 0.37017423652493897;
                                attribute Ixy : Real = 0.0061222076255589685;
                                attribute sigma_Ixy : Real = 0.02351283871158888;
                                attribute Ixz : Real = -0.000639257326523658;
                                attribute sigma_Ixz : Real = 0.022566176940390956;
                                attribute Iyz : Real = 0.012940473403577082;
                                attribute sigma_Iyz : Real = 0.02209918015384651;
                            }
                            part <'C.1.1.2.1.5.1.5'> 'Part 136' {
                                attribute POIconv : String = "-";
                                attribute Ipoint : Boolean = false;
                                attribute mass : Real = 0.7526343445971142;
                                attribute sigma_mass : Real = 0.28909372274994966;
                                attribute Cx : Real = -89.76666345261037;
                                attribute sigma_Cx : Real = 28.721044428837228;
                                attribute Cy : Real = -19.528738548979163;
                                attribute sigma_Cy : Real = 28.23690002309109;
                                attribute Cz : Real = -20.769359869882464;
                                attribute sigma_Cz : Real = 29.057750463592832;
                                attribute Ixx : Real = 0.9786911379695393;
                                attribute sigma_Ixx : Real = 0.37074144170588635;
                                attribute Iyy : Real = 0.9700725852833165;
                                attribute sigma_Iyy : Real = 0.3723953238821935;
                                attribute Izz : Real = 0.9060240286801441;
                                attribute sigma_Izz : Real = 0.37017423652493897;
                                attribute Ixy : Real = 0.002023714339072712;
                                attribute sigma_Ixy : Real = 0.02351283871158888;
                                attribute Ixz : Real = -0.00039750999514207643;
                                attribute sigma_Ixz : Real = 0.022566176940390956;
                                attribute Iyz : Real = 0.00885074351613383;
                                attribute sigma_Iyz : Real = 0.02209918015384651;
                            }
                        }
                        part <'C.1.1.2.1.5.2'> 'Subassembly 40' {
                            attribute POIconv : String = "-";
                            attribute Ipoint : Boolean = false;
                            attribute mass : Real = 1.609108484207187;
                            attribute sigma_mass : Real = 0.5007250159521434;
                            attribute Cx : Real = -62.98658297489551;
                            attribute sigma_Cx : Real = 26.104472439896927;
                            attribute Cy : Real = -24.640488473890073;
                            attribute sigma_Cy : Real = 25.127817568318424;
                            attribute Cz : Real = -23.368309690162295;
                            attribute sigma_Cz : Real = 26.26616482604091;
                            attribute Ixx : Real = 10495.242378494046;
                            attribute sigma_Ixx : Real = 5871.342597480227;
                            attribute Iyy : Real = 8718.43080966913;
                            attribute sigma_Iyy : Real = 5611.993322405682;
                            attribute Izz : Real = 5657.265095658617;
                            attribute sigma_Izz : Real = 5112.489306299155;
                            attribute Ixy : Real = -775.1198878957305;
                            attribute sigma_Ixy : Real = 2473.9562496522976;
                            attribute Ixz : Real = -1961.7406127779523;
                            attribute sigma_Ixz : Real = 2428.946646072159;
                            attribute Iyz : Real = -4824.459043919755;
                            attribute sigma_Iyz : Real = 2822.2578020855567;
                            part <'C.1.1.2.1.5.2.1'> 'Part 137' {
                                attribute POIconv : String = "+";
                                attribute Ipoint : Boolean = false;
                                attribute mass : Real = 0.676165806948673;
                                attribute sigma_mass : Real = 0.28909372274994966;
                                attribute Cx : Real = -96.10035391524434;
                                attribute sigma_Cx : Real = 28.721044428837228;
                                attribute Cy : Real = -69.41496604122221;
                                attribute sigma_Cy : Real = 28.23690002309109;
                                attribute Cz : Real = -94.27793025970459;
                                attribute sigma_Cz : Real = 29.057750463592832;
                                attribute Ixx : Real = 0.8177669569200914;
                                attribute sigma_Ixx : Real = 0.37074144170588635;
                                attribute Iyy : Real = 0.7299320788650162;
                                attribute sigma_Iyy : Real = 0.3723953238821935;
                                attribute Izz : Real = 0.8097335357735644;
                                attribute sigma_Izz : Real = 0.37017423652493897;
                                attribute Ixy : Real = 0.01811276072234147;
                                attribute sigma_Ixy : Real = 0.02351283871158888;
                                attribute Ixz : Real = -0.05779361816424772;
                                attribute sigma_Ixz : Real = 0.022566176940390956;
                                attribute Iyz : Real = 0.04648571447315491;
                                attribute sigma_Iyz : Real = 0.02209918015384651;
                            }
                            part <'C.1.1.2.1.5.2.2'> 'Part 138' {
                                attribute POIconv : String = "-";
                                attribute Ipoint : Boolean = false;
                                attribute mass : Real = 0.8123143940349109;
                                attribute sigma_mass : Real = 0.28909372274994966;
                                attribute Cx : Real = -49.23978759907186;
                                attribute sigma_Cx : Real = 28.721044428837228;
                                attribute Cy : Real = 22.621416673064232;
                                attribute sigma_Cy : Real = 28.23690002309109;
                                attribute Cz : Real = 40.08059962652624;
                                attribute sigma_Cz : Real = 29.057750463592832;
                                attribute Ixx : Real = 1.002210221059507;
                                attribute sigma_Ixx : Real = 0.37074144170588635;
                                attribute Iyy : Real = 1.185394183821374;
                                attribute sigma_Iyy : Real = 0.3723953238821935;
                                attribute Izz : Real = 0.9463297037965218;
                                attribute sigma_Izz : Real = 0.37017423652493897;
                                attribute Ixy : Real = -0.022432198261390094;
                                attribute sigma_Ixy : Real = 0.02351283871158888;
                                attribute Ixz : Real = 0.034175143590491466;
                                attribute sigma_Ixz : Real = 0.022566176940390956;
                                attribute Iyz : Real = 0.08665344471318208;
                                attribute sigma_Iyz : Real = 0.02209918015384651;
                            }
                            part <'C.1.1.2.1.5.2.3'> 'Part 139' {
                                attribute POIconv : String = "-";
                                attribute Ipoint : Boolean = false;
                                attribute mass : Real = 0.12062828322360292;
                                attribute sigma_mass : Real = 0.28909372274994966;
                                attribute Cx : Real = 30.05693545565009;
                                attribute sigma_Cx : Real = 28.721044428837228;
                                attribute Cy : Real = -91.9261603616178;
                                attribute sigma_Cy : Real = 28.23690002309109;
                                attribute Cz : Real = -53.16067193634808;
                                attribute sigma_Cz : Real = 29.057750463592832;
                                attribute Ixx : Real = 0.15840495688468167;
                                attribute sigma_Ixx : Real = 0.37074144170588635;
                                attribute Iyy : Real = 0.15415726107422356;
                                attribute sigma_Iyy : Real = 0.3723953238821935;
                                attribute Izz : Real = 0.1506746933151752;
                                attribute sigma_Izz : Real = 0.37017423652493897;
                                attribute Ixy : Real = 0.006711086624961781;
                                attribute sigma_Ixy : Real = 0.02351283871158888;
                                attribute Ixz : Real = -0.0015860072164172753;
                                attribute sigma_Ixz : Real = 0.022566176940390956;
                                attribute Iyz : Real = -0.0007317874406657901;
                                attribute sigma_Iyz : Real = 0.02209918015384651;
                            }
                        }
                        part <'C.1.1.2.1.5.3'> 'Subassembly 41' {
                            attribute POIconv : String = "-";
                            attribute Ipoint : Boolean = false;
                            attribute mass : Real = 0.964943844099529;
                            attribute sigma_mass : Real = 0.5007250159521434;
                            attribute Cx : Real = -69.15055481234776;
                            attribute sigma_Cx : Real = 30.892100502755667;
                            attribute Cy : Real = 10.672727360084073;
                            attribute sigma_Cy : Real = 30.990423744988586;
                            attribute Cz : Real = -65.84365203416877;
                            attribute sigma_Cz : Real = 27.62825876107644;
                            attribute Ixx : Real = 2577.397037716498;
                            attribute sigma_Ixx : Real = 2722.2077061023538;
                            attribute Iyy : Real = 2511.398231015163;
                            attribute sigma_Iyy : Real = 2674.834823997744;
                            attribute Izz : Real = 2056.9184670658847;
                            attribute sigma_Izz : Real = 3909.749615471609;
                            attribute Ixy : Real = -1006.618649041541;
                            attribute sigma_Ixy : Real = 1954.578154789646;
                            attribute Ixz : Real = 75.46078384018838;
                            attribute sigma_Ixz : Real = 830.4833806470791;
                            attribute Iyz : Real = -176.53835805840828;
                            attribute sigma_Iyz : Real = 815.4924578682949;
                            part <'C.1.1.2.1.5.3.1'> 'Part 140' {
                                attribute POIconv : String = "-";
                                attribute Ipoint : Boolean = false;
                                attribute mass : Real = 0.28459705574368127;
                                attribute sigma_mass : Real = 0.28909372274994966;
                                attribute Cx : Real = -83.23765029199421;
                                attribute sigma_Cx : Real = 28.721044428837228;
                                attribute Cy : Real = 6.243040785193443;
                                attribute sigma_Cy : Real = 28.23690002309109;
                                attribute Cz : Real = -6.131899217143655;
                                attribute sigma_Cz : Real = 29.057750463592832;
                                attribute Ixx : Real = 0.3174809909585794;
                                attribute sigma_Ixx : Real = 0.37074144170588635;
                                attribute Iyy : Real = 0.36332572703877697;
                                attribute sigma_Iyy : Real = 0.3723953238821935;
                                attribute Izz : Real = 0.36544653798551574;
                                attribute sigma_Izz : Real = 0.37017423652493897;
                                attribute Ixy : Real = -0.021020534893919716;
                                attribute sigma_Ixy : Real = 0.02351283871158888;
                                attribute Ixz : Real = 0.0011902640754227955;
                                attribute sigma_Ixz : Real = 0.022566176940390956;
                                attribute Iyz : Real = 0.00030644695781537024;
                                attribute sigma_Iyz : Real = 0.02209918015384651;
                            }
                            part <'C.1.1.2.1.5.3.2'> 'Part 141' {
                                attribute POIconv : String = "+";
                                attribute Ipoint : Boolean = false;
                                attribute mass : Real = 0.5458731079851277;
                                attribute sigma_mass : Real = 0.28909372274994966;
                                attribute Cx : Real = -81.45713596604764;
                                attribute sigma_Cx : Real = 28.721044428837228;
                                attribute Cy : Real = -7.000693446025252;
                                attribute sigma_Cy : Real = 28.23690002309109;
                                attribute Cz : Real = -96.07520098797977;
                                attribute sigma_Cz : Real = 29.057750463592832;
                                attribute Ixx : Real = 0.5347265581717263;
                                attribute sigma_Ixx : Real = 0.37074144170588635;
                                attribute Iyy : Real = 0.5734655753935646;
                                attribute sigma_Iyy : Real = 0.3723953238821935;
                                attribute Izz : Real = 0.5902595852370592;
                                attribute sigma_Izz : Real = 0.37017423652493897;
                                attribute Ixy : Real = -0.02793345944694969;
                                attribute sigma_Ixy : Real = 0.02351283871158888;
                                attribute Ixz : Real = 0.027203295076605523;
                                attribute sigma_Ixz : Real = 0.022566176940390956;
                                attribute Iyz : Real = 0.0036293523578296983;
                                attribute sigma_Iyz : Real = 0.02209918015384651;
                            }
                            part <'C.1.1.2.1.5.3.3'> 'Part 142' {
                                attribute POIconv : String = "-";
                                attribute Ipoint : Boolean = false;
                                attribute mass : Real = 0.1344736803707201;
                                attribute sigma_mass : Real = 0.28909372274994966;
                                attribute Cx : Real = 10.61953529715538;
                                attribute sigma_Cx : Real = 28.721044428837228;
                                attribute Cy : Real = 91.78987140767276;
                                attribute sigma_Cy : Real = 28.23690002309109;
                                attribute Cz : Real = -69.49640740640461;
                                attribute sigma_Cz : Real = 29.057750463592832;
                                attribute Ixx : Real = 0.1994522258616676;
                                attribute sigma_Ixx : Real = 0.37074144170588635;
                                attribute Iyy : Real = 0.1967005418142774;
                                attribute sigma_Iyy : Real = 0.3723953238821935;
                                attribute Izz : Real = 0.1966584182224298;
                                attribute sigma_Izz : Real = 0.37017423652493897;
                                attribute Ixy : Real = 0.0025516026135663145;
                                attribute sigma_Ixy : Real = 0.02351283871158888;
                                attribute Ixz : Real = 0.0011009687983479684;
                                attribute sigma_Ixz : Real = 0.022566176940390956;
                                attribute Iyz : Real = 0.0003185896142718945;
                                attribute sigma_Iyz : Real = 0.02209918015384651;
                            }
                        }
                        part <'C.1.1.2.1.5.4'> 'Subassembly 42' {
                            attribute POIconv : String = "-";
                            attribute Ipoint : Boolean = false;
                            attribute mass : Real = 3.222242954750778;
                            attribute sigma_mass : Real = 0.6464332159373649;
                            attribute Cx : Real = 7.028207089787453;
                            attribute sigma_Cx : Real = 18.236425164117858;
                            attribute Cy : Real = 8.996883292892319;
                            attribute sigma_Cy : Real = 17.053533451349757;
                            attribute Cz : Real = -12.24991348682863;
                            attribute sigma_Cz : Real = 17.48967024229969;
                            attribute Ixx : Real = 12767.368472023538;
                            attribute sigma_Ixx : Real = 6684.555683724957;
                            attribute Iyy : Real = 13297.588849603835;
                            attribute sigma_Iyy : Real = 7113.578737829268;
                            attribute Izz : Real = 15617.550134587227;
                            attribute sigma_Izz : Real = 7430.13509966566;
                            attribute Ixy : Real = -5055.232168805023;
                            attribute sigma_Ixy : Real = 3433.7792672953083;
                            attribute Ixz : Real = 1633.3044270641578;
                            attribute sigma_Ixz : Real = 3268.295688229378;
                            attribute Iyz : Real = 5400.260272371043;
                            attribute sigma_Iyz : Real = 3315.8475538101493;
                            part <'C.1.1.2.1.5.4.1'> 'Part 143' {
                                attribute POIconv : String = "+";
                                attribute Ipoint : Boolean = false;
                                attribute mass : Real = 0.1215258111958392;
                                attribute sigma_mass : Real = 0.28909372274994966;
                                attribute Cx : Real = 97.89935210719705;
                                attribute sigma_Cx : Real = 28.721044428837228;
                                attribute Cy : Real = -14.352465933188796;
                                attribute sigma_Cy : Real = 28.23690002309109;
                                attribute Cz : Real = 42.845899472013116;
                                attribute sigma_Cz : Real = 29.057750463592832;
                                attribute Ixx : Real = 0.17301150346399724;
                                attribute sigma_Ixx : Real = 0.37074144170588635;
                                attribute Iyy : Real = 0.15823515097252172;
                                attribute sigma_Iyy : Real = 0.3723953238821935;
                                attribute Izz : Real = 0.17622942245687723;
                                attribute sigma_Izz : Real = 0.37017423652493897;
                                attribute Ixy : Real = 0.006047759901812523;
                                attribute sigma_Ixy : Real = 0.02351283871158888;
                                attribute Ixz : Real = 0.008413166574839984;
                                attribute sigma_Ixz : Real = 0.022566176940390956;
                                attribute Iyz : Real = -0.0004807438877178667;
                                attribute sigma_Iyz : Real = 0.02209918015384651;
                            }
                            part <'C.1.1.2.1.5.4.2'> 'Part 144' {
                                attribute POIconv : String = "+";
                                attribute Ipoint : Boolean = false;
                                attribute mass : Real = 0.46269242569990454;
                                attribute sigma_mass : Real = 0.28909372274994966;
                                attribute Cx : Real = -2.2517085541039705;
                                attribute sigma_Cx : Real = 28.721044428837228;
                                attribute Cy : Real = 83.73118420131505;
                                attribute sigma_Cy : Real = 28.23690002309109;
                                attribute Cz : Real = -98.01948610693216;
                                attribute sigma_Cz : Real = 29.057750463592832;
                                attribute Ixx : Real = 0.6048215949955417;
                                attribute sigma_Ixx : Real = 0.37074144170588635;
                                attribute Iyy : Real = 0.7201245139841406;
                                attribute sigma_Iyy : Real = 0.3723953238821935;
                                attribute Izz : Real = 0.5765976279600344;
                                attribute sigma_Izz : Real = 0.37017423652493897;
                                attribute Ixy : Real = -0.06448649363053159;
                                attribute sigma_Ixy : Real = 0.02351283871158888;
                                attribute Ixz : Real = 0.007168666867494928;
                                attribute sigma_Ixz : Real = 0.022566176940390956;
                                attribute Iyz : Real = 0.0162296272098285;
                                attribute sigma_Iyz : Real = 0.02209918015384651;
                            }
                            part <'C.1.1.2.1.5.4.3'> 'Part 145' {
                                attribute POIconv : String = "+";
                                attribute Ipoint : Boolean = false;
                                attribute mass : Real = 0.9827399011156521;
                                attribute sigma_mass : Real = 0.28909372274994966;
                                attribute Cx : Real = 66.33293624036014;
                                attribute sigma_Cx : Real = 28.721044428837228;
                                attribute Cy : Real = 49.1757424082607;
                                attribute sigma_Cy : Real = 28.23690002309109;
                                attribute Cz : Real = -18.6045931186527;
                                attribute sigma_Cz : Real = 29.057750463592832;
                                attribute Ixx : Real = 1.3108250003809785;
                                attribute sigma_Ixx : Real = 0.37074144170588635;
                                attribute Iyy : Real = 1.2985415627352457;
                                attribute sigma_Iyy : Real = 0.3723953238821935;
                                attribute Izz : Real = 1.0950475129815074;
                                attribute sigma_Izz : Real = 0.37017423652493897;
                                attribute Ixy : Real = -0.04401540679121507;
                                attribute sigma_Ixy : Real = 0.02351283871158888;
                                attribute Ixz : Real = -0.07174685322028279;
                                attribute sigma_Ixz : Real = 0.022566176940390956;
                                attribute Iyz : Real = 0.05532002807269491;
                                attribute sigma_Iyz : Real = 0.02209918015384651;
                            }
                            part <'C.1.1.2.1.5.4.4'> 'Part 146' {
                                attribute POIconv : String = "-";
                                attribute Ipoint : Boolean = false;
                                attribute mass : Real = 0.8762005920649972;
                                attribute sigma_mass : Real = 0.28909372274994966;
                                attribute Cx : Real = -55.63594405539334;
                                attribute sigma_Cx : Real = 28.721044428837228;
                                attribute Cy : Real = -45.388418808579445;
                                attribute sigma_Cy : Real = 28.23690002309109;
                                attribute Cz : Real = 27.493249252438545;
                                attribute sigma_Cz : Real = 29.057750463592832;
                                attribute Ixx : Real = 1.17859494960956;
                                attribute sigma_Ixx : Real = 0.37074144170588635;
                                attribute Iyy : Real = 1.1898543637982602;
                                attribute sigma_Iyy : Real = 0.3723953238821935;
                                attribute Izz : Real = 0.9244969492842944;
                                attribute sigma_Izz : Real = 0.37017423652493897;
                                attribute Ixy : Real = -0.004802690682821149;
                                attribute sigma_Ixy : Real = 0.02351283871158888;
                                attribute Ixz : Real = 0.033619872224326;
                                attribute sigma_Ixz : Real = 0.022566176940390956;
                                attribute Iyz : Real = -0.023429283271321405;
                                attribute sigma_Iyz : Real = 0.02209918015384651;
                            }
                            part <'C.1.1.2.1.5.4.5'> 'Part 147' {
                                attribute POIconv : String = "+";
                                attribute Ipoint : Boolean = false;
                                attribute mass : Real = 0.7790842246743851;
                                attribute sigma_mass : Real = 0.28909372274994966;
                                attribute Cx : Real = -5.9667938854545355;
                                attribute sigma_Cx : Real = 28.721044428837228;
                                attribute Cy : Real = -21.262207766994834;
                                attribute sigma_Cy : Real = 28.23690002309109;
                                attribute Cz : Real = -6.58764666877687;
                                attribute sigma_Cz : Real = 29.057750463592832;
                                attribute Ixx : Real = 0.9049289085296087;
                                attribute sigma_Ixx : Real = 0.37074144170588635;
                                attribute Iyy : Real = 1.0021354911993983;
                                attribute sigma_Iyy : Real = 0.3723953238821935;
                                attribute Izz : Real = 0.9534793197752769;
                                attribute sigma_Izz : Real = 0.37017423652493897;
                                attribute Ixy : Real = -0.046207166276300594;
                                attribute sigma_Ixy : Real = 0.02351283871158888;
                                attribute Ixz : Real = -0.08452388087665226;
                                attribute sigma_Ixz : Real = 0.022566176940390956;
                                attribute Iyz : Real = 0.06762880194057005;
                                attribute sigma_Iyz : Real = 0.02209918015384651;
                            }
                        }
                        part <'C.1.1.2.1.5.5'> 'Subassembly 43' {
                            attribute POIconv : String = "-";
                            attribute Ipoint : Boolean = false;
                            attribute mass : Real = 2.4080397121601274;
                            attribute sigma_mass : Real = 0.6464332159373649;
                            attribute Cx : Real = -33.369032667258665;
                            attribute sigma_Cx : Real = 23.349701713883835;
                            attribute Cy : Real = -18.876203743944878;
                            attribute sigma_Cy : Real = 19.486701130261665;
                            attribute Cz : Real = 58.061088595803916;
                            attribute sigma_Cz : Real = 20.19719046429248;
                            attribute Ixx : Real = 8612.194947446987;
                            attribute sigma_Ixx : Real = 5315.630762633261;
                            attribute Iyy : Real = 7344.924206269195;
                            attribute sigma_Iyy : Real = 6643.30007801089;
                            attribute Izz : Real = 7966.404599643123;
                            attribute sigma_Izz : Real = 6384.730102103138;
                            attribute Ixy : Real = -851.2750658061543;
                            attribute sigma_Ixy : Real = 2629.857759381251;
                            attribute Ixz : Real = 2796.0902994184107;
                            attribute sigma_Ixz : Real = 2982.3789097935874;
                            attribute Iyz : Real = -1018.5817830854243;
                            attribute sigma_Iyz : Real = 2551.742198776832;
                            part <'C.1.1.2.1.5.5.1'> 'Part 148' {
                                attribute POIconv : String = "+";
                                attribute Ipoint : Boolean = false;
                                attribute mass : Real = 0.5692882913739886;
                                attribute sigma_mass : Real = 0.28909372274994966;
                                attribute Cx : Real = -20.47927901148796;
                                attribute sigma_Cx : Real = 28.721044428837228;
                                attribute Cy : Real = -33.217661594972014;
                                attribute sigma_Cy : Real = 28.23690002309109;
                                attribute Cz : Real = 8.835651725530624;
                                attribute sigma_Cz : Real = 29.057750463592832;
                                attribute Ixx : Real = 0.8289207536336094;
                                attribute sigma_Ixx : Real = 0.37074144170588635;
                                attribute Iyy : Real = 0.7676713468109841;
                                attribute sigma_Iyy : Real = 0.3723953238821935;
                                attribute Izz : Real = 0.8125309094102543;
                                attribute sigma_Izz : Real = 0.37017423652493897;
                                attribute Ixy : Real = 0.0005303710081927901;
                                attribute sigma_Ixy : Real = 0.02351283871158888;
                                attribute Ixz : Real = 0.009410466876182872;
                                attribute sigma_Ixz : Real = 0.022566176940390956;
                                attribute Iyz : Real = 0.03702571528161821;
                                attribute sigma_Iyz : Real = 0.02209918015384651;
                            }
                            part <'C.1.1.2.1.5.5.2'> 'Part 149' {
                                attribute POIconv : String = "-";
                                attribute Ipoint : Boolean = false;
                                attribute mass : Real = 0.15183776629413478;
                                attribute sigma_mass : Real = 0.28909372274994966;
                                attribute Cx : Real = 59.654495073482394;
                                attribute sigma_Cx : Real = 28.721044428837228;
                                attribute Cy : Real = 49.16452025063336;
                                attribute sigma_Cy : Real = 28.23690002309109;
                                attribute Cz : Real = -8.414956089109182;
                                attribute sigma_Cz : Real = 29.057750463592832;
                                attribute Ixx : Real = 0.165857578928367;
                                attribute sigma_Ixx : Real = 0.37074144170588635;
                                attribute Iyy : Real = 0.17216267449049777;
                                attribute sigma_Iyy : Real = 0.3723953238821935;
                                attribute Izz : Real = 0.16724703343679237;
                                attribute sigma_Izz : Real = 0.37017423652493897;
                                attribute Ixy : Real = -0.00197736672212002;
                                attribute sigma_Ixy : Real = 0.02351283871158888;
                                attribute Ixz : Real = 0.0058231361076871374;
                                attribute sigma_Ixz : Real = 0.022566176940390956;
                                attribute Iyz : Real = 0.0018797894763217964;
                                attribute sigma_Iyz : Real = 0.02209918015384651;
                            }
                            part <'C.1.1.2.1.5.5.3'> 'Part 150' {
                                attribute POIconv : String = "-";
                                attribute Ipoint : Boolean = false;
                                attribute mass : Real = 0.10770200214954093;
                                attribute sigma_mass : Real = 0.28909372274994966;
                                attribute Cx : Real = 74.13820647634566;
                                attribute sigma_Cx : Real = 28.721044428837228;
                                attribute Cy : Real = -30.705874180421233;
                                attribute sigma_Cy : Real = 28.23690002309109;
                                attribute Cz : Real = 4.817138891667128;
                                attribute sigma_Cz : Real = 29.057750463592832;
                                attribute Ixx : Real = 0.1257832376891619;
                                attribute sigma_Ixx : Real = 0.37074144170588635;
                                attribute Iyy : Real = 0.10392978416812212;
                                attribute sigma_Iyy : Real = 0.3723953238821935;
                                attribute Izz : Real = 0.13898286923139067;
                                attribute sigma_Izz : Real = 0.37017423652493897;
                                attribute Ixy : Real = -0.003402490667846773;
                                attribute sigma_Ixy : Real = 0.02351283871158888;
                                attribute Ixz : Real = 0.0012548029673312864;
                                attribute sigma_Ixz : Real = 0.022566176940390956;
                                attribute Iyz : Real = -7.626846859778377e-06;
                                attribute sigma_Iyz : Real = 0.02209918015384651;
                            }
                            part <'C.1.1.2.1.5.5.4'> 'Part 151' {
                                attribute POIconv : String = "-";
                                attribute Ipoint : Boolean = false;
                                attribute mass : Real = 0.9767942562880926;
                                attribute sigma_mass : Real = 0.28909372274994966;
                                attribute Cx : Real = -53.13462843187153;
                                attribute sigma_Cx : Real = 28.721044428837228;
                                attribute Cy : Real = 18.97773602977395;
                                attribute sigma_Cy : Real = 28.23690002309109;
                                attribute Cz : Real = 98.64025609567761;
                                attribute sigma_Cz : Real = 29.057750463592832;
                                attribute Ixx : Real = 1.4181757016777667;
                                attribute sigma_Ixx : Real = 0.37074144170588635;
                                attribute Iyy : Real = 1.304351102648269;
                                attribute sigma_Iyy : Real = 0.3723953238821935;
                                attribute Izz : Real = 1.3441982823391134;
                                attribute sigma_Izz : Real = 0.37017423652493897;
                                attribute Ixy : Real = 0.027490749776944545;
                                attribute sigma_Ixy : Real = 0.02351283871158888;
                                attribute Ixz : Real = -0.07202193601768515;
                                attribute sigma_Ixz : Real = 0.022566176940390956;
                                attribute Iyz : Real = -0.03568700747841831;
                                attribute sigma_Iyz : Real = 0.02209918015384651;
                            }
                            part <'C.1.1.2.1.5.5.5'> 'Part 152' {
                                attribute POIconv : String = "-";
                                attribute Ipoint : Boolean = false;
                                attribute mass : Real = 0.6024173960543703;
                                attribute sigma_mass : Real = 0.28909372274994966;
                                attribute Cx : Real = -56.167668756097555;
                                attribute sigma_Cx : Real = 28.721044428837228;
                                attribute Cy : Real = -81.73653865233064;
                                attribute sigma_Cy : Real = 28.23690002309109;
                                attribute Cz : Real = 65.05627376027405;
                                attribute sigma_Cz : Real = 29.057750463592832;
                                attribute Ixx : Real = 0.7724924516764912;
                                attribute sigma_Ixx : Real = 0.37074144170588635;
                                attribute Iyy : Real = 0.8379278897473506;
                                attribute sigma_Iyy : Real = 0.3723953238821935;
                                attribute Izz : Real = 0.7378951037295188;
                                attribute sigma_Izz : Real = 0.37017423652493897;
                                attribute Ixy : Real = 0.032745472532650435;
                                attribute sigma_Ixy : Real = 0.02351283871158888;
                                attribute Ixz : Real = -0.021583451067481694;
                                attribute sigma_Ixz : Real = 0.022566176940390956;
                                attribute Iyz : Real = -0.01001994014271302;
                                attribute sigma_Iyz : Real = 0.02209918015384651;
                            }
                        }
                    }
                }
                part <'C.1.1.2.2'> 'Subsystem 4' {
                    attribute POIconv : String = "-";
                    attribute Ipoint : Boolean = false;
                    attribute mass : Real = 18.22715183463041;
                    attribute sigma_mass : Real = 1.7820933926902207;
                    attribute Cx : Real = -4.868964782135025;
                    attribute sigma_Cx : Real = 7.869633600524663;
                    attribute Cy : Real = -14.797855482181655;
                    attribute sigma_Cy : Real = 7.423458649925451;
                    attribute Cz : Real = 10.650613679203293;
                    attribute sigma_Cz : Real = 7.847228142105054;
                    attribute Ixx : Real = 102056.67474914368;
                    attribute sigma_Ixx : Real = 19136.771438154654;
                    attribute Iyy : Real = 100336.90119787194;
                    attribute sigma_Iyy : Real = 21176.009173007686;
                    attribute Izz : Real = 100312.44363424747;
                    attribute sigma_Izz : Real = 18881.39609356407;
                    attribute Ixy : Real = -6284.731227025179;
                    attribute sigma_Ixy : Real = 8959.90918348857;
                    attribute Ixz : Real = 1082.1755359313802;
                    attribute sigma_Ixz : Real = 9935.863826669936;
                    attribute Iyz : Real = -4106.363420615689;
                    attribute sigma_Iyz : Real = 8374.640674145685;
                    part <'C.1.1.2.2.1'> 'Assembly 12' {
                        attribute POIconv : String = "-";
                        attribute Ipoint : Boolean = false;
                        attribute mass : Real = 7.448503571380396;
                        attribute sigma_mass : Real = 1.1919639546010696;
                        attribute Cx : Real = 0.6379370148955974;
                        attribute sigma_Cx : Real = 12.488160200507439;
                        attribute Cy : Real = -1.3526413049182509;
                        attribute sigma_Cy : Real = 11.927614088683717;
                        attribute Cz : Real = 17.883163879580483;
                        attribute sigma_Cz : Real = 11.882802004780391;
                        attribute Ixx : Real = 46133.404346965915;
                        attribute sigma_Ixx : Real = 12276.208122949629;
                        attribute Iyy : Real = 46061.706376434486;
                        attribute sigma_Iyy : Real = 13012.844026496965;
                        attribute Izz : Real = 44259.58339041629;
                        attribute sigma_Izz : Real = 12821.847167468924;
                        attribute Ixy : Real = -3593.94263710787;
                        attribute sigma_Ixy : Real = 6208.323931518655;
                        attribute Ixz : Real = -3876.700127720149;
                        attribute sigma_Ixz : Real = 5828.28157433354;
                        attribute Iyz : Real = -4969.922546802821;
                        attribute sigma_Iyz : Real = 5324.487356352981;
                        part <'C.1.1.2.2.1.1'> 'Subassembly 44' {
                            attribute POIconv : String = "-";
                            attribute Ipoint : Boolean = false;
                            attribute mass : Real = 1.8700212576393969;
                            attribute sigma_mass : Real = 0.5781874454998993;
                            attribute Cx : Real = 19.042977724330875;
                            attribute sigma_Cx : Real = 20.15470312446756;
                            attribute Cy : Real = 14.85304684236597;
                            attribute sigma_Cy : Real = 24.111499644546317;
                            attribute Cz : Real = 29.791329751981607;
                            attribute sigma_Cz : Real = 18.407122272746985;
                            attribute Ixx : Real = 4580.802114057332;
                            attribute sigma_Ixx : Real = 3696.47071482153;
                            attribute Iyy : Real = 2527.903280838264;
                            attribute sigma_Iyy : Real = 2398.280520240986;
                            attribute Izz : Real = 4727.644159359155;
                            attribute sigma_Izz : Real = 4101.02831969691;
                            attribute Ixy : Real = -1162.8377714127914;
                            attribute sigma_Ixy : Real = 1921.1458882475536;
                            attribute Ixz : Real = 29.129574997786193;
                            attribute sigma_Ixz : Real = 1079.6554796153575;
                            attribute Iyz : Real = -1276.6138581311134;
                            attribute sigma_Iyz : Real = 1501.3082334120152;
                            part <'C.1.1.2.2.1.1.1'> 'Part 153' {
                                attribute POIconv : String = "-";
                                attribute Ipoint : Boolean = false;
                                attribute mass : Real = 0.855321117463056;
                                attribute sigma_mass : Real = 0.28909372274994966;
                                attribute Cx : Real = 4.351499816402793;
                                attribute sigma_Cx : Real = 28.721044428837228;
                                attribute Cy : Real = -21.02312254719436;
                                attribute sigma_Cy : Real = 28.23690002309109;
                                attribute Cz : Real = 6.591932894662023;
                                attribute sigma_Cz : Real = 29.057750463592832;
                                attribute Ixx : Real = 1.011890819436567;
                                attribute sigma_Ixx : Real = 0.37074144170588635;
                                attribute Iyy : Real = 1.1037062744217299;
                                attribute sigma_Iyy : Real = 0.3723953238821935;
                                attribute Izz : Real = 1.0899136050558529;
                                attribute sigma_Izz : Real = 0.37017423652493897;
                                attribute Ixy : Real = 0.03067171311202662;
                                attribute sigma_Ixy : Real = 0.02351283871158888;
                                attribute Ixz : Real = 0.02717709442391499;
                                attribute sigma_Ixz : Real = 0.022566176940390956;
                                attribute Iyz : Real = 0.01112129199620427;
                                attribute sigma_Iyz : Real = 0.02209918015384651;
                            }
                            part <'C.1.1.2.2.1.1.2'> 'Part 154' {
                                attribute POIconv : String = "+";
                                attribute Ipoint : Boolean = false;
                                attribute mass : Real = 0.08018356888229028;
                                attribute sigma_mass : Real = 0.28909372274994966;
                                attribute Cx : Real = 55.72422328405082;
                                attribute sigma_Cx : Real = 28.721044428837228;
                                attribute Cy : Real = -63.476700987666845;
                                attribute sigma_Cy : Real = 28.23690002309109;
                                attribute Cz : Real = 21.198144974187016;
                                attribute sigma_Cz : Real = 29.057750463592832;
                                attribute Ixx : Real = 0.09829198843261945;
                                attribute sigma_Ixx : Real = 0.37074144170588635;
                                attribute Iyy : Real = 0.09654515079313099;
                                attribute sigma_Iyy : Real = 0.3723953238821935;
                                attribute Izz : Real = 0.0966067730546954;
                                attribute sigma_Izz : Real = 0.37017423652493897;
                                attribute Ixy : Real = 0.0009798259919753046;
                                attribute sigma_Ixy : Real = 0.02351283871158888;
                                attribute Ixz : Real = 0.00024115810899414248;
                                attribute sigma_Ixz : Real = 0.022566176940390956;
                                attribute Iyz : Real = 7.37659657377281e-05;
                                attribute sigma_Iyz : Real = 0.02209918015384651;
                            }
                            part <'C.1.1.2.2.1.1.3'> 'Part 155' {
                                attribute POIconv : String = "+";
                                attribute Ipoint : Boolean = false;
                                attribute mass : Real = 0.3022511094980873;
                                attribute sigma_mass : Real = 0.28909372274994966;
                                attribute Cx : Real = 75.32320339232683;
                                attribute sigma_Cx : Real = 28.721044428837228;
                                attribute Cy : Real = 81.75194882787764;
                                attribute sigma_Cy : Real = 28.23690002309109;
                                attribute Cz : Real = 27.09015137515962;
                                attribute sigma_Cz : Real = 29.057750463592832;
                                attribute Ixx : Real = 0.33478560117777884;
                                attribute sigma_Ixx : Real = 0.37074144170588635;
                                attribute Iyy : Real = 0.3329397819957529;
                                attribute sigma_Iyy : Real = 0.3723953238821935;
                                attribute Izz : Real = 0.3270648789313383;
                                attribute sigma_Izz : Real = 0.37017423652493897;
                                attribute Ixy : Real = 0.01622390100726502;
                                attribute sigma_Ixy : Real = 0.02351283871158888;
                                attribute Ixz : Real = -0.015992914831490568;
                                attribute sigma_Ixz : Real = 0.022566176940390956;
                                attribute Iyz : Real = -0.01936987097497332;
                                attribute sigma_Iyz : Real = 0.02209918015384651;
                            }
                            part <'C.1.1.2.2.1.1.4'> 'Part 156' {
                                attribute POIconv : String = "+";
                                attribute Ipoint : Boolean = false;
                                attribute mass : Real = 0.6322654617959633;
                                attribute sigma_mass : Real = 0.28909372274994966;
                                attribute Cx : Real = 7.3610767256468534;
                                attribute sigma_Cx : Real = 28.721044428837228;
                                attribute Cy : Real = 41.338973538950086;
                                attribute sigma_Cy : Real = 28.23690002309109;
                                attribute Cz : Real = 63.55626191943884;
                                attribute sigma_Cz : Real = 29.057750463592832;
                                attribute Ixx : Real = 0.9551482203657099;
                                attribute sigma_Ixx : Real = 0.37074144170588635;
                                attribute Iyy : Real = 0.9194819283207218;
                                attribute sigma_Iyy : Real = 0.3723953238821935;
                                attribute Izz : Real = 0.8733881917209926;
                                attribute sigma_Izz : Real = 0.37017423652493897;
                                attribute Ixy : Real = 0.04531404116053733;
                                attribute sigma_Ixy : Real = 0.02351283871158888;
                                attribute Ixz : Real = 0.004886040855269214;
                                attribute sigma_Ixz : Real = 0.022566176940390956;
                                attribute Iyz : Real = -0.029527678514451056;
                                attribute sigma_Iyz : Real = 0.02209918015384651;
                            }
                        }
                        part <'C.1.1.2.2.1.2'> 'Subassembly 45' {
                            attribute POIconv : String = "-";
                            attribute Ipoint : Boolean = false;
                            attribute mass : Real = 2.091520572860958;
                            attribute sigma_mass : Real = 0.6464332159373649;
                            attribute Cx : Real = 5.2805352549354145;
                            attribute sigma_Cx : Real = 28.09852011809438;
                            attribute Cy : Real = -30.244744182931463;
                            attribute sigma_Cy : Real = 21.748951895013516;
                            attribute Cz : Real = 27.842401890770056;
                            attribute sigma_Cz : Real = 24.953402444148413;
                            attribute Ixx : Real = 16280.358228482952;
                            attribute sigma_Ixx : Real = 7574.064988563821;
                            attribute Iyy : Real = 22474.942155002846;
                            attribute sigma_Iyy : Real = 9561.488692511293;
                            attribute Izz : Real = 13831.676678087722;
                            attribute sigma_Izz : Real = 8057.959147747066;
                            attribute Ixy : Real = 4127.204708166517;
                            attribute sigma_Ixy : Real = 3792.784729286596;
                            attribute Ixz : Real = -3366.1510448047657;
                            attribute sigma_Ixz : Real = 4079.8741607652946;
                            attribute Iyz : Real = -3275.998559440784;
                            attribute sigma_Iyz : Real = 3185.236149886907;
                            part <'C.1.1.2.2.1.2.1'> 'Part 157' {
                                attribute POIconv : String = "+";
                                attribute Ipoint : Boolean = false;
                                attribute mass : Real = 0.6295002899167593;
                                attribute sigma_mass : Real = 0.28909372274994966;
                                attribute Cx : Real = -25.61848503537476;
                                attribute sigma_Cx : Real = 28.721044428837228;
                                attribute Cy : Real = -57.095806021243334;
                                attribute sigma_Cy : Real = 28.23690002309109;
                                attribute Cz : Real = -84.21276365406811;
                                attribute sigma_Cz : Real = 29.057750463592832;
                                attribute Ixx : Real = 0.6434653361214111;
                                attribute sigma_Ixx : Real = 0.37074144170588635;
                                attribute Iyy : Real = 0.6757857073193699;
                                attribute sigma_Iyy : Real = 0.3723953238821935;
                                attribute Izz : Real = 0.7229691868410921;
                                attribute sigma_Izz : Real = 0.37017423652493897;
                                attribute Ixy : Real = 0.006136141931393743;
                                attribute sigma_Ixy : Real = 0.02351283871158888;
                                attribute Ixz : Real = -0.0016994229790750132;
                                attribute sigma_Ixz : Real = 0.022566176940390956;
                                attribute Iyz : Real = -0.0033163206767449814;
                                attribute sigma_Iyz : Real = 0.02209918015384651;
                            }
                            part <'C.1.1.2.2.1.2.2'> 'Part 158' {
                                attribute POIconv : String = "-";
                                attribute Ipoint : Boolean = false;
                                attribute mass : Real = 0.7332497966079973;
                                attribute sigma_mass : Real = 0.28909372274994966;
                                attribute Cx : Real = 77.08858493715525;
                                attribute sigma_Cx : Real = 28.721044428837228;
                                attribute Cy : Real = -36.88400159589946;
                                attribute sigma_Cy : Real = 28.23690002309109;
                                attribute Cz : Real = 91.61950079724193;
                                attribute sigma_Cz : Real = 29.057750463592832;
                                attribute Ixx : Real = 0.9606364971161523;
                                attribute sigma_Ixx : Real = 0.37074144170588635;
                                attribute Iyy : Real = 0.9855901543380022;
                                attribute sigma_Iyy : Real = 0.3723953238821935;
                                attribute Izz : Real = 0.9440147050071717;
                                attribute sigma_Izz : Real = 0.37017423652493897;
                                attribute Ixy : Real = -0.028827491222627472;
                                attribute sigma_Ixy : Real = 0.02351283871158888;
                                attribute Ixz : Real = 0.03276269160907726;
                                attribute sigma_Ixz : Real = 0.022566176940390956;
                                attribute Iyz : Real = 0.03920061223880837;
                                attribute sigma_Iyz : Real = 0.02209918015384651;
                            }
                            part <'C.1.1.2.2.1.2.3'> 'Part 159' {
                                attribute POIconv : String = "+";
                                attribute Ipoint : Boolean = false;
                                attribute mass : Real = 0.3508497709115036;
                                attribute sigma_mass : Real = 0.28909372274994966;
                                attribute Cx : Real = -91.8515557423234;
                                attribute sigma_Cx : Real = 28.721044428837228;
                                attribute Cy : Real = 45.420784410089254;
                                attribute sigma_Cy : Real = 28.23690002309109;
                                attribute Cz : Real = 94.70796925015748;
                                attribute sigma_Cz : Real = 29.057750463592832;
                                attribute Ixx : Real = 0.4205162186672067;
                                attribute sigma_Ixx : Real = 0.37074144170588635;
                                attribute Iyy : Real = 0.5004571198168236;
                                attribute sigma_Iyy : Real = 0.3723953238821935;
                                attribute Izz : Real = 0.43971269939499696;
                                attribute sigma_Izz : Real = 0.37017423652493897;
                                attribute Ixy : Real = -0.007283636028104069;
                                attribute sigma_Ixy : Real = 0.02351283871158888;
                                attribute Ixz : Real = -0.018455258131757347;
                                attribute sigma_Ixz : Real = 0.022566176940390956;
                                attribute Iyz : Real = -0.03375045589190957;
                                attribute sigma_Iyz : Real = 0.02209918015384651;
                            }
                            part <'C.1.1.2.2.1.2.4'> 'Part 160' {
                                attribute POIconv : String = "+";
                                attribute Ipoint : Boolean = false;
                                attribute mass : Real = 0.1311549131362699;
                                attribute sigma_mass : Real = 0.28909372274994966;
                                attribute Cx : Real = -99.81856071390212;
                                attribute sigma_Cx : Real = 28.721044428837228;
                                attribute Cy : Real = 36.38377725146711;
                                attribute sigma_Cy : Real = 28.23690002309109;
                                attribute Cz : Real = 23.7374025862664;
                                attribute sigma_Cz : Real = 29.057750463592832;
                                attribute Ixx : Real = 0.14938146417337916;
                                attribute sigma_Ixx : Real = 0.37074144170588635;
                                attribute Iyy : Real = 0.15153397534380042;
                                attribute sigma_Iyy : Real = 0.3723953238821935;
                                attribute Izz : Real = 0.154632344761327;
                                attribute sigma_Izz : Real = 0.37017423652493897;
                                attribute Ixy : Real = -0.0027815909208092644;
                                attribute sigma_Ixy : Real = 0.02351283871158888;
                                attribute Ixz : Real = -0.002273090261887583;
                                attribute sigma_Ixz : Real = 0.022566176940390956;
                                attribute Iyz : Real = 0.0006452655050746567;
                                attribute sigma_Iyz : Real = 0.02209918015384651;
                            }
                            part <'C.1.1.2.2.1.2.5'> 'Part 161' {
                                attribute POIconv : String = "-";
                                attribute Ipoint : Boolean = false;
                                attribute mass : Real = 0.24676580228842795;
                                attribute sigma_mass : Real = 0.28909372274994966;
                                attribute Cx : Real = 64.69208640046418;
                                attribute sigma_Cx : Real = 28.721044428837228;
                                attribute Cy : Real = -85.01289207488298;
                                attribute sigma_Cy : Real = 28.23690002309109;
                                attribute Cz : Real = 31.298457086086273;
                                attribute sigma_Cz : Real = 29.057750463592832;
                                attribute Ixx : Real = 0.31763448575623865;
                                attribute sigma_Ixx : Real = 0.37074144170588635;
                                attribute Iyy : Real = 0.26658696509313023;
                                attribute sigma_Iyy : Real = 0.3723953238821935;
                                attribute Izz : Real = 0.28184354054357186;
                                attribute sigma_Izz : Real = 0.37017423652493897;
                                attribute Ixy : Real = -0.025203932874431536;
                                attribute sigma_Ixy : Real = 0.02351283871158888;
                                attribute Ixz : Real = -0.0006307231815927926;
                                attribute sigma_Ixz : Real = 0.022566176940390956;
                                attribute Iyz : Real = -7.151757905495217e-05;
                                attribute sigma_Iyz : Real = 0.02209918015384651;
                            }
                        }
                        part <'C.1.1.2.2.1.3'> 'Subassembly 46' {
                            attribute POIconv : String = "-";
                            attribute Ipoint : Boolean = false;
                            attribute mass : Real = 1.7429508695597762;
                            attribute sigma_mass : Real = 0.5007250159521434;
                            attribute Cx : Real = -43.44618008436389;
                            attribute sigma_Cx : Real = 18.540257475337402;
                            attribute Cy : Real = -1.9126241707650773;
                            attribute sigma_Cy : Real = 25.753725082471316;
                            attribute Cz : Real = -0.8353909417971653;
                            attribute sigma_Cz : Real = 24.691713977190314;
                            attribute Ixx : Real = 13572.373198565532;
                            attribute sigma_Ixx : Real = 6628.922375742476;
                            attribute Iyy : Real = 5465.1972311524105;
                            attribute sigma_Iyy : Real = 4138.030922518527;
                            attribute Izz : Real = 10164.286023046825;
                            attribute sigma_Izz : Real = 5685.636967927616;
                            attribute Ixy : Real = -3062.965297546595;
                            attribute sigma_Ixy : Real = 2580.016298452773;
                            attribute Ixz : Real = -619.9803356658347;
                            attribute sigma_Ixz : Real = 1535.5070425009012;
                            attribute Iyz : Real = -1945.0615619422588;
                            attribute sigma_Iyz : Real = 2756.7065189037585;
                            part <'C.1.1.2.2.1.3.1'> 'Part 162' {
                                attribute POIconv : String = "+";
                                attribute Ipoint : Boolean = false;
                                attribute mass : Real = 0.7893546829856932;
                                attribute sigma_mass : Real = 0.28909372274994966;
                                attribute Cx : Real = -67.3292264342308;
                                attribute sigma_Cx : Real = 28.721044428837228;
                                attribute Cy : Real = -73.68204486556351;
                                attribute sigma_Cy : Real = 28.23690002309109;
                                attribute Cz : Real = -38.91388191841543;
                                attribute sigma_Cz : Real = 29.057750463592832;
                                attribute Ixx : Real = 1.1290150077386103;
                                attribute sigma_Ixx : Real = 0.37074144170588635;
                                attribute Iyy : Real = 1.1553110575148235;
                                attribute sigma_Iyy : Real = 0.3723953238821935;
                                attribute Izz : Real = 1.1540887704207425;
                                attribute sigma_Izz : Real = 0.37017423652493897;
                                attribute Ixy : Real = 0.03496088578509725;
                                attribute sigma_Ixy : Real = 0.02351283871158888;
                                attribute Ixz : Real = -0.06512104541504529;
                                attribute sigma_Ixz : Real = 0.022566176940390956;
                                attribute Iyz : Real = 0.0332753571194644;
                                attribute sigma_Iyz : Real = 0.02209918015384651;
                            }
                            part <'C.1.1.2.2.1.3.2'> 'Part 163' {
                                attribute POIconv : String = "+";
                                attribute Ipoint : Boolean = false;
                                attribute mass : Real = 0.34623989950399847;
                                attribute sigma_mass : Real = 0.28909372274994966;
                                attribute Cx : Real = -43.06602762080729;
                                attribute sigma_Cx : Real = 28.721044428837228;
                                attribute Cy : Real = 1.5229502692818642;
                                attribute sigma_Cy : Real = 28.23690002309109;
                                attribute Cz : Real = 96.34249876253307;
                                attribute sigma_Cz : Real = 29.057750463592832;
                                attribute Ixx : Real = 0.44940755420150236;
                                attribute sigma_Ixx : Real = 0.37074144170588635;
                                attribute Iyy : Real = 0.4369300211826027;
                                attribute sigma_Iyy : Real = 0.3723953238821935;
                                attribute Izz : Real = 0.46562037221866565;
                                attribute sigma_Izz : Real = 0.37017423652493897;
                                attribute Ixy : Real = -0.00170280583917383;
                                attribute sigma_Ixy : Real = 0.02351283871158888;
                                attribute Ixz : Real = 0.02977670813782962;
                                attribute sigma_Ixz : Real = 0.022566176940390956;
                                attribute Iyz : Real = 0.044653474482573605;
                                attribute sigma_Iyz : Real = 0.02209918015384651;
                            }
                            part <'C.1.1.2.2.1.3.3'> 'Part 164' {
                                attribute POIconv : String = "+";
                                attribute Ipoint : Boolean = false;
                                attribute mass : Real = 0.6073562870700844;
                                attribute sigma_mass : Real = 0.28909372274994966;
                                attribute Cx : Real = -12.623134488239884;
                                attribute sigma_Cx : Real = 28.721044428837228;
                                attribute Cy : Real = 89.40444383770227;
                                attribute sigma_Cy : Real = 28.23690002309109;
                                attribute Cz : Real = -6.745311804115772;
                                attribute sigma_Cz : Real = 29.057750463592832;
                                attribute Ixx : Real = 0.7477489793465344;
                                attribute sigma_Ixx : Real = 0.37074144170588635;
                                attribute Iyy : Real = 0.7959935845449397;
                                attribute sigma_Iyy : Real = 0.3723953238821935;
                                attribute Izz : Real = 0.78254186501959;
                                attribute sigma_Izz : Real = 0.37017423652493897;
                                attribute Ixy : Real = -0.03885328169766915;
                                attribute sigma_Ixy : Real = 0.02351283871158888;
                                attribute Ixz : Real = -0.0012848464781238028;
                                attribute sigma_Ixz : Real = 0.022566176940390956;
                                attribute Iyz : Real = -0.041375048005681744;
                                attribute sigma_Iyz : Real = 0.02209918015384651;
                            }
                        }
                        part <'C.1.1.2.2.1.4'> 'Subassembly 47' {
                            attribute POIconv : String = "-";
                            attribute Ipoint : Boolean = false;
                            attribute mass : Real = 1.7440108713202647;
                            attribute sigma_mass : Real = 0.6464332159373649;
                            attribute Cx : Real = 19.392718687921658;
                            attribute sigma_Cx : Real = 25.49727348914511;
                            attribute Cy : Real = 16.479511789349306;
                            attribute sigma_Cy : Real = 19.915598635943788;
                            attribute Cz : Real = 11.878067649556943;
                            attribute sigma_Cz : Real = 24.869859431961554;
                            attribute Ixx : Real = 7761.514924205168;
                            attribute sigma_Ixx : Real = 4475.295001993062;
                            attribute Iyy : Real = 9768.192266047621;
                            attribute sigma_Iyy : Real = 5985.777663628189;
                            attribute Izz : Real = 8064.592031452636;
                            attribute sigma_Izz : Real = 5005.821217777005;
                            attribute Ixy : Real = -2591.833928552899;
                            attribute sigma_Ixy : Real = 2183.5938634389568;
                            attribute Ixz : Real = 1828.7092076742917;
                            attribute sigma_Ixz : Real = 2811.5187837570297;
                            attribute Iyz : Real = 1118.321514207783;
                            attribute sigma_Iyz : Real = 1967.8640139937615;
                            part <'C.1.1.2.2.1.4.1'> 'Part 165' {
                                attribute POIconv : String = "+";
                                attribute Ipoint : Boolean = false;
                                attribute mass : Real = 0.3922002762623597;
                                attribute sigma_mass : Real = 0.28909372274994966;
                                attribute Cx : Real = 41.76503103226423;
                                attribute sigma_Cx : Real = 28.721044428837228;
                                attribute Cy : Real = 16.801129328086972;
                                attribute sigma_Cy : Real = 28.23690002309109;
                                attribute Cz : Real = -31.626209104433656;
                                attribute sigma_Cz : Real = 29.057750463592832;
                                attribute Ixx : Real = 0.48126984569039655;
                                attribute sigma_Ixx : Real = 0.37074144170588635;
                                attribute Iyy : Real = 0.5040004115610209;
                                attribute sigma_Iyy : Real = 0.3723953238821935;
                                attribute Izz : Real = 0.49089795328071667;
                                attribute sigma_Izz : Real = 0.37017423652493897;
                                attribute Ixy : Real = -0.048019304466833994;
                                attribute sigma_Ixy : Real = 0.02351283871158888;
                                attribute Ixz : Real = -0.003057873010357374;
                                attribute sigma_Ixz : Real = 0.022566176940390956;
                                attribute Iyz : Real = 0.03230530719502631;
                                attribute sigma_Iyz : Real = 0.02209918015384651;
                            }
                            part <'C.1.1.2.2.1.4.2'> 'Part 166' {
                                attribute POIconv : String = "+";
                                attribute Ipoint : Boolean = false;
                                attribute mass : Real = 0.36562424327223564;
                                attribute sigma_mass : Real = 0.28909372274994966;
                                attribute Cx : Real = 5.3220359608531;
                                attribute sigma_Cx : Real = 28.721044428837228;
                                attribute Cy : Real = -41.46459153853357;
                                attribute sigma_Cy : Real = 28.23690002309109;
                                attribute Cz : Real = 65.6319173052907;
                                attribute sigma_Cz : Real = 29.057750463592832;
                                attribute Ixx : Real = 0.5162617026691243;
                                attribute sigma_Ixx : Real = 0.37074144170588635;
                                attribute Iyy : Real = 0.4954593465074545;
                                attribute sigma_Iyy : Real = 0.3723953238821935;
                                attribute Izz : Real = 0.5326384598125916;
                                attribute sigma_Izz : Real = 0.37017423652493897;
                                attribute Ixy : Real = 0.030207636725343538;
                                attribute sigma_Ixy : Real = 0.02351283871158888;
                                attribute Ixz : Real = 0.02205165776763099;
                                attribute sigma_Ixz : Real = 0.022566176940390956;
                                attribute Iyz : Real = -0.03535328358763729;
                                attribute sigma_Iyz : Real = 0.02209918015384651;
                            }
                            part <'C.1.1.2.2.1.4.3'> 'Part 167' {
                                attribute POIconv : String = "-";
                                attribute Ipoint : Boolean = false;
                                attribute mass : Real = 0.19489581103413367;
                                attribute sigma_mass : Real = 0.28909372274994966;
                                attribute Cx : Real = -73.25983932241797;
                                attribute sigma_Cx : Real = 28.721044428837228;
                                attribute Cy : Real = -26.92969162017107;
                                attribute sigma_Cy : Real = 28.23690002309109;
                                attribute Cz : Real = -48.997609969228506;
                                attribute sigma_Cz : Real = 29.057750463592832;
                                attribute Ixx : Real = 0.2217614715819434;
                                attribute sigma_Ixx : Real = 0.37074144170588635;
                                attribute Iyy : Real = 0.24654102146115023;
                                attribute sigma_Iyy : Real = 0.3723953238821935;
                                attribute Izz : Real = 0.23082892828115417;
                                attribute sigma_Izz : Real = 0.37017423652493897;
                                attribute Ixy : Real = -0.02575661379570556;
                                attribute sigma_Ixy : Real = 0.02351283871158888;
                                attribute Ixz : Real = -0.0007370291618240341;
                                attribute sigma_Ixz : Real = 0.022566176940390956;
                                attribute Iyz : Real = -0.003283593917601211;
                                attribute sigma_Iyz : Real = 0.02209918015384651;
                            }
                            part <'C.1.1.2.2.1.4.4'> 'Part 168' {
                                attribute POIconv : String = "+";
                                attribute Ipoint : Boolean = false;
                                attribute mass : Real = 0.28059754030313344;
                                attribute sigma_mass : Real = 0.28909372274994966;
                                attribute Cx : Real = -43.049339298158884;
                                attribute sigma_Cx : Real = 28.721044428837228;
                                attribute Cy : Real = 26.16354515776038;
                                attribute sigma_Cy : Real = 28.23690002309109;
                                attribute Cz : Real = 93.12769616954029;
                                attribute sigma_Cz : Real = 29.057750463592832;
                                attribute Ixx : Real = 0.308688770596357;
                                attribute sigma_Ixx : Real = 0.37074144170588635;
                                attribute Iyy : Real = 0.30325470210694705;
                                attribute sigma_Iyy : Real = 0.3723953238821935;
                                attribute Izz : Real = 0.3512915592998523;
                                attribute sigma_Izz : Real = 0.37017423652493897;
                                attribute Ixy : Real = 0.00012055425453756205;
                                attribute sigma_Ixy : Real = 0.02351283871158888;
                                attribute Ixz : Real = 0.018464009269710403;
                                attribute sigma_Ixz : Real = 0.022566176940390956;
                                attribute Iyz : Real = 0.01283015502173616;
                                attribute sigma_Iyz : Real = 0.02209918015384651;
                            }
                            part <'C.1.1.2.2.1.4.5'> 'Part 169' {
                                attribute POIconv : String = "+";
                                attribute Ipoint : Boolean = false;
                                attribute mass : Real = 0.510693000448402;
                                attribute sigma_mass : Real = 0.28909372274994966;
                                attribute Cx : Real = 81.95249321870506;
                                attribute sigma_Cx : Real = 28.721044428837228;
                                attribute Cy : Real = 68.96228790283203;
                                attribute sigma_Cy : Real = 28.23690002309109;
                                attribute Cz : Real = -14.606244023889303;
                                attribute sigma_Cz : Real = 29.057750463592832;
                                attribute Ixx : Real = 0.5349014972267188;
                                attribute sigma_Ixx : Real = 0.37074144170588635;
                                attribute Iyy : Real = 0.524934917587324;
                                attribute sigma_Iyy : Real = 0.3723953238821935;
                                attribute Izz : Real = 0.5736673343665503;
                                attribute sigma_Izz : Real = 0.37017423652493897;
                                attribute Ixy : Real = -0.04917564918169298;
                                attribute sigma_Ixy : Real = 0.02351283871158888;
                                attribute Ixz : Real = -0.024640099051106902;
                                attribute sigma_Ixz : Real = 0.022566176940390956;
                                attribute Iyz : Real = 0.011977660643177224;
                                attribute sigma_Iyz : Real = 0.02209918015384651;
                            }
                        }
                    }
                    part <'C.1.1.2.2.2'> 'Assembly 13' {
                        attribute POIconv : String = "-";
                        attribute Ipoint : Boolean = false;
                        attribute mass : Real = 2.793848690938903;
                        attribute sigma_mass : Real = 0.6464332159373648;
                        attribute Cx : Real = -21.40009707187319;
                        attribute sigma_Cx : Real = 15.534353323054303;
                        attribute Cy : Real = 23.63630475883233;
                        attribute sigma_Cy : Real = 18.08063018451818;
                        attribute Cz : Real = -1.3348119586099294;
                        attribute sigma_Cz : Real = 18.468866541043052;
                        attribute Ixx : Real = 15754.538064410179;
                        attribute sigma_Ixx : Real = 6755.533964936606;
                        attribute Iyy : Real = 9732.336255096474;
                        attribute sigma_Iyy : Real = 5192.086049280334;
                        attribute Izz : Real = 11224.614255035;
                        attribute sigma_Izz : Real = 5589.491445518823;
                        attribute Ixy : Real = 1325.1797124745285;
                        attribute sigma_Ixy : Real = 2668.1529069581943;
                        attribute Ixz : Real = -1097.8757646335782;
                        attribute sigma_Ixz : Real = 2362.0911675912625;
                        attribute Iyz : Real = 74.47651337419097;
                        attribute sigma_Iyz : Real = 3143.063458086148;
                        part <'C.1.1.2.2.2.1'> 'Subassembly 48' {
                            attribute POIconv : String = "-";
                            attribute Ipoint : Boolean = false;
                            attribute mass : Real = 1.3784646292303222;
                            attribute sigma_mass : Real = 0.40884026350990615;
                            attribute Cx : Real = -33.13474464984104;
                            attribute sigma_Cx : Real = 22.400351809298773;
                            attribute Cy : Real = -3.363801776010158;
                            attribute sigma_Cy : Real = 27.787735790081378;
                            attribute Cz : Real = -0.557200167013529;
                            attribute sigma_Cz : Real = 21.19346879387262;
                            attribute Ixx : Real = 6271.426410342605;
                            attribute sigma_Ixx : Real = 4159.099111597139;
                            attribute Iyy : Real = 1820.319187925209;
                            attribute sigma_Iyy : Real = 2109.3898149688434;
                            attribute Izz : Real = 7248.121141309136;
                            attribute sigma_Izz : Real = 4545.1994916056265;
                            attribute Ixy : Real = 2859.1568021664243;
                            attribute sigma_Ixy : Real = 2193.8072064983494;
                            attribute Ixz : Real = -767.2394413186853;
                            attribute sigma_Ixz : Real = 1050.9347412779023;
                            attribute Iyz : Real = 1569.559039333847;
                            attribute sigma_Iyz : Real = 1962.4971541924983;
                            part <'C.1.1.2.2.2.1.1'> 'Part 170' {
                                attribute POIconv : String = "+";
                                attribute Ipoint : Boolean = false;
                                attribute mass : Real = 0.6996860573282465;
                                attribute sigma_mass : Real = 0.28909372274994966;
                                attribute Cx : Real = -1.7720005940645933;
                                attribute sigma_Cx : Real = 28.721044428837228;
                                attribute Cy : Real = -67.52090468071401;
                                attribute sigma_Cy : Real = 28.23690002309109;
                                attribute Cz : Real = 16.659361915662885;
                                attribute sigma_Cz : Real = 29.057750463592832;
                                attribute Ixx : Real = 0.7565597034536904;
                                attribute sigma_Ixx : Real = 0.37074144170588635;
                                attribute Iyy : Real = 0.7140389968962108;
                                attribute sigma_Iyy : Real = 0.3723953238821935;
                                attribute Izz : Real = 0.7799959383165427;
                                attribute sigma_Izz : Real = 0.37017423652493897;
                                attribute Ixy : Real = -0.041547433095870986;
                                attribute sigma_Ixy : Real = 0.02351283871158888;
                                attribute Ixz : Real = -0.01745733488467227;
                                attribute sigma_Ixz : Real = 0.022566176940390956;
                                attribute Iyz : Real = -0.04193598402791303;
                                attribute sigma_Iyz : Real = 0.02209918015384651;
                            }
                            part <'C.1.1.2.2.2.1.2'> 'Part 171' {
                                attribute POIconv : String = "-";
                                attribute Ipoint : Boolean = false;
                                attribute mass : Real = 0.6787785719020758;
                                attribute sigma_mass : Real = 0.28909372274994966;
                                attribute Cx : Real = -65.46351229771972;
                                attribute sigma_Cx : Real = 28.721044428837228;
                                attribute Cy : Real = 62.76944437995553;
                                attribute sigma_Cy : Real = 28.23690002309109;
                                attribute Cz : Real = -18.304060399532318;
                                attribute sigma_Cz : Real = 29.057750463592832;
                                attribute Ixx : Real = 0.7822071559843139;
                                attribute sigma_Ixx : Real = 0.37074144170588635;
                                attribute Iyy : Real = 0.7778822248011155;
                                attribute sigma_Iyy : Real = 0.3723953238821935;
                                attribute Izz : Real = 0.978182922344661;
                                attribute sigma_Izz : Real = 0.37017423652493897;
                                attribute Ixy : Real = 0.014097647102195519;
                                attribute sigma_Ixy : Real = 0.02351283871158888;
                                attribute Ixz : Real = -0.01694636423436308;
                                attribute sigma_Ixz : Real = 0.022566176940390956;
                                attribute Iyz : Real = 0.01500608161680842;
                                attribute sigma_Iyz : Real = 0.02209918015384651;
                            }
                        }
                        part <'C.1.1.2.2.2.2'> 'Subassembly 49' {
                            attribute POIconv : String = "-";
                            attribute Ipoint : Boolean = false;
                            attribute mass : Real = 1.4153840617085807;
                            attribute sigma_mass : Real = 0.5007250159521434;
                            attribute Cx : Real = -9.971540639504346;
                            attribute sigma_Cx : Real = 20.8919604289553;
                            attribute Cy : Real = 49.932129934934935;
                            attribute sigma_Cy : Real = 19.84897482550879;
                            attribute Cz : Real = -2.0921402195302217;
                            attribute sigma_Cz : Real = 30.047963237396157;
                            attribute Ixx : Real = 7497.861477064483;
                            attribute sigma_Ixx : Real = 4654.284923258925;
                            attribute Iyy : Real = 7535.688471840768;
                            attribute sigma_Iyy : Real = 4638.158009773543;
                            attribute Izz : Real = 1618.2049776500833;
                            attribute sigma_Izz : Real = 1686.7367507863787;
                            attribute Ixy : Real = -671.8729375177036;
                            attribute sigma_Ixy : Real = 813.6372716160243;
                            attribute Ixz : Real = -355.4652014324578;
                            attribute sigma_Ixz : Real = 2029.810177551415;
                            attribute Iyz : Real = -1552.210986772875;
                            attribute sigma_Iyz : Real = 2037.9027489226426;
                            part <'C.1.1.2.2.2.2.1'> 'Part 172' {
                                attribute POIconv : String = "+";
                                attribute Ipoint : Boolean = false;
                                attribute mass : Real = 0.4198192962212488;
                                attribute sigma_mass : Real = 0.28909372274994966;
                                attribute Cx : Real = -37.14067074470222;
                                attribute sigma_Cx : Real = 28.721044428837228;
                                attribute Cy : Real = 14.053925639018416;
                                attribute sigma_Cy : Real = 28.23690002309109;
                                attribute Cz : Real = -85.41102516464889;
                                attribute sigma_Cz : Real = 29.057750463592832;
                                attribute Ixx : Real = 0.4565478244430911;
                                attribute sigma_Ixx : Real = 0.37074144170588635;
                                attribute Iyy : Real = 0.43155697305090707;
                                attribute sigma_Iyy : Real = 0.3723953238821935;
                                attribute Izz : Real = 0.44063510654598226;
                                attribute sigma_Izz : Real = 0.37017423652493897;
                                attribute Ixy : Real = -0.01574009883870208;
                                attribute sigma_Ixy : Real = 0.02351283871158888;
                                attribute Ixz : Real = -0.02596286629234972;
                                attribute sigma_Ixz : Real = 0.022566176940390956;
                                attribute Iyz : Real = -0.005362394374839528;
                                attribute sigma_Iyz : Real = 0.02209918015384651;
                            }
                            part <'C.1.1.2.2.2.2.2'> 'Part 173' {
                                attribute POIconv : String = "+";
                                attribute Ipoint : Boolean = false;
                                attribute mass : Real = 0.7348289012997411;
                                attribute sigma_mass : Real = 0.28909372274994966;
                                attribute Cx : Real = -10.253697354346514;
                                attribute sigma_Cx : Real = 28.721044428837228;
                                attribute Cy : Real = 62.32720548287034;
                                attribute sigma_Cy : Real = 28.23690002309109;
                                attribute Cz : Real = 63.26927565969527;
                                attribute sigma_Cz : Real = 29.057750463592832;
                                attribute Ixx : Real = 0.9086654377186083;
                                attribute sigma_Ixx : Real = 0.37074144170588635;
                                attribute Iyy : Real = 0.817470985763932;
                                attribute sigma_Iyy : Real = 0.3723953238821935;
                                attribute Izz : Real = 0.9042395640767662;
                                attribute sigma_Izz : Real = 0.37017423652493897;
                                attribute Ixy : Real = 0.04881666259776883;
                                attribute sigma_Ixy : Real = 0.02351283871158888;
                                attribute Ixz : Real = -0.00671583145843677;
                                attribute sigma_Ixz : Real = 0.022566176940390956;
                                attribute Iyz : Real = -0.0737893775556489;
                                attribute sigma_Iyz : Real = 0.02209918015384651;
                            }
                            part <'C.1.1.2.2.2.2.3'> 'Part 174' {
                                attribute POIconv : String = "-";
                                attribute Ipoint : Boolean = false;
                                attribute mass : Real = 0.26073586418759076;
                                attribute sigma_mass : Real = 0.28909372274994966;
                                attribute Cx : Real = 34.56955854780972;
                                attribute sigma_Cx : Real = 28.721044428837228;
                                attribute Cy : Real = 72.76789420284331;
                                attribute sigma_Cy : Real = 28.23690002309109;
                                attribute Cz : Real = -52.1450235042721;
                                attribute sigma_Cz : Real = 29.057750463592832;
                                attribute Ixx : Real = 0.3281893917850688;
                                attribute sigma_Ixx : Real = 0.37074144170588635;
                                attribute Iyy : Real = 0.31658153701329195;
                                attribute sigma_Iyy : Real = 0.3723953238821935;
                                attribute Izz : Real = 0.35617066525768576;
                                attribute sigma_Izz : Real = 0.37017423652493897;
                                attribute Ixy : Real = 0.023748535612479228;
                                attribute sigma_Ixy : Real = 0.02351283871158888;
                                attribute Ixz : Real = 0.008651694245284846;
                                attribute sigma_Ixz : Real = 0.022566176940390956;
                                attribute Iyz : Real = -0.0021481332233297193;
                                attribute sigma_Iyz : Real = 0.02209918015384651;
                            }
                        }
                    }
                    part <'C.1.1.2.2.3'> 'Assembly 14' {
                        attribute POIconv : String = "-";
                        attribute Ipoint : Boolean = false;
                        attribute mass : Real = 7.9847995723111085;
                        attribute sigma_mass : Real = 1.1563748909997986;
                        attribute Cx : Real = -4.22182210081867;
                        attribute sigma_Cx : Real = 12.449369048861335;
                        attribute Cy : Real = -40.787982374489836;
                        attribute sigma_Cy : Real = 9.770354385243092;
                        attribute Cz : Real = 8.097486317078793;
                        attribute sigma_Cz : Real = 12.409891185274457;
                        attribute Ixx : Real = 28458.566061791385;
                        attribute sigma_Ixx : Real = 11288.132808677037;
                        attribute Iyy : Real = 42707.117436876884;
                        attribute sigma_Iyy : Real = 15668.405660513961;
                        attribute Izz : Real = 32968.370086790026;
                        attribute sigma_Izz : Real = 10888.32520138551;
                        attribute Ixy : Real = -5373.86924820884;
                        attribute sigma_Ixy : Real = 4741.324639391652;
                        attribute Ixz : Real = 6893.777334612579;
                        attribute sigma_Ixz : Real = 7576.114453859485;
                        attribute Iyz : Real = 756.2532708824685;
                        attribute sigma_Iyz : Real = 4358.531952768692;
                        part <'C.1.1.2.2.3.1'> 'Subassembly 50' {
                            attribute POIconv : String = "-";
                            attribute Ipoint : Boolean = false;
                            attribute mass : Real = 1.7899949761810712;
                            attribute sigma_mass : Real = 0.5781874454998993;
                            attribute Cx : Real = 50.59611300880514;
                            attribute sigma_Cx : Real = 20.745081949216413;
                            attribute Cy : Real = -10.277745241141082;
                            attribute sigma_Cy : Real = 16.256558643017687;
                            attribute Cz : Real = -4.908987565862508;
                            attribute sigma_Cz : Real = 18.518368566527954;
                            attribute Ixx : Real = 2486.2298722191917;
                            attribute sigma_Ixx : Real = 2187.5540115893273;
                            attribute Iyy : Real = 5119.368523079636;
                            attribute sigma_Iyy : Real = 3832.7129167070657;
                            attribute Izz : Real = 4079.683745684356;
                            attribute sigma_Izz : Real = 3134.899915248627;
                            attribute Ixy : Real = -738.7629728353611;
                            attribute sigma_Ixy : Real = 1336.7879531590154;
                            attribute Ixz : Real = -1986.19734690606;
                            attribute sigma_Ixz : Real = 1867.3558076282575;
                            attribute Iyz : Real = -405.7011125521964;
                            attribute sigma_Iyz : Real = 1002.4513528125922;
                            part <'C.1.1.2.2.3.1.1'> 'Part 175' {
                                attribute POIconv : String = "+";
                                attribute Ipoint : Boolean = false;
                                attribute mass : Real = 0.3818557383387815;
                                attribute sigma_mass : Real = 0.28909372274994966;
                                attribute Cx : Real = 78.52229713462293;
                                attribute sigma_Cx : Real = 28.721044428837228;
                                attribute Cy : Real = 21.36943400837481;
                                attribute sigma_Cy : Real = 28.23690002309109;
                                attribute Cz : Real = -9.543733717873693;
                                attribute sigma_Cz : Real = 29.057750463592832;
                                attribute Ixx : Real = 0.5319513754691908;
                                attribute sigma_Ixx : Real = 0.37074144170588635;
                                attribute Iyy : Real = 0.5483133823325838;
                                attribute sigma_Iyy : Real = 0.3723953238821935;
                                attribute Izz : Real = 0.4872504616722236;
                                attribute sigma_Izz : Real = 0.37017423652493897;
                                attribute Ixy : Real = -0.008903521278638978;
                                attribute sigma_Ixy : Real = 0.02351283871158888;
                                attribute Ixz : Real = 0.018111536032810044;
                                attribute sigma_Ixz : Real = 0.022566176940390956;
                                attribute Iyz : Real = -0.008122788963804048;
                                attribute sigma_Iyz : Real = 0.02209918015384651;
                            }
                            part <'C.1.1.2.2.3.1.2'> 'Part 176' {
                                attribute POIconv : String = "-";
                                attribute Ipoint : Boolean = false;
                                attribute mass : Real = 0.34342165624699555;
                                attribute sigma_mass : Real = 0.28909372274994966;
                                attribute Cx : Real = 41.91951500251889;
                                attribute sigma_Cx : Real = 28.721044428837228;
                                attribute Cy : Real = 2.2042570635676384;
                                attribute sigma_Cy : Real = 28.23690002309109;
                                attribute Cz : Real = 22.982495417818427;
                                attribute sigma_Cz : Real = 29.057750463592832;
                                attribute Ixx : Real = 0.40729414914632167;
                                attribute sigma_Ixx : Real = 0.37074144170588635;
                                attribute Iyy : Real = 0.47263102522078565;
                                attribute sigma_Iyy : Real = 0.3723953238821935;
                                attribute Izz : Real = 0.47056312665341976;
                                attribute sigma_Izz : Real = 0.37017423652493897;
                                attribute Ixy : Real = -0.006881955584817899;
                                attribute sigma_Ixy : Real = 0.02351283871158888;
                                attribute Ixz : Real = -0.006839163063818052;
                                attribute sigma_Ixz : Real = 0.022566176940390956;
                                attribute Iyz : Real = -0.009270036525564025;
                                attribute sigma_Iyz : Real = 0.02209918015384651;
                            }
                            part <'C.1.1.2.2.3.1.3'> 'Part 177' {
                                attribute POIconv : String = "+";
                                attribute Ipoint : Boolean = false;
                                attribute mass : Real = 0.6777255211237352;
                                attribute sigma_mass : Real = 0.28909372274994966;
                                attribute Cx : Real = 83.33116816356778;
                                attribute sigma_Cx : Real = 28.721044428837228;
                                attribute Cy : Real = -21.35280929505825;
                                attribute sigma_Cy : Real = 28.23690002309109;
                                attribute Cz : Real = 15.441287821158767;
                                attribute sigma_Cz : Real = 29.057750463592832;
                                attribute Ixx : Real = 0.9386723776818713;
                                attribute sigma_Ixx : Real = 0.37074144170588635;
                                attribute Iyy : Real = 0.7963311692494339;
                                attribute sigma_Iyy : Real = 0.3723953238821935;
                                attribute Izz : Real = 0.7530448965205254;
                                attribute sigma_Izz : Real = 0.37017423652493897;
                                attribute Ixy : Real = -0.052695440524780354;
                                attribute sigma_Ixy : Real = 0.02351283871158888;
                                attribute Ixz : Real = 0.0012846230703561275;
                                attribute sigma_Ixz : Real = 0.022566176940390956;
                                attribute Iyz : Real = 0.05640080099556968;
                                attribute sigma_Iyz : Real = 0.02209918015384651;
                            }
                            part <'C.1.1.2.2.3.1.4'> 'Part 178' {
                                attribute POIconv : String = "-";
                                attribute Ipoint : Boolean = false;
                                attribute mass : Real = 0.38699206047155893;
                                attribute sigma_mass : Real = 0.28909372274994966;
                                attribute Cx : Real = -26.587445428594947;
                                attribute sigma_Cx : Real = 28.721044428837228;
                                attribute Cy : Real = -33.18620836362243;
                                attribute sigma_Cy : Real = 28.23690002309109;
                                attribute Cz : Real = -60.725729214027524;
                                attribute sigma_Cz : Real = 29.057750463592832;
                                attribute Ixx : Real = 0.4727235236998924;
                                attribute sigma_Ixx : Real = 0.37074144170588635;
                                attribute Iyy : Real = 0.5222823067161467;
                                attribute sigma_Iyy : Real = 0.3723953238821935;
                                attribute Izz : Real = 0.48139932215659925;
                                attribute sigma_Izz : Real = 0.37017423652493897;
                                attribute Ixy : Real = 0.025724385298106316;
                                attribute sigma_Ixy : Real = 0.02351283871158888;
                                attribute Ixz : Real = -0.011550567601656537;
                                attribute sigma_Ixz : Real = 0.022566176940390956;
                                attribute Iyz : Real = -0.0023495446656244673;
                                attribute sigma_Iyz : Real = 0.02209918015384651;
                            }
                        }
                        part <'C.1.1.2.2.3.2'> 'Subassembly 51' {
                            attribute POIconv : String = "-";
                            attribute Ipoint : Boolean = false;
                            attribute mass : Real = 3.265384811228141;
                            attribute sigma_mass : Real = 0.6464332159373649;
                            attribute Cx : Real = 1.8430844618695317;
                            attribute sigma_Cx : Real = 17.204927428720044;
                            attribute Cy : Real = -72.09557973110854;
                            attribute sigma_Cy : Real = 14.764639128856894;
                            attribute Cz : Real = 0.8461501343586872;
                            attribute sigma_Cz : Real = 17.45434224732792;
                            attribute Ixx : Real = 6566.442860214721;
                            attribute sigma_Ixx : Real = 4527.158622860416;
                            attribute Iyy : Real = 12367.910106967245;
                            attribute sigma_Iyy : Real = 6509.750177418542;
                            attribute Izz : Real = 7901.562914503439;
                            attribute sigma_Izz : Real = 4855.907586351207;
                            attribute Ixy : Real = -2096.075076547242;
                            attribute sigma_Ixy : Real = 2305.421607718066;
                            attribute Ixz : Real = 2677.580857776139;
                            attribute sigma_Ixz : Real = 3151.9067039606575;
                            attribute Iyz : Real = -9.072327129877511;
                            attribute sigma_Iyz : Real = 2000.6381558545372;
                            part <'C.1.1.2.2.3.2.1'> 'Part 179' {
                                attribute POIconv : String = "-";
                                attribute Ipoint : Boolean = false;
                                attribute mass : Real = 0.921826909518335;
                                attribute sigma_mass : Real = 0.28909372274994966;
                                attribute Cx : Real = -51.94877693429589;
                                attribute sigma_Cx : Real = 28.721044428837228;
                                attribute Cy : Real = -91.24262607656419;
                                attribute sigma_Cy : Real = 28.23690002309109;
                                attribute Cz : Real = 46.45874951966107;
                                attribute sigma_Cz : Real = 29.057750463592832;
                                attribute Ixx : Real = 1.1651781250013817;
                                attribute sigma_Ixx : Real = 0.37074144170588635;
                                attribute Iyy : Real = 1.26555224577138;
                                attribute sigma_Iyy : Real = 0.3723953238821935;
                                attribute Izz : Real = 1.0835543969554178;
                                attribute sigma_Izz : Real = 0.37017423652493897;
                                attribute Ixy : Real = -0.015265954075495313;
                                attribute sigma_Ixy : Real = 0.02351283871158888;
                                attribute Ixz : Real = 0.09962482356939162;
                                attribute sigma_Ixz : Real = 0.022566176940390956;
                                attribute Iyz : Real = -0.07392358763382721;
                                attribute sigma_Iyz : Real = 0.02209918015384651;
                            }
                            part <'C.1.1.2.2.3.2.2'> 'Part 180' {
                                attribute POIconv : String = "+";
                                attribute Ipoint : Boolean = false;
                                attribute mass : Real = 0.8862786426742095;
                                attribute sigma_mass : Real = 0.28909372274994966;
                                attribute Cx : Real = 54.19662734493613;
                                attribute sigma_Cx : Real = 28.721044428837228;
                                attribute Cy : Real = -68.70926516130567;
                                attribute sigma_Cy : Real = 28.23690002309109;
                                attribute Cz : Real = -41.655086586251855;
                                attribute sigma_Cz : Real = 29.057750463592832;
                                attribute Ixx : Real = 1.0921190348871317;
                                attribute sigma_Ixx : Real = 0.37074144170588635;
                                attribute Iyy : Real = 1.1557262504995385;
                                attribute sigma_Iyy : Real = 0.3723953238821935;
                                attribute Izz : Real = 1.131124092215032;
                                attribute sigma_Izz : Real = 0.37017423652493897;
                                attribute Ixy : Real = 0.1221352198976941;
                                attribute sigma_Ixy : Real = 0.02351283871158888;
                                attribute Ixz : Real = -0.05467236166137991;
                                attribute sigma_Ixz : Real = 0.022566176940390956;
                                attribute Iyz : Real = -0.05448487207736866;
                                attribute sigma_Iyz : Real = 0.02209918015384651;
                            }
                            part <'C.1.1.2.2.3.2.3'> 'Part 181' {
                                attribute POIconv : String = "+";
                                attribute Ipoint : Boolean = false;
                                attribute mass : Real = 0.3094832809737418;
                                attribute sigma_mass : Real = 0.28909372274994966;
                                attribute Cx : Real = 65.61011811718345;
                                attribute sigma_Cx : Real = 28.721044428837228;
                                attribute Cy : Real = -31.50172927416861;
                                attribute sigma_Cy : Real = 28.23690002309109;
                                attribute Cz : Real = 38.402926130220294;
                                attribute sigma_Cz : Real = 29.057750463592832;
                                attribute Ixx : Real = 0.4233542535556114;
                                attribute sigma_Ixx : Real = 0.37074144170588635;
                                attribute Iyy : Real = 0.43254369374762774;
                                attribute sigma_Iyy : Real = 0.3723953238821935;
                                attribute Izz : Real = 0.3669955389625493;
                                attribute sigma_Izz : Real = 0.37017423652493897;
                                attribute Ixy : Real = 0.008415277523069996;
                                attribute sigma_Ixy : Real = 0.02351283871158888;
                                attribute Ixz : Real = 0.014774548870305677;
                                attribute sigma_Ixz : Real = 0.022566176940390956;
                                attribute Iyz : Real = -0.010480292298601068;
                                attribute sigma_Iyz : Real = 0.02209918015384651;
                            }
                            part <'C.1.1.2.2.3.2.4'> 'Part 182' {
                                attribute POIconv : String = "+";
                                attribute Ipoint : Boolean = false;
                                attribute mass : Real = 0.22355187601805665;
                                attribute sigma_mass : Real = 0.28909372274994966;
                                attribute Cx : Real = -42.93162287212908;
                                attribute sigma_Cx : Real = 28.721044428837228;
                                attribute Cy : Real = -96.18664039298892;
                                attribute sigma_Cy : Real = 28.23690002309109;
                                attribute Cz : Real = -82.45789795182645;
                                attribute sigma_Cz : Real = 29.057750463592832;
                                attribute Ixx : Real = 0.3079912211934493;
                                attribute sigma_Ixx : Real = 0.37074144170588635;
                                attribute Iyy : Real = 0.35107218112298116;
                                attribute sigma_Iyy : Real = 0.3723953238821935;
                                attribute Izz : Real = 0.3078917453193108;
                                attribute sigma_Izz : Real = 0.37017423652493897;
                                attribute Ixy : Real = -0.02019461563142872;
                                attribute sigma_Ixy : Real = 0.02351283871158888;
                                attribute Ixz : Real = 0.005513813084381957;
                                attribute sigma_Ixz : Real = 0.022566176940390956;
                                attribute Iyz : Real = 0.006168232857509408;
                                attribute sigma_Iyz : Real = 0.02209918015384651;
                            }
                            part <'C.1.1.2.2.3.2.5'> 'Part 183' {
                                attribute POIconv : String = "+";
                                attribute Ipoint : Boolean = false;
                                attribute mass : Real = 0.9242441020437981;
                                attribute sigma_mass : Real = 0.28909372274994966;
                                attribute Cx : Real = -5.231239879503846;
                                attribute sigma_Cx : Real = 28.721044428837228;
                                attribute Cy : Real = -64.01164601556957;
                                attribute sigma_Cy : Real = 28.23690002309109;
                                attribute Cz : Real = 3.6815470084547997;
                                attribute sigma_Cz : Real = 29.057750463592832;
                                attribute Ixx : Real = 1.0950805614993238;
                                attribute sigma_Ixx : Real = 0.37074144170588635;
                                attribute Iyy : Real = 1.1707770162630593;
                                attribute sigma_Iyy : Real = 0.3723953238821935;
                                attribute Izz : Real = 1.0120576525062939;
                                attribute sigma_Izz : Real = 0.37017423652493897;
                                attribute Ixy : Real = -0.010934337522805072;
                                attribute sigma_Ixy : Real = 0.02351283871158888;
                                attribute Ixz : Real = -0.08165481635000502;
                                attribute sigma_Ixz : Real = 0.022566176940390956;
                                attribute Iyz : Real = 0.0296555379743003;
                                attribute sigma_Iyz : Real = 0.02209918015384651;
                            }
                        }
                        part <'C.1.1.2.2.3.3'> 'Subassembly 52' {
                            attribute POIconv : String = "-";
                            attribute Ipoint : Boolean = false;
                            attribute mass : Real = 0.9042685998999513;
                            attribute sigma_mass : Real = 0.40884026350990615;
                            attribute Cx : Real = -44.12431627490372;
                            attribute sigma_Cx : Real = 44.74082732628019;
                            attribute Cy : Real = -32.188208635495656;
                            attribute sigma_Cy : Real = 27.630835740261183;
                            attribute Cz : Real = 73.36857524151401;
                            attribute sigma_Cz : Real = 48.586903987386485;
                            attribute Ixx : Real = 816.3719651594015;
                            attribute sigma_Ixx : Real = 4672.575093725355;
                            attribute Iyy : Real = 1416.8520160842768;
                            attribute sigma_Iyy : Real = 8093.944013202667;
                            attribute Izz : Real = 647.2246323535072;
                            attribute sigma_Izz : Real = 3709.188146456086;
                            attribute Ixy : Real = -119.57975133950889;
                            attribute sigma_Ixy : Real = 715.0056935566982;
                            attribute Ixz : Real = 702.8095570387854;
                            attribute sigma_Ixz : Real = 4018.2030979760443;
                            attribute Iyz : Real = 134.80845197186923;
                            attribute sigma_Iyz : Real = 805.8319844527565;
                            part <'C.1.1.2.2.3.3.1'> 'Part 184' {
                                attribute POIconv : String = "-";
                                attribute Ipoint : Boolean = false;
                                attribute mass : Real = 0.04803869580011815;
                                attribute sigma_mass : Real = 0.28909372274994966;
                                attribute Cx : Real = 66.72488856129348;
                                attribute sigma_Cx : Real = 28.721044428837228;
                                attribute Cy : Real = -10.92528160661459;
                                attribute sigma_Cy : Real = 28.23690002309109;
                                attribute Cz : Real = -51.6026321798563;
                                attribute sigma_Cz : Real = 29.057750463592832;
                                attribute Ixx : Real = 0.06142990296864371;
                                attribute sigma_Ixx : Real = 0.37074144170588635;
                                attribute Iyy : Real = 0.06211455597531635;
                                attribute sigma_Iyy : Real = 0.3723953238821935;
                                attribute Izz : Real = 0.06698754323627717;
                                attribute sigma_Izz : Real = 0.37017423652493897;
                                attribute Ixy : Real = -0.0033889768570873873;
                                attribute sigma_Ixy : Real = 0.02351283871158888;
                                attribute Ixz : Real = 0.00012456251773068552;
                                attribute sigma_Ixz : Real = 0.022566176940390956;
                                attribute Iyz : Real = 0.002252160035002961;
                                attribute sigma_Iyz : Real = 0.02209918015384651;
                            }
                            part <'C.1.1.2.2.3.3.2'> 'Part 185' {
                                attribute POIconv : String = "-";
                                attribute Ipoint : Boolean = false;
                                attribute mass : Real = 0.8562299040998332;
                                attribute sigma_mass : Real = 0.28909372274994966;
                                attribute Cx : Real = -50.343500170856714;
                                attribute sigma_Cx : Real = 28.721044428837228;
                                attribute Cy : Real = -33.38116309605539;
                                attribute sigma_Cy : Real = 28.23690002309109;
                                attribute Cz : Real = 80.38007272407413;
                                attribute sigma_Cz : Real = 29.057750463592832;
                                attribute Ixx : Real = 1.0210523919141257;
                                attribute sigma_Ixx : Real = 0.37074144170588635;
                                attribute Iyy : Real = 1.0426604759076454;
                                attribute sigma_Iyy : Real = 0.3723953238821935;
                                attribute Izz : Real = 0.825067983737281;
                                attribute sigma_Izz : Real = 0.37017423652493897;
                                attribute Ixy : Real = 0.002357001642284754;
                                attribute sigma_Ixy : Real = 0.02351283871158888;
                                attribute Ixz : Real = -0.0052327181802938934;
                                attribute sigma_Ixz : Real = 0.022566176940390956;
                                attribute Iyz : Real = -0.0066476320400703625;
                                attribute sigma_Iyz : Real = 0.02209918015384651;
                            }
                        }
                        part <'C.1.1.2.2.3.4'> 'Subassembly 53' {
                            attribute POIconv : String = "-";
                            attribute Ipoint : Boolean = false;
                            attribute mass : Real = 1.494205376476748;
                            attribute sigma_mass : Real = 0.5007250159521434;
                            attribute Cx : Real = -35.55934921452879;
                            attribute sigma_Cx : Real = 23.231222705364043;
                            attribute Cy : Real = -15.856691270065312;
                            attribute sigma_Cy : Real = 21.911062116448857;
                            attribute Cz : Real = -31.255618875744435;
                            attribute sigma_Cz : Real = 19.75044298276489;
                            attribute Ixx : Real = 1858.7457656762022;
                            attribute sigma_Ixx : Real = 1955.2288813398304;
                            attribute Iyy : Real = 2292.080337531563;
                            attribute sigma_Iyy : Real = 2331.715257034724;
                            attribute Izz : Real = 3611.159299136013;
                            attribute sigma_Izz : Real = 3061.5713135796414;
                            attribute Ixy : Real = -1755.464983925602;
                            attribute sigma_Ixy : Real = 1509.4246195589092;
                            attribute Ixz : Real = 489.80184251025776;
                            attribute sigma_Ixz : Real = 1078.7063984792937;
                            attribute Iyz : Real = 328.0213651238119;
                            attribute sigma_Iyz : Real = 961.636048328705;
                            part <'C.1.1.2.2.3.4.1'> 'Part 186' {
                                attribute POIconv : String = "-";
                                attribute Ipoint : Boolean = false;
                                attribute mass : Real = 0.3002359834588133;
                                attribute sigma_mass : Real = 0.28909372274994966;
                                attribute Cx : Real = 25.597803201526403;
                                attribute sigma_Cx : Real = 28.721044428837228;
                                attribute Cy : Real = 30.103622004389763;
                                attribute sigma_Cy : Real = 28.23690002309109;
                                attribute Cz : Real = -57.109012082219124;
                                attribute sigma_Cz : Real = 29.057750463592832;
                                attribute Ixx : Real = 0.36829728687696506;
                                attribute sigma_Ixx : Real = 0.37074144170588635;
                                attribute Iyy : Real = 0.42310058052205446;
                                attribute sigma_Iyy : Real = 0.3723953238821935;
                                attribute Izz : Real = 0.35415201145191993;
                                attribute sigma_Izz : Real = 0.37017423652493897;
                                attribute Ixy : Real = 0.03080669356825065;
                                attribute sigma_Ixy : Real = 0.02351283871158888;
                                attribute Ixz : Real = -0.011446127957038359;
                                attribute sigma_Ixz : Real = 0.022566176940390956;
                                attribute Iyz : Real = -0.009596556081073104;
                                attribute sigma_Iyz : Real = 0.02209918015384651;
                            }
                            part <'C.1.1.2.2.3.4.2'> 'Part 187' {
                                attribute POIconv : String = "+";
                                attribute Ipoint : Boolean = false;
                                attribute mass : Real = 0.3281037449145224;
                                attribute sigma_mass : Real = 0.28909372274994966;
                                attribute Cx : Real = -14.040295174345374;
                                attribute sigma_Cx : Real = 28.721044428837228;
                                attribute Cy : Real = 14.488649740815163;
                                attribute sigma_Cy : Real = 28.23690002309109;
                                attribute Cz : Real = -18.506762851029634;
                                attribute sigma_Cz : Real = 29.057750463592832;
                                attribute Ixx : Real = 0.4284691494171979;
                                attribute sigma_Ixx : Real = 0.37074144170588635;
                                attribute Iyy : Real = 0.41935830629330473;
                                attribute sigma_Iyy : Real = 0.3723953238821935;
                                attribute Izz : Real = 0.392214819135819;
                                attribute sigma_Izz : Real = 0.37017423652493897;
                                attribute Ixy : Real = 0.006701085850058464;
                                attribute sigma_Ixy : Real = 0.02351283871158888;
                                attribute Ixz : Real = 0.016201924786676227;
                                attribute sigma_Ixz : Real = 0.022566176940390956;
                                attribute Iyz : Real = 0.023212845009562173;
                                attribute sigma_Iyz : Real = 0.02209918015384651;
                            }
                            part <'C.1.1.2.2.3.4.3'> 'Part 188' {
                                attribute POIconv : String = "+";
                                attribute Ipoint : Boolean = false;
                                attribute mass : Real = 0.8658656481034123;
                                attribute sigma_mass : Real = 0.28909372274994966;
                                attribute Cx : Real = -64.91963169537485;
                                attribute sigma_Cx : Real = 28.721044428837228;
                                attribute Cy : Real = -43.292079120874405;
                                attribute sigma_Cy : Real = 28.23690002309109;
                                attribute Cz : Real = -27.12198505178094;
                                attribute sigma_Cz : Real = 29.057750463592832;
                                attribute Ixx : Real = 1.077036074914798;
                                attribute sigma_Ixx : Real = 0.37074144170588635;
                                attribute Iyy : Real = 1.1624130034062254;
                                attribute sigma_Iyy : Real = 0.3723953238821935;
                                attribute Izz : Real = 1.0652868370570392;
                                attribute sigma_Izz : Real = 0.37017423652493897;
                                attribute Ixy : Real = -0.13159559804711357;
                                attribute sigma_Ixy : Real = 0.02351283871158888;
                                attribute Ixz : Real = -0.047983866772825394;
                                attribute sigma_Ixz : Real = 0.022566176940390956;
                                attribute Iyz : Real = -0.041762921962672866;
                                attribute sigma_Iyz : Real = 0.02209918015384651;
                            }
                        }
                        part <'C.1.1.2.2.3.5'> 'Subassembly 54' {
                            attribute POIconv : String = "-";
                            attribute Ipoint : Boolean = false;
                            attribute mass : Real = 0.5309458085251972;
                            attribute sigma_mass : Real = 0.40884026350990615;
                            attribute Cx : Real = -70.18111139502382;
                            attribute sigma_Cx : Real = 29.48269485701874;
                            attribute Cy : Real = -35.91138841172938;
                            attribute sigma_Cy : Real = 34.0023999068388;
                            attribute Cz : Real = 96.1270937732749;
                            attribute sigma_Cz : Real = 26.384238452898675;
                            attribute Ixx : Real = 100.22429417941565;
                            attribute sigma_Ixx : Real = 517.9992889658733;
                            attribute Iyy : Real = 39.32961740938295;
                            attribute sigma_Iyy : Real = 219.48104718476537;
                            attribute Izz : Real = 137.44658443859123;
                            attribute sigma_Izz : Real = 700.6255626957136;
                            attribute Ixy : Real = 61.28672242096492;
                            attribute sigma_Ixy : Real = 317.25722356883;
                            attribute Ixz : Real = -5.389284163481445;
                            attribute sigma_Ixz : Real = 61.81497108100646;
                            attribute Iyz : Real = 8.69353690229656;
                            attribute sigma_Iyz : Real = 99.26191670213635;
                            part <'C.1.1.2.2.3.5.1'> 'Part 189' {
                                attribute POIconv : String = "-";
                                attribute Ipoint : Boolean = false;
                                attribute mass : Real = 0.47780262160301207;
                                attribute sigma_mass : Real = 0.28909372274994966;
                                attribute Cx : Real = -73.00108168274164;
                                attribute sigma_Cx : Real = 28.721044428837228;
                                attribute Cy : Real = -31.360478466376662;
                                attribute sigma_Cy : Real = 28.23690002309109;
                                attribute Cz : Real = 95.72706767357886;
                                attribute sigma_Cz : Real = 29.057750463592832;
                                attribute Ixx : Real = 0.5265216427943255;
                                attribute sigma_Ixx : Real = 0.37074144170588635;
                                attribute Iyy : Real = 0.5261432335377831;
                                attribute sigma_Iyy : Real = 0.3723953238821935;
                                attribute Izz : Real = 0.5543274632164974;
                                attribute sigma_Izz : Real = 0.37017423652493897;
                                attribute Ixy : Real = 0.02960063515569681;
                                attribute sigma_Ixy : Real = 0.02351283871158888;
                                attribute Ixz : Real = -0.00012168005271508214;
                                attribute sigma_Ixz : Real = 0.022566176940390956;
                                attribute Iyz : Real = 0.00016350315055952514;
                                attribute sigma_Iyz : Real = 0.02209918015384651;
                            }
                            part <'C.1.1.2.2.3.5.2'> 'Part 190' {
                                attribute POIconv : String = "+";
                                attribute Ipoint : Boolean = false;
                                attribute mass : Real = 0.05314318692218512;
                                attribute sigma_mass : Real = 0.28909372274994966;
                                attribute Cx : Real = -44.827170949429274;
                                attribute sigma_Cx : Real = 28.721044428837228;
                                attribute Cy : Real = -76.82795417495072;
                                attribute sigma_Cy : Real = 28.23690002309109;
                                attribute Cz : Real = 99.72366993315518;
                                attribute sigma_Cz : Real = 29.057750463592832;
                                attribute Ixx : Real = 0.06773992825147897;
                                attribute sigma_Ixx : Real = 0.37074144170588635;
                                attribute Iyy : Real = 0.07836658136671154;
                                attribute sigma_Iyy : Real = 0.3723953238821935;
                                attribute Izz : Real = 0.06488608151294459;
                                attribute sigma_Izz : Real = 0.37017423652493897;
                                attribute Ixy : Real = 0.005263767600881721;
                                attribute sigma_Ixy : Real = 0.02351283871158888;
                                attribute Ixz : Real = 0.004183776910756587;
                                attribute sigma_Ixz : Real = 0.022566176940390956;
                                attribute Iyz : Real = -0.00301476035404252;
                                attribute sigma_Iyz : Real = 0.02209918015384651;
                            }
                        }
                    }
                }
                part <'C.1.1.2.3'> 'Subsystem 5' {
                    attribute POIconv : String = "-";
                    attribute Ipoint : Boolean = false;
                    attribute mass : Real = 31.66261834547459;
                    attribute sigma_mass : Real = 2.276326249260491;
                    attribute Cx : Real = 2.8282316487796813;
                    attribute sigma_Cx : Real = 6.520477815416599;
                    attribute Cy : Real = 3.5704264865922064;
                    attribute sigma_Cy : Real = 6.132595055852162;
                    attribute Cz : Real = 10.993853832967268;
                    attribute sigma_Cz : Real = 6.094760851232559;
                    attribute Ixx : Real = 207419.6511169976;
                    attribute sigma_Ixx : Real = 29275.009237210103;
                    attribute Iyy : Real = 237064.7470659124;
                    attribute sigma_Iyy : Real = 32486.824920143194;
                    attribute Izz : Real = 230720.11322500277;
                    attribute sigma_Izz : Real = 33804.398607566356;
                    attribute Ixy : Real = 16255.874990328333;
                    attribute sigma_Ixy : Real = 16373.733166274165;
                    attribute Ixz : Real = -17826.255321625347;
                    attribute sigma_Ixz : Real = 15058.245724625083;
                    attribute Iyz : Real = 2608.8610310662093;
                    attribute sigma_Iyz : Real = 13930.827914589068;
                    part <'C.1.1.2.3.1'> 'Assembly 15' {
                        attribute POIconv : String = "-";
                        attribute Ipoint : Boolean = false;
                        attribute mass : Real = 6.776666811689967;
                        attribute sigma_mass : Real = 1.2265207905297186;
                        attribute Cx : Real = 6.74761162547304;
                        attribute sigma_Cx : Real = 14.030995004288307;
                        attribute Cy : Real = 1.947211890432477;
                        attribute sigma_Cy : Real = 13.263995555054244;
                        attribute Cz : Real = 25.372945206962566;
                        attribute sigma_Cz : Real = 12.82923577877861;
                        attribute Ixx : Real = 28442.75301994515;
                        attribute sigma_Ixx : Real = 11510.289720531477;
                        attribute Iyy : Real = 33394.138525291215;
                        attribute sigma_Iyy : Real = 12844.808953536723;
                        attribute Izz : Real = 37770.27970316629;
                        attribute sigma_Izz : Real = 15512.206860273636;
                        attribute Ixy : Real = 825.0985040784553;
                        attribute sigma_Ixy : Real = 7560.209718628592;
                        attribute Ixz : Real = -2881.9617885173902;
                        attribute sigma_Ixz : Real = 5469.169368781902;
                        attribute Iyz : Real = -2051.2112366456363;
                        attribute sigma_Iyz : Real = 5386.78274279549;
                        part <'C.1.1.2.3.1.1'> 'Subassembly 55' {
                            attribute POIconv : String = "-";
                            attribute Ipoint : Boolean = false;
                            attribute mass : Real = 1.8335733300319408;
                            attribute sigma_mass : Real = 0.6464332159373649;
                            attribute Cx : Real = 51.0155304639657;
                            attribute sigma_Cx : Real = 16.983652330986057;
                            attribute Cy : Real = -19.231104361428457;
                            attribute sigma_Cy : Real = 16.768274644397497;
                            attribute Cz : Real = 26.700556443985498;
                            attribute sigma_Cz : Real = 25.696714687580553;
                            attribute Ixx : Real = 4963.66946390069;
                            attribute sigma_Ixx : Real = 4216.248678847564;
                            attribute Iyy : Real = 5157.750832302399;
                            attribute sigma_Iyy : Real = 4362.161126163971;
                            attribute Izz : Real = 2076.550264149479;
                            attribute sigma_Izz : Real = 1929.4976930416688;
                            attribute Ixy : Real = -701.0560722770974;
                            attribute sigma_Ixy : Real = 928.3089173636005;
                            attribute Ixz : Real = -466.4063588791215;
                            attribute sigma_Ixz : Real = 1561.7639992968263;
                            attribute Iyz : Real = 680.6757344731562;
                            attribute sigma_Iyz : Real = 1378.0745039551146;
                            part <'C.1.1.2.3.1.1.1'> 'Part 191' {
                                attribute POIconv : String = "-";
                                attribute Ipoint : Boolean = false;
                                attribute mass : Real = 0.2017568920047488;
                                attribute sigma_mass : Real = 0.28909372274994966;
                                attribute Cx : Real = 68.65355842746794;
                                attribute sigma_Cx : Real = 28.721044428837228;
                                attribute Cy : Real = 0.6748892366886139;
                                attribute sigma_Cy : Real = 28.23690002309109;
                                attribute Cz : Real = 67.41321492008865;
                                attribute sigma_Cz : Real = 29.057750463592832;
                                attribute Ixx : Real = 0.24496460754134886;
                                attribute sigma_Ixx : Real = 0.37074144170588635;
                                attribute Iyy : Real = 0.25679066894576086;
                                attribute sigma_Iyy : Real = 0.3723953238821935;
                                attribute Izz : Real = 0.19759319167786243;
                                attribute sigma_Izz : Real = 0.37017423652493897;
                                attribute Ixy : Real = -0.006378790443042046;
                                attribute sigma_Ixy : Real = 0.02351283871158888;
                                attribute Ixz : Real = -0.011015689262780133;
                                attribute sigma_Ixz : Real = 0.022566176940390956;
                                attribute Iyz : Real = 0.014957847660477037;
                                attribute sigma_Iyz : Real = 0.02209918015384651;
                            }
                            part <'C.1.1.2.3.1.1.2'> 'Part 192' {
                                attribute POIconv : String = "+";
                                attribute Ipoint : Boolean = false;
                                attribute mass : Real = 0.19057214169902728;
                                attribute sigma_mass : Real = 0.28909372274994966;
                                attribute Cx : Real = 62.64283275231719;
                                attribute sigma_Cx : Real = 28.721044428837228;
                                attribute Cy : Real = -57.9179001506418;
                                attribute sigma_Cy : Real = 28.23690002309109;
                                attribute Cz : Real = 96.48704556748271;
                                attribute sigma_Cz : Real = 29.057750463592832;
                                attribute Ixx : Real = 0.21287893065200106;
                                attribute sigma_Ixx : Real = 0.37074144170588635;
                                attribute Iyy : Real = 0.20975969055237606;
                                attribute sigma_Iyy : Real = 0.3723953238821935;
                                attribute Izz : Real = 0.2293773328263036;
                                attribute sigma_Izz : Real = 0.37017423652493897;
                                attribute Ixy : Real = -0.015535023367661199;
                                attribute sigma_Ixy : Real = 0.02351283871158888;
                                attribute Ixz : Real = -0.0036337337007628936;
                                attribute sigma_Ixz : Real = 0.022566176940390956;
                                attribute Iyz : Real = -0.0188370907797132;
                                attribute sigma_Iyz : Real = 0.02209918015384651;
                            }
                            part <'C.1.1.2.3.1.1.3'> 'Part 193' {
                                attribute POIconv : String = "-";
                                attribute Ipoint : Boolean = false;
                                attribute mass : Real = 0.5426606895879377;
                                attribute sigma_mass : Real = 0.28909372274994966;
                                attribute Cx : Real = 80.8619745541364;
                                attribute sigma_Cx : Real = 28.721044428837228;
                                attribute Cy : Real = 8.39486550539732;
                                attribute sigma_Cy : Real = 28.23690002309109;
                                attribute Cz : Real = 6.17535631172359;
                                attribute sigma_Cz : Real = 29.057750463592832;
                                attribute Ixx : Real = 0.8269090735238956;
                                attribute sigma_Ixx : Real = 0.37074144170588635;
                                attribute Iyy : Real = 0.7506516924279656;
                                attribute sigma_Iyy : Real = 0.3723953238821935;
                                attribute Izz : Real = 0.7343245518450107;
                                attribute sigma_Izz : Real = 0.37017423652493897;
                                attribute Ixy : Real = 0.07182772582190096;
                                attribute sigma_Ixy : Real = 0.02351283871158888;
                                attribute Ixz : Real = -0.05154987776560595;
                                attribute sigma_Ixz : Real = 0.022566176940390956;
                                attribute Iyz : Real = -0.024594550556900477;
                                attribute sigma_Iyz : Real = 0.02209918015384651;
                            }
                            part <'C.1.1.2.3.1.1.4'> 'Part 194' {
                                attribute POIconv : String = "-";
                                attribute Ipoint : Boolean = false;
                                attribute mass : Real = 0.2217793539171107;
                                attribute sigma_mass : Real = 0.28909372274994966;
                                attribute Cx : Real = 17.347895121201873;
                                attribute sigma_Cx : Real = 28.721044428837228;
                                attribute Cy : Real = -26.311938371509314;
                                attribute sigma_Cy : Real = 28.23690002309109;
                                attribute Cz : Real = -75.32026804983616;
                                attribute sigma_Cz : Real = 29.057750463592832;
                                attribute Ixx : Real = 0.2942299446199009;
                                attribute sigma_Ixx : Real = 0.37074144170588635;
                                attribute Iyy : Real = 0.31046253632181203;
                                attribute sigma_Iyy : Real = 0.3723953238821935;
                                attribute Izz : Real = 0.2813837037222907;
                                attribute sigma_Izz : Real = 0.37017423652493897;
                                attribute Ixy : Real = 0.006218850816250379;
                                attribute sigma_Ixy : Real = 0.02351283871158888;
                                attribute Ixz : Real = -0.02413819180300856;
                                attribute sigma_Ixz : Real = 0.022566176940390956;
                                attribute Iyz : Real = 0.012351308300200899;
                                attribute sigma_Iyz : Real = 0.02209918015384651;
                            }
                            part <'C.1.1.2.3.1.1.5'> 'Part 195' {
                                attribute POIconv : String = "+";
                                attribute Ipoint : Boolean = false;
                                attribute mass : Real = 0.6768042528231163;
                                attribute sigma_mass : Real = 0.28909372274994966;
                                attribute Cx : Real = 29.585199523717165;
                                attribute sigma_Cx : Real = 28.721044428837228;
                                attribute Cy : Real = -34.10200816579163;
                                attribute sigma_Cy : Real = 28.23690002309109;
                                attribute Cz : Real = 44.80167152360082;
                                attribute sigma_Cz : Real = 29.057750463592832;
                                attribute Ixx : Real = 0.7392883402225693;
                                attribute sigma_Ixx : Real = 0.37074144170588635;
                                attribute Iyy : Real = 0.8312327009620615;
                                attribute sigma_Iyy : Real = 0.3723953238821935;
                                attribute Izz : Real = 0.8362273992383054;
                                attribute sigma_Izz : Real = 0.37017423652493897;
                                attribute Ixy : Real = 0.02514644397238257;
                                attribute sigma_Ixy : Real = 0.02351283871158888;
                                attribute Ixz : Real = 0.01741511537849129;
                                attribute sigma_Ixz : Real = 0.022566176940390956;
                                attribute Iyz : Real = 0.020945190167058127;
                                attribute sigma_Iyz : Real = 0.02209918015384651;
                            }
                        }
                        part <'C.1.1.2.3.1.2'> 'Subassembly 56' {
                            attribute POIconv : String = "-";
                            attribute Ipoint : Boolean = false;
                            attribute mass : Real = 0.4758445786868688;
                            attribute sigma_mass : Real = 0.40884026350990615;
                            attribute Cx : Real = -11.475700010882365;
                            attribute sigma_Cx : Real = 36.171236357576724;
                            attribute Cy : Real = -12.332447809426109;
                            attribute sigma_Cy : Real = 27.397537516654843;
                            attribute Cz : Real = -7.733425097060875;
                            attribute sigma_Cz : Real = 35.014325977393106;
                            attribute Ixx : Real = 52.95511802744218;
                            attribute sigma_Ixx : Real = 438.8901968485617;
                            attribute Iyy : Real = 104.09391104494843;
                            attribute sigma_Iyy : Real = 854.6105464684498;
                            attribute Izz : Real = 62.405016266326946;
                            attribute sigma_Izz : Real = 516.0047311221656;
                            attribute Ixy : Real = 17.488581181742173;
                            attribute sigma_Ixy : Real = 152.55546855440272;
                            attribute Ixz : Real = -51.56122222328342;
                            attribute sigma_Ixz : Real = 425.5652885421578;
                            attribute Iyz : Real = 15.972318034295798;
                            attribute sigma_Iyz : Real = 139.32171536072835;
                            part <'C.1.1.2.3.1.2.1'> 'Part 196' {
                                attribute POIconv : String = "+";
                                attribute Ipoint : Boolean = false;
                                attribute mass : Real = 0.03308807502221316;
                                attribute sigma_mass : Real = 0.28909372274994966;
                                attribute Cx : Real = 28.40084624476731;
                                attribute sigma_Cx : Real = 28.721044428837228;
                                attribute Cy : Real = -24.667787086218596;
                                attribute sigma_Cy : Real = 28.23690002309109;
                                attribute Cz : Real = 28.634455800056458;
                                attribute sigma_Cz : Real = 29.057750463592832;
                                attribute Ixx : Real = 0.03507778863209477;
                                attribute sigma_Ixx : Real = 0.37074144170588635;
                                attribute Iyy : Real = 0.039794912554532526;
                                attribute sigma_Iyy : Real = 0.3723953238821935;
                                attribute Izz : Real = 0.041501837097676686;
                                attribute sigma_Izz : Real = 0.37017423652493897;
                                attribute Ixy : Real = 0.0005716764811712153;
                                attribute sigma_Ixy : Real = 0.02351283871158888;
                                attribute Ixz : Real = 0.00010225247334140415;
                                attribute sigma_Ixz : Real = 0.022566176940390956;
                                attribute Iyz : Real = -7.3559638454395216e-06;
                                attribute sigma_Iyz : Real = 0.02209918015384651;
                            }
                            part <'C.1.1.2.3.1.2.2'> 'Part 197' {
                                attribute POIconv : String = "+";
                                attribute Ipoint : Boolean = false;
                                attribute mass : Real = 0.44275650366465563;
                                attribute sigma_mass : Real = 0.28909372274994966;
                                attribute Cx : Real = -14.455753704532981;
                                attribute sigma_Cx : Real = 28.721044428837228;
                                attribute Cy : Real = -11.410603346303105;
                                attribute sigma_Cy : Real = 28.23690002309109;
                                attribute Cz : Real = -10.451269242912531;
                                attribute sigma_Cz : Real = 29.057750463592832;
                                attribute Ixx : Real = 0.47554547574018785;
                                attribute sigma_Ixx : Real = 0.37074144170588635;
                                attribute Iyy : Real = 0.4739426683714093;
                                attribute sigma_Iyy : Real = 0.3723953238821935;
                                attribute Izz : Real = 0.4059268710803595;
                                attribute sigma_Izz : Real = 0.37017423652493897;
                                attribute Ixy : Real = 0.0028811845819153334;
                                attribute sigma_Ixy : Real = 0.02351283871158888;
                                attribute Ixz : Real = -0.010076932861846102;
                                attribute sigma_Ixz : Real = 0.022566176940390956;
                                attribute Iyz : Real = -0.019369151282463012;
                                attribute sigma_Iyz : Real = 0.02209918015384651;
                            }
                        }
                        part <'C.1.1.2.3.1.3'> 'Subassembly 57' {
                            attribute POIconv : String = "-";
                            attribute Ipoint : Boolean = false;
                            attribute mass : Real = 1.7888333261816296;
                            attribute sigma_mass : Real = 0.5781874454998993;
                            attribute Cx : Real = 12.968423249419613;
                            attribute sigma_Cx : Real = 29.3668440595873;
                            attribute Cy : Real = -2.293724204044972;
                            attribute sigma_Cy : Real = 21.85549715473876;
                            attribute Cz : Real = 48.280948353314294;
                            attribute sigma_Cz : Real = 18.49091465937132;
                            attribute Ixx : Real = 2627.6275206518503;
                            attribute sigma_Ixx : Real = 3327.97571419892;
                            attribute Iyy : Real = 10789.920491014314;
                            attribute sigma_Iyy : Real = 5836.2880377426645;
                            attribute Izz : Real = 12447.144645575421;
                            attribute sigma_Izz : Real = 6771.023787833425;
                            attribute Ixy : Real = 2172.525024890039;
                            attribute sigma_Ixy : Real = 3102.4469518847804;
                            attribute Ixz : Real = 738.2223824431431;
                            attribute sigma_Ixz : Real = 2531.2471789423994;
                            attribute Iyz : Real = 478.6911540863925;
                            attribute sigma_Iyz : Real = 1547.9702939350182;
                            part <'C.1.1.2.3.1.3.1'> 'Part 198' {
                                attribute POIconv : String = "+";
                                attribute Ipoint : Boolean = false;
                                attribute mass : Real = 0.5433124298229813;
                                attribute sigma_mass : Real = 0.28909372274994966;
                                attribute Cx : Real = 91.01874330081046;
                                attribute sigma_Cx : Real = 28.721044428837228;
                                attribute Cy : Real = -27.00051823630929;
                                attribute sigma_Cy : Real = 28.23690002309109;
                                attribute Cz : Real = 34.61931757628918;
                                attribute sigma_Cz : Real = 29.057750463592832;
                                attribute Ixx : Real = 0.7382956422295451;
                                attribute sigma_Ixx : Real = 0.37074144170588635;
                                attribute Iyy : Real = 0.7107770884193192;
                                attribute sigma_Iyy : Real = 0.3723953238821935;
                                attribute Izz : Real = 0.8113776701219594;
                                attribute sigma_Izz : Real = 0.37017423652493897;
                                attribute Ixy : Real = 0.01318499833317646;
                                attribute sigma_Ixy : Real = 0.02351283871158888;
                                attribute Ixz : Real = -0.02182231900762043;
                                attribute sigma_Ixz : Real = 0.022566176940390956;
                                attribute Iyz : Real = -0.006105077178933551;
                                attribute sigma_Iyz : Real = 0.02209918015384651;
                            }
                            part <'C.1.1.2.3.1.3.2'> 'Part 199' {
                                attribute POIconv : String = "+";
                                attribute Ipoint : Boolean = false;
                                attribute mass : Real = 0.34429813690832817;
                                attribute sigma_mass : Real = 0.28909372274994966;
                                attribute Cx : Real = 86.92097919993103;
                                attribute sigma_Cx : Real = 28.721044428837228;
                                attribute Cy : Real = -4.746119165793061;
                                attribute sigma_Cy : Real = 28.23690002309109;
                                attribute Cz : Real = 56.174975261092186;
                                attribute sigma_Cz : Real = 29.057750463592832;
                                attribute Ixx : Real = 0.41979101797520396;
                                attribute sigma_Ixx : Real = 0.37074144170588635;
                                attribute Iyy : Real = 0.3710750195989728;
                                attribute sigma_Iyy : Real = 0.3723953238821935;
                                attribute Izz : Real = 0.41846541440958507;
                                attribute sigma_Izz : Real = 0.37017423652493897;
                                attribute Ixy : Real = -0.036823989763189055;
                                attribute sigma_Ixy : Real = 0.02351283871158888;
                                attribute Ixz : Real = -0.007268370627463555;
                                attribute sigma_Ixz : Real = 0.022566176940390956;
                                attribute Iyz : Real = 0.015092720033780762;
                                attribute sigma_Iyz : Real = 0.02209918015384651;
                            }
                            part <'C.1.1.2.3.1.3.3'> 'Part 200' {
                                attribute POIconv : String = "-";
                                attribute Ipoint : Boolean = false;
                                attribute mass : Real = 0.7634404668330681;
                                attribute sigma_mass : Real = 0.28909372274994966;
                                attribute Cx : Real = -62.20163619145751;
                                attribute sigma_Cx : Real = 28.721044428837228;
                                attribute Cy : Real = 31.335248751565814;
                                attribute sigma_Cy : Real = 28.23690002309109;
                                attribute Cz : Real = 45.288399839773774;
                                attribute sigma_Cz : Real = 29.057750463592832;
                                attribute Ixx : Real = 0.7506995817795064;
                                attribute sigma_Ixx : Real = 0.37074144170588635;
                                attribute Iyy : Real = 0.7634941794798735;
                                attribute sigma_Iyy : Real = 0.3723953238821935;
                                attribute Izz : Real = 0.7933615100188953;
                                attribute sigma_Izz : Real = 0.37017423652493897;
                                attribute Ixy : Real = -0.022147348672817348;
                                attribute sigma_Ixy : Real = 0.02351283871158888;
                                attribute Ixz : Real = -0.002487193942590132;
                                attribute sigma_Ixz : Real = 0.022566176940390956;
                                attribute Iyz : Real = -0.005297538129773369;
                                attribute sigma_Iyz : Real = 0.02209918015384651;
                            }
                            part <'C.1.1.2.3.1.3.4'> 'Part 201' {
                                attribute POIconv : String = "-";
                                attribute Ipoint : Boolean = false;
                                attribute mass : Real = 0.13778229261725208;
                                attribute sigma_mass : Real = 0.28909372274994966;
                                attribute Cx : Real = -63.09048677794635;
                                attribute sigma_Cx : Real = 28.721044428837228;
                                attribute Cy : Real = -85.07544659078121;
                                attribute sigma_Cy : Real = 28.23690002309109;
                                attribute Cz : Real = 99.00784189812839;
                                attribute sigma_Cz : Real = 29.057750463592832;
                                attribute Ixx : Real = 0.17923436663313697;
                                attribute sigma_Ixx : Real = 0.37074144170588635;
                                attribute Iyy : Real = 0.18238904714735232;
                                attribute sigma_Iyy : Real = 0.3723953238821935;
                                attribute Izz : Real = 0.16877397682766557;
                                attribute sigma_Izz : Real = 0.37017423652493897;
                                attribute Ixy : Real = -0.005829413648427368;
                                attribute sigma_Ixy : Real = 0.02351283871158888;
                                attribute Ixz : Real = 8.768979596522473e-05;
                                attribute sigma_Ixz : Real = 0.022566176940390956;
                                attribute Iyz : Real = 0.013625494200226625;
                                attribute sigma_Iyz : Real = 0.02209918015384651;
                            }
                        }
                        part <'C.1.1.2.3.1.4'> 'Subassembly 58' {
                            attribute POIconv : String = "-";
                            attribute Ipoint : Boolean = false;
                            attribute mass : Real = 1.6173462128080427;
                            attribute sigma_mass : Real = 0.6464332159373649;
                            attribute Cx : Real = -10.557037037415144;
                            attribute sigma_Cx : Real = 20.930653943215866;
                            attribute Cy : Real = 71.75978411426344;
                            attribute sigma_Cy : Real = 16.117671225854526;
                            attribute Cz : Real = 33.791283551783934;
                            attribute sigma_Cz : Real = 29.677024155031877;
                            attribute Ixx : Real = 4216.068012814219;
                            attribute sigma_Ixx : Real = 4027.413795941917;
                            attribute Iyy : Real = 5370.74007375043;
                            attribute sigma_Iyy : Real = 4664.47056869793;
                            attribute Izz : Real = 1329.2151109957513;
                            attribute sigma_Izz : Real = 1996.800180042284;
                            attribute Ixy : Real = 76.10582741347602;
                            attribute sigma_Ixy : Real = 796.353409678726;
                            attribute Ixz : Real = -1004.5042609064652;
                            attribute sigma_Ixz : Real = 1724.866115830078;
                            attribute Iyz : Real = -368.51344887360125;
                            attribute sigma_Iyz : Real = 1202.543519352261;
                            part <'C.1.1.2.3.1.4.1'> 'Part 202' {
                                attribute POIconv : String = "+";
                                attribute Ipoint : Boolean = false;
                                attribute mass : Real = 0.07755370915262029;
                                attribute sigma_mass : Real = 0.28909372274994966;
                                attribute Cx : Real = -5.862633092328906;
                                attribute sigma_Cx : Real = 28.721044428837228;
                                attribute Cy : Real = 72.41359152831137;
                                attribute sigma_Cy : Real = 28.23690002309109;
                                attribute Cz : Real = -66.02655639871955;
                                attribute sigma_Cz : Real = 29.057750463592832;
                                attribute Ixx : Real = 0.10696283434151345;
                                attribute sigma_Ixx : Real = 0.37074144170588635;
                                attribute Iyy : Real = 0.11241554872105647;
                                attribute sigma_Iyy : Real = 0.3723953238821935;
                                attribute Izz : Real = 0.10620296057443154;
                                attribute sigma_Izz : Real = 0.37017423652493897;
                                attribute Ixy : Real = -0.007846729545288353;
                                attribute sigma_Ixy : Real = 0.02351283871158888;
                                attribute Ixz : Real = -0.005205180699407828;
                                attribute sigma_Ixz : Real = 0.022566176940390956;
                                attribute Iyz : Real = -0.007361154328928053;
                                attribute sigma_Iyz : Real = 0.02209918015384651;
                            }
                            part <'C.1.1.2.3.1.4.2'> 'Part 203' {
                                attribute POIconv : String = "-";
                                attribute Ipoint : Boolean = false;
                                attribute mass : Real = 0.10513522690092214;
                                attribute sigma_mass : Real = 0.28909372274994966;
                                attribute Cx : Real = 57.00324783101678;
                                attribute sigma_Cx : Real = 28.721044428837228;
                                attribute Cy : Real = 47.535066306591034;
                                attribute sigma_Cy : Real = 28.23690002309109;
                                attribute Cz : Real = -16.182217560708523;
                                attribute sigma_Cz : Real = 29.057750463592832;
                                attribute Ixx : Real = 0.13551568426536068;
                                attribute sigma_Ixx : Real = 0.37074144170588635;
                                attribute Iyy : Real = 0.13368519737671267;
                                attribute sigma_Iyy : Real = 0.3723953238821935;
                                attribute Izz : Real = 0.11999905947091685;
                                attribute sigma_Izz : Real = 0.37017423652493897;
                                attribute Ixy : Real = -0.004373116928128338;
                                attribute sigma_Ixy : Real = 0.02351283871158888;
                                attribute Ixz : Real = -0.008104542666268142;
                                attribute sigma_Ixz : Real = 0.022566176940390956;
                                attribute Iyz : Real = -0.004497123293024494;
                                attribute sigma_Iyz : Real = 0.02209918015384651;
                            }
                            part <'C.1.1.2.3.1.4.3'> 'Part 204' {
                                attribute POIconv : String = "+";
                                attribute Ipoint : Boolean = false;
                                attribute mass : Real = 0.25733619152544995;
                                attribute sigma_mass : Real = 0.28909372274994966;
                                attribute Cx : Real = 7.374726561829448;
                                attribute sigma_Cx : Real = 28.721044428837228;
                                attribute Cy : Real = 80.04060229286551;
                                attribute sigma_Cy : Real = 28.23690002309109;
                                attribute Cz : Real = 92.05705286003649;
                                attribute sigma_Cz : Real = 29.057750463592832;
                                attribute Ixx : Real = 0.2771713747403308;
                                attribute sigma_Ixx : Real = 0.37074144170588635;
                                attribute Iyy : Real = 0.33526471192253005;
                                attribute sigma_Iyy : Real = 0.3723953238821935;
                                attribute Izz : Real = 0.34104150255091464;
                                attribute sigma_Izz : Real = 0.37017423652493897;
                                attribute Ixy : Real = -0.025175789319774364;
                                attribute sigma_Ixy : Real = 0.02351283871158888;
                                attribute Ixz : Real = -0.015170073867423271;
                                attribute sigma_Ixz : Real = 0.022566176940390956;
                                attribute Iyz : Real = 0.005649570345318704;
                                attribute sigma_Iyz : Real = 0.02209918015384651;
                            }
                            part <'C.1.1.2.3.1.4.4'> 'Part 205' {
                                attribute POIconv : String = "-";
                                attribute Ipoint : Boolean = false;
                                attribute mass : Real = 0.6430239959149622;
                                attribute sigma_mass : Real = 0.28909372274994966;
                                attribute Cx : Real = -40.56690093129873;
                                attribute sigma_Cx : Real = 28.721044428837228;
                                attribute Cy : Real = 69.87919686362147;
                                attribute sigma_Cy : Real = 28.23690002309109;
                                attribute Cz : Real = -7.449634652584791;
                                attribute sigma_Cz : Real = 29.057750463592832;
                                attribute Ixx : Real = 0.7825312164095768;
                                attribute sigma_Ixx : Real = 0.37074144170588635;
                                attribute Iyy : Real = 0.7553746232066285;
                                attribute sigma_Iyy : Real = 0.3723953238821935;
                                attribute Izz : Real = 0.8028865719582547;
                                attribute sigma_Izz : Real = 0.37017423652493897;
                                attribute Ixy : Real = -0.011248901337559134;
                                attribute sigma_Ixy : Real = 0.02351283871158888;
                                attribute Ixz : Real = 0.009332727233953871;
                                attribute sigma_Ixz : Real = 0.022566176940390956;
                                attribute Iyz : Real = -0.020336001319640418;
                                attribute sigma_Iyz : Real = 0.02209918015384651;
                            }
                            part <'C.1.1.2.3.1.4.5'> 'Part 206' {
                                attribute POIconv : String = "-";
                                attribute Ipoint : Boolean = false;
                                attribute mass : Real = 0.5342970893140883;
                                attribute sigma_mass : Real = 0.28909372274994966;
                                attribute Cx : Real = 2.947690337896347;
                                attribute sigma_Cx : Real = 28.721044428837228;
                                attribute Cy : Real = 74.7065988369286;
                                attribute sigma_Cy : Real = 28.23690002309109;
                                attribute Cz : Real = 79.68378127552569;
                                attribute sigma_Cz : Real = 29.057750463592832;
                                attribute Ixx : Real = 0.6129229295080617;
                                attribute sigma_Ixx : Real = 0.37074144170588635;
                                attribute Iyy : Real = 0.6611321472380082;
                                attribute sigma_Iyy : Real = 0.3723953238821935;
                                attribute Izz : Real = 0.6752065583022;
                                attribute sigma_Izz : Real = 0.37017423652493897;
                                attribute Ixy : Real = 0.02353989303576627;
                                attribute sigma_Ixy : Real = 0.02351283871158888;
                                attribute Ixz : Real = 0.008023090549977647;
                                attribute sigma_Ixz : Real = 0.022566176940390956;
                                attribute Iyz : Real = 0.013821623675489572;
                                attribute sigma_Iyz : Real = 0.02209918015384651;
                            }
                        }
                        part <'C.1.1.2.3.1.5'> 'Subassembly 59' {
                            attribute POIconv : String = "-";
                            attribute Ipoint : Boolean = false;
                            attribute mass : Real = 1.0610693639814854;
                            attribute sigma_mass : Real = 0.40884026350990615;
                            attribute Cx : Real = -45.68760172527842;
                            attribute sigma_Cx : Real = 46.143208609872886;
                            attribute Cy : Real = -54.31478095471155;
                            attribute sigma_Cy : Real = 41.75451706999472;
                            attribute Cz : Real = -13.526258024587756;
                            attribute sigma_Cz : Real = 30.114863091445322;
                            attribute Ixx : Real = 1205.8146509738096;
                            attribute sigma_Ixx : Real = 4740.530426181194;
                            attribute Iyy : Real = 1565.867010077599;
                            attribute sigma_Iyy : Real = 6143.338251610888;
                            attribute Izz : Real = 2439.9485892017537;
                            attribute sigma_Izz : Real = 9544.498766361468;
                            attribute Ixy : Real = -1205.9600467081982;
                            attribute sigma_Ixy : Real = 4720.405794346563;
                            attribute Ixz : Real = 480.6900160867613;
                            attribute sigma_Ixz : Real = 1915.8806557178195;
                            attribute Iyz : Real = 414.2997062846399;
                            attribute sigma_Iyz : Real = 1652.3050804727486;
                            part <'C.1.1.2.3.1.5.1'> 'Part 207' {
                                attribute POIconv : String = "+";
                                attribute Ipoint : Boolean = false;
                                attribute mass : Real = 0.9916431890237145;
                                attribute sigma_mass : Real = 0.28909372274994966;
                                attribute Cx : Real = -55.29658221639693;
                                attribute sigma_Cx : Real = 28.721044428837228;
                                attribute Cy : Real = -62.59580650366843;
                                attribute sigma_Cy : Real = 28.23690002309109;
                                attribute Cz : Real = -10.22542673163116;
                                attribute sigma_Cz : Real = 29.057750463592832;
                                attribute Ixx : Real = 1.3052119954712176;
                                attribute sigma_Ixx : Real = 0.37074144170588635;
                                attribute Iyy : Real = 1.298355961276188;
                                attribute sigma_Iyy : Real = 0.3723953238821935;
                                attribute Izz : Real = 1.1960568089899328;
                                attribute sigma_Izz : Real = 0.37017423652493897;
                                attribute Ixy : Real = -0.0026266695130579085;
                                attribute sigma_Ixy : Real = 0.02351283871158888;
                                attribute Ixz : Real = 0.010798719757647375;
                                attribute sigma_Ixz : Real = 0.022566176940390956;
                                attribute Iyz : Real = -0.02861200530929836;
                                attribute sigma_Iyz : Real = 0.02209918015384651;
                            }
                            part <'C.1.1.2.3.1.5.2'> 'Part 208' {
                                attribute POIconv : String = "-";
                                attribute Ipoint : Boolean = false;
                                attribute mass : Real = 0.06942617495777086;
                                attribute sigma_mass : Real = 0.28909372274994966;
                                attribute Cx : Real = 91.56149867922068;
                                attribute sigma_Cx : Real = 28.721044428837228;
                                attribute Cy : Real = 63.96658178418875;
                                attribute sigma_Cy : Real = 28.23690002309109;
                                attribute Cz : Real = -60.67341645248234;
                                attribute sigma_Cz : Real = 29.057750463592832;
                                attribute Ixx : Real = 0.07283614190677053;
                                attribute sigma_Ixx : Real = 0.37074144170588635;
                                attribute Iyy : Real = 0.0762629662462501;
                                attribute sigma_Iyy : Real = 0.3723953238821935;
                                attribute Izz : Real = 0.08098728686827261;
                                attribute sigma_Izz : Real = 0.37017423652493897;
                                attribute Ixy : Real = 0.00983192775955202;
                                attribute sigma_Ixy : Real = 0.02351283871158888;
                                attribute Ixz : Real = -0.0019387864821624144;
                                attribute sigma_Ixz : Real = 0.022566176940390956;
                                attribute Iyz : Real = 0.001152984632487434;
                                attribute sigma_Iyz : Real = 0.02209918015384651;
                            }
                        }
                    }
                    part <'C.1.1.2.3.2'> 'Assembly 16' {
                        attribute POIconv : String = "-";
                        attribute Ipoint : Boolean = false;
                        attribute mass : Real = 6.757135045843199;
                        attribute sigma_mass : Real = 1.0423422407897138;
                        attribute Cx : Real = -16.034816069792864;
                        attribute sigma_Cx : Real = 15.069512099850096;
                        attribute Cy : Real = 9.78767629717178;
                        attribute sigma_Cy : Real = 13.890880191212926;
                        attribute Cz : Real = 11.391061685281509;
                        attribute sigma_Cz : Real = 12.682932964480521;
                        attribute Ixx : Real = 39324.968400801285;
                        attribute sigma_Ixx : Real = 12978.672558969642;
                        attribute Iyy : Real = 48078.366291498314;
                        attribute sigma_Iyy : Real = 14966.387333303153;
                        attribute Izz : Real = 53370.530647982094;
                        attribute sigma_Izz : Real = 18352.72100212791;
                        attribute Ixy : Real = 5545.653112032111;
                        attribute sigma_Ixy : Real = 8974.172301783292;
                        attribute Ixz : Real = -4883.688821454109;
                        attribute sigma_Ixz : Real = 6700.7905155570115;
                        attribute Iyz : Real = -1167.5972313075702;
                        attribute sigma_Iyz : Real = 6196.705718736;
                        part <'C.1.1.2.3.2.1'> 'Subassembly 60' {
                            attribute POIconv : String = "-";
                            attribute Ipoint : Boolean = false;
                            attribute mass : Real = 0.8363523058644495;
                            attribute sigma_mass : Real = 0.40884026350990615;
                            attribute Cx : Real = 16.711763770757898;
                            attribute sigma_Cx : Real = 35.35991551973585;
                            attribute Cy : Real = -38.350562027554005;
                            attribute sigma_Cy : Real = 35.69353256673558;
                            attribute Cz : Real = -54.16554467799582;
                            attribute sigma_Cz : Real = 26.300596460720904;
                            attribute Ixx : Real = 1045.0300088923125;
                            attribute sigma_Ixx : Real = 2016.3672857796332;
                            attribute Iyy : Real = 986.4253667855937;
                            attribute sigma_Iyy : Real = 1920.0251102375337;
                            attribute Izz : Real = 1812.7545220557824;
                            attribute sigma_Izz : Real = 3356.8079774647376;
                            attribute Ixy : Real = -905.3765769084481;
                            attribute sigma_Ixy : Real = 1677.7456022979027;
                            attribute Ixz : Real = 308.99644886374415;
                            attribute sigma_Ixz : Real = 693.0428497878536;
                            attribute Iyz : Real = 319.03576471544886;
                            attribute sigma_Iyz : Real = 714.340963381971;
                            part <'C.1.1.2.3.2.1.1'> 'Part 209' {
                                attribute POIconv : String = "+";
                                attribute Ipoint : Boolean = false;
                                attribute mass : Real = 0.13887204244593157;
                                attribute sigma_mass : Real = 0.28909372274994966;
                                attribute Cx : Real = 89.26507718861103;
                                attribute sigma_Cx : Real = 28.721044428837228;
                                attribute Cy : Real = 36.58494339324534;
                                attribute sigma_Cy : Real = 28.23690002309109;
                                attribute Cz : Real = -79.73456969484687;
                                attribute sigma_Cz : Real = 29.057750463592832;
                                attribute Ixx : Real = 0.14514116367016228;
                                attribute sigma_Ixx : Real = 0.37074144170588635;
                                attribute Iyy : Real = 0.14596382733371122;
                                attribute sigma_Iyy : Real = 0.3723953238821935;
                                attribute Izz : Real = 0.14465895499196033;
                                attribute sigma_Izz : Real = 0.37017423652493897;
                                attribute Ixy : Real = 0.005346107723156964;
                                attribute sigma_Ixy : Real = 0.02351283871158888;
                                attribute Ixz : Real = 0.0015761853435010964;
                                attribute sigma_Ixz : Real = 0.022566176940390956;
                                attribute Iyz : Real = -0.0037011263911777134;
                                attribute sigma_Iyz : Real = 0.02209918015384651;
                            }
                            part <'C.1.1.2.3.2.1.2'> 'Part 210' {
                                attribute POIconv : String = "+";
                                attribute Ipoint : Boolean = false;
                                attribute mass : Real = 0.697480263418518;
                                attribute sigma_mass : Real = 0.28909372274994966;
                                attribute Cx : Real = 2.2660118993371725;
                                attribute sigma_Cx : Real = 28.721044428837228;
                                attribute Cy : Real = -53.27062103897333;
                                attribute sigma_Cy : Real = 28.23690002309109;
                                attribute Cz : Real = -49.074615351855755;
                                attribute sigma_Cz : Real = 29.057750463592832;
                                attribute Ixx : Real = 0.9396640060114518;
                                attribute sigma_Ixx : Real = 0.37074144170588635;
                                attribute Iyy : Real = 0.8412246628530119;
                                attribute sigma_Iyy : Real = 0.3723953238821935;
                                attribute Izz : Real = 0.962606489559149;
                                attribute sigma_Izz : Real = 0.37017423652493897;
                                attribute Ixy : Real = 0.020095831167865057;
                                attribute sigma_Ixy : Real = 0.02351283871158888;
                                attribute Ixz : Real = -0.07976675379093173;
                                attribute sigma_Ixz : Real = 0.022566176940390956;
                                attribute Iyz : Real = 0.029116783923820194;
                                attribute sigma_Iyz : Real = 0.02209918015384651;
                            }
                        }
                        part <'C.1.1.2.3.2.2'> 'Subassembly 61' {
                            attribute POIconv : String = "-";
                            attribute Ipoint : Boolean = false;
                            attribute mass : Real = 1.0292410368828568;
                            attribute sigma_mass : Real = 0.5007250159521434;
                            attribute Cx : Real = -66.3170520466184;
                            attribute sigma_Cx : Real = 45.49885973160002;
                            attribute Cy : Real = 39.48233516073526;
                            attribute sigma_Cy : Real = 47.714946997765374;
                            attribute Cz : Real = -39.81876401287083;
                            attribute sigma_Cz : Real = 24.81159119520951;
                            attribute Ixx : Real = 3653.465265632309;
                            attribute sigma_Ixx : Real = 6186.749473165555;
                            attribute Iyy : Real = 3393.0004239507853;
                            attribute sigma_Iyy : Real = 5937.602354052878;
                            attribute Izz : Real = 6548.1097795433725;
                            attribute sigma_Izz : Real = 11163.784557079158;
                            attribute Ixy : Real = 3234.5557134885366;
                            attribute sigma_Ixy : Real = 5571.357854211041;
                            attribute Ixz : Real = -801.0962487262585;
                            attribute sigma_Ixz : Real = 1614.1327675760122;
                            attribute Iyz : Real = 766.5691463938646;
                            attribute sigma_Iyz : Real = 1634.2719499258787;
                            part <'C.1.1.2.3.2.2.1'> 'Part 211' {
                                attribute POIconv : String = "+";
                                attribute Ipoint : Boolean = false;
                                attribute mass : Real = 0.7717454422237352;
                                attribute sigma_mass : Real = 0.28909372274994966;
                                attribute Cx : Real = -87.09769323468208;
                                attribute sigma_Cx : Real = 28.721044428837228;
                                attribute Cy : Real = 57.12637607939541;
                                attribute sigma_Cy : Real = 28.23690002309109;
                                attribute Cz : Real = -47.994602378457785;
                                attribute sigma_Cz : Real = 29.057750463592832;
                                attribute Ixx : Real = 1.021487361083056;
                                attribute sigma_Ixx : Real = 0.37074144170588635;
                                attribute Iyy : Real = 1.0702934663447334;
                                attribute sigma_Iyy : Real = 0.3723953238821935;
                                attribute Izz : Real = 1.1697831672251717;
                                attribute sigma_Izz : Real = 0.37017423652493897;
                                attribute Ixy : Real = -0.04207693301034161;
                                attribute sigma_Ixy : Real = 0.02351283871158888;
                                attribute Ixz : Real = 0.04459838752703561;
                                attribute sigma_Ixz : Real = 0.022566176940390956;
                                attribute Iyz : Real = 0.10953832114419812;
                                attribute sigma_Iyz : Real = 0.02209918015384651;
                            }
                            part <'C.1.1.2.3.2.2.2'> 'Part 212' {
                                attribute POIconv : String = "+";
                                attribute Ipoint : Boolean = false;
                                attribute mass : Real = 0.11227221190836281;
                                attribute sigma_mass : Real = 0.28909372274994966;
                                attribute Cx : Real = -99.41370082087815;
                                attribute sigma_Cx : Real = 28.721044428837228;
                                attribute Cy : Real = 97.38592957146466;
                                attribute sigma_Cy : Real = 28.23690002309109;
                                attribute Cz : Real = -29.90108672529459;
                                attribute sigma_Cz : Real = 29.057750463592832;
                                attribute Ixx : Real = 0.15903547245720948;
                                attribute sigma_Ixx : Real = 0.37074144170588635;
                                attribute Iyy : Real = 0.14521923226222264;
                                attribute sigma_Iyy : Real = 0.3723953238821935;
                                attribute Izz : Real = 0.14012225356268734;
                                attribute sigma_Izz : Real = 0.37017423652493897;
                                attribute Ixy : Real = 0.004382316501913142;
                                attribute sigma_Ixy : Real = 0.02351283871158888;
                                attribute Ixz : Real = 0.002159721094211143;
                                attribute sigma_Ixz : Real = 0.022566176940390956;
                                attribute Iyz : Real = -0.0019180314823680834;
                                attribute sigma_Iyz : Real = 0.02209918015384651;
                            }
                            part <'C.1.1.2.3.2.2.3'> 'Part 213' {
                                attribute POIconv : String = "+";
                                attribute Ipoint : Boolean = false;
                                attribute mass : Real = 0.1452233827507589;
                                attribute sigma_mass : Real = 0.28909372274994966;
                                attribute Cx : Real = 69.70235966145992;
                                attribute sigma_Cx : Real = 28.721044428837228;
                                attribute Cy : Real = -99.04682179912925;
                                attribute sigma_Cy : Real = 28.23690002309109;
                                attribute Cz : Real = -4.038118151947856;
                                attribute sigma_Cz : Real = 29.057750463592832;
                                attribute Ixx : Real = 0.16467064719103577;
                                attribute sigma_Ixx : Real = 0.37074144170588635;
                                attribute Iyy : Real = 0.16516332636656902;
                                attribute sigma_Iyy : Real = 0.3723953238821935;
                                attribute Izz : Real = 0.16574756405439617;
                                attribute sigma_Izz : Real = 0.37017423652493897;
                                attribute Ixy : Real = 6.73015669809325e-05;
                                attribute sigma_Ixy : Real = 0.02351283871158888;
                                attribute Ixz : Real = 0.0008064859573860474;
                                attribute sigma_Ixz : Real = 0.022566176940390956;
                                attribute Iyz : Real = 9.45429883206804e-05;
                                attribute sigma_Iyz : Real = 0.02209918015384651;
                            }
                        }
                        part <'C.1.1.2.3.2.3'> 'Subassembly 62' {
                            attribute POIconv : String = "-";
                            attribute Ipoint : Boolean = false;
                            attribute mass : Real = 2.3097574131095318;
                            attribute sigma_mass : Real = 0.6464332159373649;
                            attribute Cx : Real = -55.7179706711554;
                            attribute sigma_Cx : Real = 22.19800940765393;
                            attribute Cy : Real = 49.45528408050255;
                            attribute sigma_Cy : Real = 16.40117765532497;
                            attribute Cz : Real = 23.92778667463705;
                            attribute sigma_Cz : Real = 21.26476560760994;
                            attribute Ixx : Real = 7029.469476401165;
                            attribute sigma_Ixx : Real = 4467.741663452216;
                            attribute Iyy : Real = 11477.972674129896;
                            attribute sigma_Iyy : Real = 6401.843966444356;
                            attribute Izz : Real = 6837.364659506828;
                            attribute sigma_Izz : Real = 5056.4398232258245;
                            attribute Ixy : Real = 233.69447044300915;
                            attribute sigma_Ixy : Real = 1790.7809771550249;
                            attribute Ixz : Real = 2846.113554767493;
                            attribute sigma_Ixz : Real = 2539.855911644194;
                            attribute Iyz : Real = 741.3575414770705;
                            attribute sigma_Iyz : Real = 2037.7721235835704;
                            part <'C.1.1.2.3.2.3.1'> 'Part 214' {
                                attribute POIconv : String = "-";
                                attribute Ipoint : Boolean = false;
                                attribute mass : Real = 0.9044022637305316;
                                attribute sigma_mass : Real = 0.28909372274994966;
                                attribute Cx : Real = -73.1652638874948;
                                attribute sigma_Cx : Real = 28.721044428837228;
                                attribute Cy : Real = 47.319724690169096;
                                attribute sigma_Cy : Real = 28.23690002309109;
                                attribute Cz : Real = -9.99916298314929;
                                attribute sigma_Cz : Real = 29.057750463592832;
                                attribute Ixx : Real = 0.9492325947565305;
                                attribute sigma_Ixx : Real = 0.37074144170588635;
                                attribute Iyy : Real = 0.9360320524630835;
                                attribute sigma_Iyy : Real = 0.3723953238821935;
                                attribute Izz : Real = 0.8839911821577315;
                                attribute sigma_Izz : Real = 0.37017423652493897;
                                attribute Ixy : Real = 0.009948496644084932;
                                attribute sigma_Ixy : Real = 0.02351283871158888;
                                attribute Ixz : Real = 0.019967147101891583;
                                attribute sigma_Ixz : Real = 0.022566176940390956;
                                attribute Iyz : Real = -0.025267237121970227;
                                attribute sigma_Iyz : Real = 0.02209918015384651;
                            }
                            part <'C.1.1.2.3.2.3.2'> 'Part 215' {
                                attribute POIconv : String = "-";
                                attribute Ipoint : Boolean = false;
                                attribute mass : Real = 0.2961221624750178;
                                attribute sigma_mass : Real = 0.28909372274994966;
                                attribute Cx : Real = 57.75272874161601;
                                attribute sigma_Cx : Real = 28.721044428837228;
                                attribute Cy : Real = 23.951233038678765;
                                attribute sigma_Cy : Real = 28.23690002309109;
                                attribute Cz : Real = 2.959229564294219;
                                attribute sigma_Cz : Real = 29.057750463592832;
                                attribute Ixx : Real = 0.3626336955522084;
                                attribute sigma_Ixx : Real = 0.37074144170588635;
                                attribute Iyy : Real = 0.3879335935391537;
                                attribute sigma_Iyy : Real = 0.3723953238821935;
                                attribute Izz : Real = 0.3270495279040912;
                                attribute sigma_Izz : Real = 0.37017423652493897;
                                attribute Ixy : Real = 0.013342437011175195;
                                attribute sigma_Ixy : Real = 0.02351283871158888;
                                attribute Ixz : Real = 0.020906812089557816;
                                attribute sigma_Ixz : Real = 0.022566176940390956;
                                attribute Iyz : Real = -0.027296757254632677;
                                attribute sigma_Iyz : Real = 0.02209918015384651;
                            }
                            part <'C.1.1.2.3.2.3.3'> 'Part 216' {
                                attribute POIconv : String = "+";
                                attribute Ipoint : Boolean = false;
                                attribute mass : Real = 0.22443272114475257;
                                attribute sigma_mass : Real = 0.28909372274994966;
                                attribute Cx : Real = -4.827612871304154;
                                attribute sigma_Cx : Real = 28.721044428837228;
                                attribute Cy : Real = 99.99984567984939;
                                attribute sigma_Cy : Real = 28.23690002309109;
                                attribute Cz : Real = -53.286241833120584;
                                attribute sigma_Cz : Real = 29.057750463592832;
                                attribute Ixx : Real = 0.26050450990952745;
                                attribute sigma_Ixx : Real = 0.37074144170588635;
                                attribute Iyy : Real = 0.28602244937862803;
                                attribute sigma_Iyy : Real = 0.3723953238821935;
                                attribute Izz : Real = 0.2639115457422525;
                                attribute sigma_Izz : Real = 0.37017423652493897;
                                attribute Ixy : Real = 0.02205493497426421;
                                attribute sigma_Ixy : Real = 0.02351283871158888;
                                attribute Ixz : Real = -0.004006234463396817;
                                attribute sigma_Ixz : Real = 0.022566176940390956;
                                attribute Iyz : Real = 0.005434384403010348;
                                attribute sigma_Iyz : Real = 0.02209918015384651;
                            }
                            part <'C.1.1.2.3.2.3.4'> 'Part 217' {
                                attribute POIconv : String = "+";
                                attribute Ipoint : Boolean = false;
                                attribute mass : Real = 0.3628422315439675;
                                attribute sigma_mass : Real = 0.28909372274994966;
                                attribute Cx : Real = -91.83305935002863;
                                attribute sigma_Cx : Real = 28.721044428837228;
                                attribute Cy : Real = 73.45646698959172;
                                attribute sigma_Cy : Real = 28.23690002309109;
                                attribute Cz : Real = 86.74204144626856;
                                attribute sigma_Cz : Real = 29.057750463592832;
                                attribute Ixx : Real = 0.4874537378145461;
                                attribute sigma_Ixx : Real = 0.37074144170588635;
                                attribute Iyy : Real = 0.48705138601994724;
                                attribute sigma_Iyy : Real = 0.3723953238821935;
                                attribute Izz : Real = 0.44344065095010604;
                                attribute sigma_Izz : Real = 0.37017423652493897;
                                attribute Ixy : Real = -0.0049053120278111425;
                                attribute sigma_Ixy : Real = 0.02351283871158888;
                                attribute Ixz : Real = 0.0156571873612094;
                                attribute sigma_Ixz : Real = 0.022566176940390956;
                                attribute Iyz : Real = -0.016236185597347543;
                                attribute sigma_Iyz : Real = 0.02209918015384651;
                            }
                            part <'C.1.1.2.3.2.3.5'> 'Part 218' {
                                attribute POIconv : String = "-";
                                attribute Ipoint : Boolean = false;
                                attribute mass : Real = 0.5219580342152622;
                                attribute sigma_mass : Real = 0.28909372274994966;
                                attribute Cx : Real = -86.63846324197948;
                                attribute sigma_Cx : Real = 28.721044428837228;
                                attribute Cy : Real = 29.20695743523538;
                                attribute sigma_Cy : Real = 28.23690002309109;
                                attribute Cz : Real = 84.14441836066544;
                                attribute sigma_Cz : Real = 29.057750463592832;
                                attribute Ixx : Real = 0.7293026154351471;
                                attribute sigma_Ixx : Real = 0.37074144170588635;
                                attribute Iyy : Real = 0.735436075843346;
                                attribute sigma_Iyy : Real = 0.3723953238821935;
                                attribute Izz : Real = 0.7321682560002494;
                                attribute sigma_Izz : Real = 0.37017423652493897;
                                attribute Ixy : Real = -0.009181125230816344;
                                attribute sigma_Ixy : Real = 0.02351283871158888;
                                attribute Ixz : Real = -0.006440108924525716;
                                attribute sigma_Ixz : Real = 0.022566176940390956;
                                attribute Iyz : Real = -0.006741881939528966;
                                attribute sigma_Iyz : Real = 0.02209918015384651;
                            }
                        }
                        part <'C.1.1.2.3.2.4'> 'Subassembly 63' {
                            attribute POIconv : String = "-";
                            attribute Ipoint : Boolean = false;
                            attribute mass : Real = 2.581784289986361;
                            attribute sigma_mass : Real = 0.5007250159521434;
                            attribute Cx : Real = 28.904385125609544;
                            attribute sigma_Cx : Real = 20.1066147609887;
                            attribute Cy : Real = -21.944248910949447;
                            attribute sigma_Cy : Real = 19.573300331748968;
                            attribute Cz : Real = 41.82694272353329;
                            attribute sigma_Cz : Real = 17.843703053120926;
                            attribute Ixx : Real = 9469.156002243108;
                            attribute sigma_Ixx : Real = 5739.144598317708;
                            attribute Iyy : Real = 10822.45409302585;
                            attribute sigma_Iyy : Real = 6353.756743357676;
                            attribute Izz : Real = 16742.210617914694;
                            attribute sigma_Izz : Real = 7983.741820626273;
                            attribute Ixy : Real = -7189.90437595758;
                            attribute sigma_Ixy : Real = 3958.9810690724507;
                            attribute Ixz : Real = -4000.7320210708867;
                            attribute sigma_Ixz : Real = 3112.3942676492943;
                            attribute Iyz : Real = -3265.1525195374315;
                            attribute sigma_Iyz : Real = 2847.5825152374427;
                            part <'C.1.1.2.3.2.4.1'> 'Part 219' {
                                attribute POIconv : String = "+";
                                attribute Ipoint : Boolean = false;
                                attribute mass : Real = 0.9988584387758747;
                                attribute sigma_mass : Real = 0.28909372274994966;
                                attribute Cx : Real = -42.60098938830197;
                                attribute sigma_Cx : Real = 28.721044428837228;
                                attribute Cy : Real = -68.97324780002236;
                                attribute sigma_Cy : Real = 28.23690002309109;
                                attribute Cz : Real = 10.626331716775894;
                                attribute sigma_Cz : Real = 29.057750463592832;
                                attribute Ixx : Real = 1.3874784053624771;
                                attribute sigma_Ixx : Real = 0.37074144170588635;
                                attribute Iyy : Real = 1.307586360478764;
                                attribute sigma_Iyy : Real = 0.3723953238821935;
                                attribute Izz : Real = 1.256634479098342;
                                attribute sigma_Izz : Real = 0.37017423652493897;
                                attribute Ixy : Real = -0.13110482560099634;
                                attribute sigma_Ixy : Real = 0.02351283871158888;
                                attribute Ixz : Real = 0.04625486455079787;
                                attribute sigma_Ixz : Real = 0.022566176940390956;
                                attribute Iyz : Real = 0.016983430869299314;
                                attribute sigma_Iyz : Real = 0.02209918015384651;
                            }
                            part <'C.1.1.2.3.2.4.2'> 'Part 220' {
                                attribute POIconv : String = "+";
                                attribute Ipoint : Boolean = false;
                                attribute mass : Real = 0.5840093918405473;
                                attribute sigma_mass : Real = 0.28909372274994966;
                                attribute Cx : Real = 46.205307403579354;
                                attribute sigma_Cx : Real = 28.721044428837228;
                                attribute Cy : Real = -58.744016010314226;
                                attribute sigma_Cy : Real = 28.23690002309109;
                                attribute Cz : Real = 47.29798976331949;
                                attribute sigma_Cz : Real = 29.057750463592832;
                                attribute Ixx : Real = 0.7925765243026777;
                                attribute sigma_Ixx : Real = 0.37074144170588635;
                                attribute Iyy : Real = 0.837003196750336;
                                attribute sigma_Iyy : Real = 0.3723953238821935;
                                attribute Izz : Real = 0.7932874879269525;
                                attribute sigma_Izz : Real = 0.37017423652493897;
                                attribute Ixy : Real = -0.036248160328857026;
                                attribute sigma_Ixy : Real = 0.02351283871158888;
                                attribute Ixz : Real = -0.043563745725989436;
                                attribute sigma_Ixz : Real = 0.022566176940390956;
                                attribute Iyz : Real = -0.04072657822490108;
                                attribute sigma_Iyz : Real = 0.02209918015384651;
                            }
                            part <'C.1.1.2.3.2.4.3'> 'Part 221' {
                                attribute POIconv : String = "+";
                                attribute Ipoint : Boolean = false;
                                attribute mass : Real = 0.9989164593699388;
                                attribute sigma_mass : Real = 0.28909372274994966;
                                attribute Cx : Real = 90.2907453943044;
                                attribute sigma_Cx : Real = 28.721044428837228;
                                attribute Cy : Real = 46.59674004651606;
                                attribute sigma_Cy : Real = 28.23690002309109;
                                attribute Cz : Real = 69.82713281176984;
                                attribute sigma_Cz : Real = 29.057750463592832;
                                attribute Ixx : Real = 1.1095701631112358;
                                attribute sigma_Ixx : Real = 0.37074144170588635;
                                attribute Iyy : Real = 1.1100416041463839;
                                attribute sigma_Iyy : Real = 0.3723953238821935;
                                attribute Izz : Real = 1.112370446975694;
                                attribute sigma_Izz : Real = 0.37017423652493897;
                                attribute Ixy : Real = -0.017234259898404644;
                                attribute sigma_Ixy : Real = 0.02351283871158888;
                                attribute Ixz : Real = 0.018538264519253334;
                                attribute sigma_Ixz : Real = 0.022566176940390956;
                                attribute Iyz : Real = 0.01709519954696141;
                                attribute sigma_Iyz : Real = 0.02209918015384651;
                            }
                        }
                    }
                    part <'C.1.1.2.3.3'> 'Assembly 17' {
                        attribute POIconv : String = "-";
                        attribute Ipoint : Boolean = false;
                        attribute mass : Real = 8.74118715945608;
                        attribute sigma_mass : Real = 1.0014500319042867;
                        attribute Cx : Real = 18.685195565838118;
                        attribute sigma_Cx : Real = 11.413210747436105;
                        attribute Cy : Real = -2.916579258229092;
                        attribute sigma_Cy : Real = 10.636040341766636;
                        attribute Cz : Real = -4.219459367620513;
                        attribute sigma_Cz : Real = 12.211912950901143;
                        attribute Ixx : Real = 73408.96875536501;
                        attribute sigma_Ixx : Real = 17118.95104808237;
                        attribute Iyy : Real = 74306.83797118398;
                        attribute sigma_Iyy : Real = 17182.692765867636;
                        attribute Izz : Real = 54792.44537927324;
                        attribute sigma_Izz : Real = 13928.577453852999;
                        attribute Ixy : Real = 1995.468828348629;
                        attribute sigma_Ixy : Real = 6573.81958584583;
                        attribute Ixz : Real = -7445.44306688574;
                        attribute sigma_Ixz : Real = 7981.298053604893;
                        attribute Iyz : Real = 6711.832831683621;
                        attribute sigma_Iyz : Real = 8093.771117678239;
                        part <'C.1.1.2.3.3.1'> 'Subassembly 64' {
                            attribute POIconv : String = "-";
                            attribute Ipoint : Boolean = false;
                            attribute mass : Real = 3.4916543128469497;
                            attribute sigma_mass : Real = 0.5781874454998993;
                            attribute Cx : Real = 51.19043990795974;
                            attribute sigma_Cx : Real = 14.908329644541633;
                            attribute Cy : Real = 7.333855475371969;
                            attribute sigma_Cy : Real = 18.375859921673648;
                            attribute Cz : Real = 45.84651484676554;
                            attribute sigma_Cz : Real = 19.236467997494557;
                            attribute Ixx : Real = 34156.64136027418;
                            attribute sigma_Ixx : Real = 12159.316967076487;
                            attribute Iyy : Real = 18545.525009407887;
                            attribute sigma_Iyy : Real = 8934.831745951391;
                            attribute Izz : Real = 19083.914840799443;
                            attribute sigma_Izz : Real = 8031.941866575398;
                            attribute Ixy : Real = 636.3543906612579;
                            attribute sigma_Ixy : Real = 3834.9990999555016;
                            attribute Ixz : Real = 1439.074215338888;
                            attribute sigma_Ixz : Real = 3515.378046427734;
                            attribute Iyz : Real = 9054.000639138187;
                            attribute sigma_Iyz : Real = 5611.00926486008;
                            part <'C.1.1.2.3.3.1.1'> 'Part 222' {
                                attribute POIconv : String = "+";
                                attribute Ipoint : Boolean = false;
                                attribute mass : Real = 0.6981337218536064;
                                attribute sigma_mass : Real = 0.28909372274994966;
                                attribute Cx : Real = 67.63584432192147;
                                attribute sigma_Cx : Real = 28.721044428837228;
                                attribute Cy : Real = 73.54285116307437;
                                attribute sigma_Cy : Real = 28.23690002309109;
                                attribute Cz : Real = -92.03836084343493;
                                attribute sigma_Cz : Real = 29.057750463592832;
                                attribute Ixx : Real = 0.8445897074929012;
                                attribute sigma_Ixx : Real = 0.37074144170588635;
                                attribute Iyy : Real = 0.8524050803617161;
                                attribute sigma_Iyy : Real = 0.3723953238821935;
                                attribute Izz : Real = 0.8139248541718875;
                                attribute sigma_Izz : Real = 0.37017423652493897;
                                attribute Ixy : Real = -0.013188904285200972;
                                attribute sigma_Ixy : Real = 0.02351283871158888;
                                attribute Ixz : Real = 0.0015370608965754537;
                                attribute sigma_Ixz : Real = 0.022566176940390956;
                                attribute Iyz : Real = -0.06759867719942336;
                                attribute sigma_Iyz : Real = 0.02209918015384651;
                            }
                            part <'C.1.1.2.3.3.1.2'> 'Part 223' {
                                attribute POIconv : String = "+";
                                attribute Ipoint : Boolean = false;
                                attribute mass : Real = 0.9647084078663029;
                                attribute sigma_mass : Real = 0.28909372274994966;
                                attribute Cx : Real = 78.57757876627147;
                                attribute sigma_Cx : Real = 28.721044428837228;
                                attribute Cy : Real = -56.53379508294165;
                                attribute sigma_Cy : Real = 28.23690002309109;
                                attribute Cz : Real = 92.2572017647326;
                                attribute sigma_Cz : Real = 29.057750463592832;
                                attribute Ixx : Real = 1.119175687159004;
                                attribute sigma_Ixx : Real = 0.37074144170588635;
                                attribute Iyy : Real = 1.2611308568725628;
                                attribute sigma_Iyy : Real = 0.3723953238821935;
                                attribute Izz : Real = 1.0751581449878107;
                                attribute sigma_Izz : Real = 0.37017423652493897;
                                attribute Ixy : Real = -0.03904206589218167;
                                attribute sigma_Ixy : Real = 0.02351283871158888;
                                attribute Ixz : Real = 0.027826538221908642;
                                attribute sigma_Ixz : Real = 0.022566176940390956;
                                attribute Iyz : Real = 0.07962088554850537;
                                attribute sigma_Iyz : Real = 0.02209918015384651;
                            }
                            part <'C.1.1.2.3.3.1.3'> 'Part 224' {
                                attribute POIconv : String = "-";
                                attribute Ipoint : Boolean = false;
                                attribute mass : Real = 0.9123147654340137;
                                attribute sigma_mass : Real = 0.28909372274994966;
                                attribute Cx : Real = 25.994484685361385;
                                attribute sigma_Cx : Real = 28.721044428837228;
                                attribute Cy : Real = -59.17880036868155;
                                attribute sigma_Cy : Real = 28.23690002309109;
                                attribute Cz : Real = 75.86501985788345;
                                attribute sigma_Cz : Real = 29.057750463592832;
                                attribute Ixx : Real = 0.9567876611695977;
                                attribute sigma_Ixx : Real = 0.37074144170588635;
                                attribute Iyy : Real = 0.9558885021706184;
                                attribute sigma_Iyy : Real = 0.3723953238821935;
                                attribute Izz : Real = 0.8850765849763327;
                                attribute sigma_Izz : Real = 0.37017423652493897;
                                attribute Ixy : Real = 0.0030148245862326043;
                                attribute sigma_Ixy : Real = 0.02351283871158888;
                                attribute Ixz : Real = 0.03158207208613933;
                                attribute sigma_Ixz : Real = 0.022566176940390956;
                                attribute Iyz : Real = 0.01556459289111984;
                                attribute sigma_Iyz : Real = 0.02209918015384651;
                            }
                            part <'C.1.1.2.3.3.1.4'> 'Part 225' {
                                attribute POIconv : String = "+";
                                attribute Ipoint : Boolean = false;
                                attribute mass : Real = 0.9164974176930264;
                                attribute sigma_mass : Real = 0.28909372274994966;
                                attribute Cx : Real = 34.91646875627339;
                                attribute sigma_Cx : Real = 28.721044428837228;
                                attribute Cy : Real = 90.33616781234741;
                                attribute sigma_Cy : Real = 28.23690002309109;
                                attribute Cz : Real = 72.14552643708885;
                                attribute sigma_Cz : Real = 29.057750463592832;
                                attribute Ixx : Real = 1.1165697394666352;
                                attribute sigma_Ixx : Real = 0.37074144170588635;
                                attribute Iyy : Real = 1.1605305403015118;
                                attribute sigma_Iyy : Real = 0.3723953238821935;
                                attribute Izz : Real = 1.2445897060531552;
                                attribute sigma_Izz : Real = 0.37017423652493897;
                                attribute Ixy : Real = 0.05241478792559159;
                                attribute sigma_Ixy : Real = 0.02351283871158888;
                                attribute Ixz : Real = 0.07428953166550448;
                                attribute sigma_Ixz : Real = 0.022566176940390956;
                                attribute Iyz : Real = -0.11462705715255231;
                                attribute sigma_Iyz : Real = 0.02209918015384651;
                            }
                        }
                        part <'C.1.1.2.3.3.2'> 'Subassembly 65' {
                            attribute POIconv : String = "-";
                            attribute Ipoint : Boolean = false;
                            attribute mass : Real = 3.217780872141244;
                            attribute sigma_mass : Real = 0.5781874454998993;
                            attribute Cx : Real = 1.3313436381813504;
                            attribute sigma_Cx : Real = 18.47342945612833;
                            attribute Cy : Real = 3.929439308283572;
                            attribute sigma_Cy : Real = 16.825030688179993;
                            attribute Cz : Real = -66.77771582119499;
                            attribute sigma_Cz : Real = 15.325427124075588;
                            attribute Ixx : Real = 8650.864947800284;
                            attribute sigma_Ixx : Real = 5092.636679765947;
                            attribute Iyy : Real = 13343.902432752864;
                            attribute sigma_Iyy : Real = 6593.406499741442;
                            attribute Izz : Real = 18124.963170871077;
                            attribute sigma_Izz : Real = 7940.798839862667;
                            attribute Ixy : Real = 6228.152166841617;
                            attribute sigma_Ixy : Real = 3753.1849664256256;
                            attribute Ixz : Real = 3610.8893706956655;
                            attribute sigma_Ixz : Real = 2995.0395094106852;
                            attribute Iyz : Real = -1609.0287011494704;
                            attribute sigma_Iyz : Real = 2359.6650160468866;
                            part <'C.1.1.2.3.3.2.1'> 'Part 226' {
                                attribute POIconv : String = "-";
                                attribute Ipoint : Boolean = false;
                                attribute mass : Real = 0.9521157774229069;
                                attribute sigma_mass : Real = 0.28909372274994966;
                                attribute Cx : Real = 27.95442072674632;
                                attribute sigma_Cx : Real = 28.721044428837228;
                                attribute Cy : Real = -17.813743744045496;
                                attribute sigma_Cy : Real = 28.23690002309109;
                                attribute Cz : Real = -96.69689703732729;
                                attribute sigma_Cz : Real = 29.057750463592832;
                                attribute Ixx : Real = 1.371600012959723;
                                attribute sigma_Ixx : Real = 0.37074144170588635;
                                attribute Iyy : Real = 1.2419443960559506;
                                attribute sigma_Iyy : Real = 0.3723953238821935;
                                attribute Izz : Real = 1.342665845706661;
                                attribute sigma_Izz : Real = 0.37017423652493897;
                                attribute Ixy : Real = -0.07520682467824574;
                                attribute sigma_Ixy : Real = 0.02351283871158888;
                                attribute Ixz : Real = -0.007326237124911683;
                                attribute sigma_Ixz : Real = 0.022566176940390956;
                                attribute Iyz : Real = 0.04274520311737465;
                                attribute sigma_Iyz : Real = 0.02209918015384651;
                            }
                            part <'C.1.1.2.3.3.2.2'> 'Part 227' {
                                attribute POIconv : String = "+";
                                attribute Ipoint : Boolean = false;
                                attribute mass : Real = 0.9317316875497345;
                                attribute sigma_mass : Real = 0.28909372274994966;
                                attribute Cx : Real = -51.0455621406436;
                                attribute sigma_Cx : Real = 28.721044428837228;
                                attribute Cy : Real = -4.449240770190954;
                                attribute sigma_Cy : Real = 28.23690002309109;
                                attribute Cz : Real = -37.096175737679005;
                                attribute sigma_Cz : Real = 29.057750463592832;
                                attribute Ixx : Real = 1.2477798228030526;
                                attribute sigma_Ixx : Real = 0.37074144170588635;
                                attribute Iyy : Real = 1.1724668222578458;
                                attribute sigma_Iyy : Real = 0.3723953238821935;
                                attribute Izz : Real = 1.2328642761254631;
                                attribute sigma_Izz : Real = 0.37017423652493897;
                                attribute Ixy : Real = 0.020919445093805503;
                                attribute sigma_Ixy : Real = 0.02351283871158888;
                                attribute Ixz : Real = 0.03271571023539337;
                                attribute sigma_Ixz : Real = 0.022566176940390956;
                                attribute Iyz : Real = 0.07338760775987871;
                                attribute sigma_Iyz : Real = 0.02209918015384651;
                            }
                            part <'C.1.1.2.3.3.2.3'> 'Part 228' {
                                attribute POIconv : String = "-";
                                attribute Ipoint : Boolean = false;
                                attribute mass : Real = 0.6940943061190191;
                                attribute sigma_mass : Real = 0.28909372274994966;
                                attribute Cx : Real = -54.334507742896676;
                                attribute sigma_Cx : Real = 28.721044428837228;
                                attribute Cy : Real = 87.44880226440728;
                                attribute sigma_Cy : Real = 28.23690002309109;
                                attribute Cz : Real = -52.77128373272717;
                                attribute sigma_Cz : Real = 29.057750463592832;
                                attribute Ixx : Real = 0.7778768636204603;
                                attribute sigma_Ixx : Real = 0.37074144170588635;
                                attribute Iyy : Real = 0.8285365676523015;
                                attribute sigma_Iyy : Real = 0.3723953238821935;
                                attribute Izz : Real = 0.786388175813045;
                                attribute sigma_Izz : Real = 0.37017423652493897;
                                attribute Ixy : Real = 0.042779019462823;
                                attribute sigma_Ixy : Real = 0.02351283871158888;
                                attribute Ixz : Real = 0.05916467742656986;
                                attribute sigma_Ixz : Real = 0.022566176940390956;
                                attribute Iyz : Real = -0.040436065287044694;
                                attribute sigma_Iyz : Real = 0.02209918015384651;
                            }
                            part <'C.1.1.2.3.3.2.4'> 'Part 229' {
                                attribute POIconv : String = "-";
                                attribute Ipoint : Boolean = false;
                                attribute mass : Real = 0.6398391010495834;
                                attribute sigma_mass : Real = 0.28909372274994966;
                                attribute Cx : Real = 98.3718675095588;
                                attribute sigma_Cx : Real = 28.721044428837228;
                                attribute Cy : Real = -42.11589437909424;
                                attribute sigma_Cy : Real = 28.23690002309109;
                                attribute Cz : Real = -80.6726023554802;
                                attribute sigma_Cz : Real = 29.057750463592832;
                                attribute Ixx : Real = 0.8736377868553544;
                                attribute sigma_Ixx : Real = 0.37074144170588635;
                                attribute Iyy : Real = 0.8523942566839732;
                                attribute sigma_Iyy : Real = 0.3723953238821935;
                                attribute Izz : Real = 0.8865886617287865;
                                attribute sigma_Izz : Real = 0.37017423652493897;
                                attribute Ixy : Real = 0.007195729646190966;
                                attribute sigma_Ixy : Real = 0.02351283871158888;
                                attribute Ixz : Real = 0.0664610558232108;
                                attribute sigma_Ixz : Real = 0.022566176940390956;
                                attribute Iyz : Real = 0.03868451980895579;
                                attribute sigma_Iyz : Real = 0.02209918015384651;
                            }
                        }
                        part <'C.1.1.2.3.3.3'> 'Subassembly 66' {
                            attribute POIconv : String = "-";
                            attribute Ipoint : Boolean = false;
                            attribute mass : Real = 1.047543550181901;
                            attribute sigma_mass : Real = 0.40884026350990615;
                            attribute Cx : Real = -66.86771413010199;
                            attribute sigma_Cx : Real = 23.967454581746004;
                            attribute Cy : Real = -47.68288646814449;
                            attribute sigma_Cy : Real = 20.5490213424658;
                            attribute Cz : Real = -35.66197989664319;
                            attribute sigma_Cz : Real = 26.122690466669727;
                            attribute Ixx : Real = 1865.6477528621513;
                            attribute sigma_Ixx : Real = 1955.5215449163275;
                            attribute Iyy : Real = 2799.0007476015253;
                            attribute sigma_Iyy : Real = 2478.4675485640964;
                            attribute Izz : Real = 1203.2230714319753;
                            attribute sigma_Izz : Real = 1512.293424081309;
                            attribute Ixy : Real = -378.7280190058864;
                            attribute sigma_Ixy : Real = 722.992398526252;
                            attribute Ixz : Real = 1359.1446549913853;
                            attribute sigma_Ixz : Real = 1229.2410809717348;
                            attribute Iyz : Real = 482.09903281227105;
                            attribute sigma_Iyz : Real = 901.5262994352415;
                            part <'C.1.1.2.3.3.3.1'> 'Part 230' {
                                attribute POIconv : String = "+";
                                attribute Ipoint : Boolean = false;
                                attribute mass : Real = 0.4732876319605857;
                                attribute sigma_mass : Real = 0.28909372274994966;
                                attribute Cx : Real = -31.702012661844492;
                                attribute sigma_Cx : Real = 28.721044428837228;
                                attribute Cy : Real = -35.20986712537706;
                                attribute sigma_Cy : Real = 28.23690002309109;
                                attribute Cz : Real = -80.42764598503709;
                                attribute sigma_Cz : Real = 29.057750463592832;
                                attribute Ixx : Real = 0.5776282630512082;
                                attribute sigma_Ixx : Real = 0.37074144170588635;
                                attribute Iyy : Real = 0.612928435004331;
                                attribute sigma_Iyy : Real = 0.3723953238821935;
                                attribute Izz : Real = 0.657295392667476;
                                attribute sigma_Izz : Real = 0.37017423652493897;
                                attribute Ixy : Real = 0.047315951687357305;
                                attribute sigma_Ixy : Real = 0.02351283871158888;
                                attribute Ixz : Real = -0.0209877133098088;
                                attribute sigma_Ixz : Real = 0.022566176940390956;
                                attribute Iyz : Real = -0.025580359002634334;
                                attribute sigma_Iyz : Real = 0.02209918015384651;
                            }
                            part <'C.1.1.2.3.3.3.2'> 'Part 231' {
                                attribute POIconv : String = "+";
                                attribute Ipoint : Boolean = false;
                                attribute mass : Real = 0.5742559182213154;
                                attribute sigma_mass : Real = 0.28909372274994966;
                                attribute Cx : Real = -95.85042209364474;
                                attribute sigma_Cx : Real = 28.721044428837228;
                                attribute Cy : Real = -57.96284284442663;
                                attribute sigma_Cy : Real = 28.23690002309109;
                                attribute Cz : Real = 1.2327832635492086;
                                attribute sigma_Cz : Real = 29.057750463592832;
                                attribute Ixx : Real = 0.6094341659991354;
                                attribute sigma_Ixx : Real = 0.37074144170588635;
                                attribute Iyy : Real = 0.5918451796024123;
                                attribute sigma_Iyy : Real = 0.3723953238821935;
                                attribute Izz : Real = 0.5940358472508244;
                                attribute sigma_Izz : Real = 0.37017423652493897;
                                attribute Ixy : Real = -0.008256612516430856;
                                attribute sigma_Ixy : Real = 0.02351283871158888;
                                attribute Ixz : Real = -0.00900113820804338;
                                attribute sigma_Ixz : Real = 0.022566176940390956;
                                attribute Iyz : Real = -0.0053345997541966;
                                attribute sigma_Iyz : Real = 0.02209918015384651;
                            }
                        }
                        part <'C.1.1.2.3.3.4'> 'Subassembly 67' {
                            attribute POIconv : String = "-";
                            attribute Ipoint : Boolean = false;
                            attribute mass : Real = 0.9842084242859855;
                            attribute sigma_mass : Real = 0.40884026350990615;
                            attribute Cx : Real = 51.16227476574263;
                            attribute sigma_Cx : Real = 35.57400262589794;
                            attribute Cy : Real = -14.017181109407279;
                            attribute sigma_Cy : Real = 27.37951722031038;
                            attribute Cz : Real = 56.157077078938215;
                            attribute sigma_Cz : Real = 28.41140796990721;
                            attribute Ixx : Real = 29.070425851301945;
                            attribute sigma_Ixx : Real = 198.46590610082572;
                            attribute Iyy : Real = 286.23247162756974;
                            attribute sigma_Iyy : Real = 1839.9033433500103;
                            attribute Izz : Real = 278.38731035357324;
                            attribute sigma_Izz : Real = 1791.3724643953258;
                            attribute Ixy : Real = -52.050843661814085;
                            attribute sigma_Ixy : Real = 359.0409059153994;
                            attribute Ixz : Real = 68.87911037359837;
                            attribute sigma_Ixz : Real = 461.65501994295363;
                            attribute Iyz : Real = 13.430888118923587;
                            attribute sigma_Iyz : Real = 96.07386635679599;
                            part <'C.1.1.2.3.3.4.1'> 'Part 232' {
                                attribute POIconv : String = "-";
                                attribute Ipoint : Boolean = false;
                                attribute mass : Real = 0.04330555290146731;
                                attribute sigma_mass : Real = 0.28909372274994966;
                                attribute Cx : Real = -25.640655355527997;
                                attribute sigma_Cx : Real = 28.721044428837228;
                                attribute Cy : Real = -28.993777837604284;
                                attribute sigma_Cy : Real = 28.23690002309109;
                                attribute Cz : Real = 75.9551013354212;
                                attribute sigma_Cz : Real = 29.057750463592832;
                                attribute Ixx : Real = 0.043565605630665215;
                                attribute sigma_Ixx : Real = 0.37074144170588635;
                                attribute Iyy : Real = 0.048302207446119176;
                                attribute sigma_Iyy : Real = 0.3723953238821935;
                                attribute Izz : Real = 0.05053253801369557;
                                attribute sigma_Izz : Real = 0.37017423652493897;
                                attribute Ixy : Real = 0.0033737695972688793;
                                attribute sigma_Ixy : Real = 0.02351283871158888;
                                attribute Ixz : Real = -0.003095254732756547;
                                attribute sigma_Ixz : Real = 0.022566176940390956;
                                attribute Iyz : Real = -0.0007330748379831833;
                                attribute sigma_Iyz : Real = 0.02209918015384651;
                            }
                            part <'C.1.1.2.3.3.4.2'> 'Part 233' {
                                attribute POIconv : String = "+";
                                attribute Ipoint : Boolean = false;
                                attribute mass : Real = 0.9409028713845182;
                                attribute sigma_mass : Real = 0.28909372274994966;
                                attribute Cx : Real = 54.69717029482126;
                                attribute sigma_Cx : Real = 28.721044428837228;
                                attribute Cy : Real = -13.32787531428039;
                                attribute sigma_Cy : Real = 28.23690002309109;
                                attribute Cz : Real = 55.245862528681755;
                                attribute sigma_Cz : Real = 29.057750463592832;
                                attribute Ixx : Real = 1.111065119286856;
                                attribute sigma_Ixx : Real = 0.37074144170588635;
                                attribute Iyy : Real = 1.2257314538222586;
                                attribute sigma_Iyy : Real = 0.3723953238821935;
                                attribute Izz : Real = 0.9732723834667619;
                                attribute sigma_Izz : Real = 0.37017423652493897;
                                attribute Ixy : Real = -0.05047023546156895;
                                attribute sigma_Ixy : Real = 0.02351283871158888;
                                attribute Ixz : Real = -0.0034150040870669952;
                                attribute sigma_Ixz : Real = 0.022566176940390956;
                                attribute Iyz : Real = -0.00023428343943622182;
                                attribute sigma_Iyz : Real = 0.02209918015384651;
                            }
                        }
                    }
                    part <'C.1.1.2.3.4'> 'Assembly 18' {
                        attribute POIconv : String = "-";
                        attribute Ipoint : Boolean = false;
                        attribute mass : Real = 3.323058825741289;
                        attribute sigma_mass : Real = 0.7648700959862226;
                        attribute Cx : Real = -33.4868973654338;
                        attribute sigma_Cx : Real = 21.38983382203289;
                        attribute Cy : Real = 57.551927266181615;
                        attribute sigma_Cy : Real = 18.425056442157654;
                        attribute Cz : Real = 17.567782059957818;
                        attribute sigma_Cz : Real = 19.37484774500335;
                        attribute Ixx : Real = 13212.692555714088;
                        attribute sigma_Ixx : Real = 8250.096391863191;
                        attribute Iyy : Real = 30505.687808489532;
                        attribute sigma_Iyy : Real = 11907.56548276426;
                        attribute Izz : Real = 22902.04565992346;
                        attribute sigma_Izz : Real = 10527.698596436958;
                        attribute Ixy : Real = -2378.590704758287;
                        attribute sigma_Ixy : Real = 4854.631926573994;
                        attribute Ixz : Real = -13097.11964782995;
                        attribute sigma_Ixz : Real = 5821.467934394916;
                        attribute Iyz : Real = -2342.3133410631526;
                        attribute sigma_Iyz : Real = 3799.5844838291764;
                        part <'C.1.1.2.3.4.1'> 'Subassembly 68' {
                            attribute POIconv : String = "-";
                            attribute Ipoint : Boolean = false;
                            attribute mass : Real = 2.14174658659962;
                            attribute sigma_mass : Real = 0.5781874454998993;
                            attribute Cx : Real = -9.326548477070675;
                            attribute sigma_Cx : Real = 27.706220588406108;
                            attribute Cy : Real = 45.73502595864985;
                            attribute sigma_Cy : Real = 21.97687781362273;
                            attribute Cz : Real = 20.75352532228529;
                            attribute sigma_Cz : Real = 23.51558188345588;
                            attribute Ixx : Real = 11452.93475902588;
                            attribute sigma_Ixx : Real = 7023.334255657797;
                            attribute Iyy : Real = 26495.655053333816;
                            attribute sigma_Iyy : Real = 10957.65715506586;
                            attribute Izz : Real = 17983.901994779502;
                            attribute sigma_Izz : Real = 9363.83566509534;
                            attribute Ixy : Real = -3920.8550128542397;
                            attribute sigma_Ixy : Real = 4275.419110364019;
                            attribute Ixz : Real = -12784.181020867958;
                            attribute sigma_Ixz : Real = 5390.762095002267;
                            attribute Iyz : Real = -2991.275598611973;
                            attribute sigma_Iyz : Real = 3128.20512870414;
                            part <'C.1.1.2.3.4.1.1'> 'Part 234' {
                                attribute POIconv : String = "+";
                                attribute Ipoint : Boolean = false;
                                attribute mass : Real = 0.2811081306487322;
                                attribute sigma_mass : Real = 0.28909372274994966;
                                attribute Cx : Real = -27.522867592051625;
                                attribute sigma_Cx : Real = 28.721044428837228;
                                attribute Cy : Real = 59.66183729469776;
                                attribute sigma_Cy : Real = 28.23690002309109;
                                attribute Cz : Real = 19.088839506730437;
                                attribute sigma_Cz : Real = 29.057750463592832;
                                attribute Ixx : Real = 0.4283722611925715;
                                attribute sigma_Ixx : Real = 0.37074144170588635;
                                attribute Iyy : Real = 0.4406517655099938;
                                attribute sigma_Iyy : Real = 0.3723953238821935;
                                attribute Izz : Real = 0.4294795600464828;
                                attribute sigma_Izz : Real = 0.37017423652493897;
                                attribute Ixy : Real = 0.013364300055362094;
                                attribute sigma_Ixy : Real = 0.02351283871158888;
                                attribute Ixz : Real = 0.007087496858972354;
                                attribute sigma_Ixz : Real = 0.022566176940390956;
                                attribute Iyz : Real = -0.013233216165753982;
                                attribute sigma_Iyz : Real = 0.02209918015384651;
                            }
                            part <'C.1.1.2.3.4.1.2'> 'Part 235' {
                                attribute POIconv : String = "-";
                                attribute Ipoint : Boolean = false;
                                attribute mass : Real = 0.07347928326041438;
                                attribute sigma_mass : Real = 0.28909372274994966;
                                attribute Cx : Real = -94.68974452465773;
                                attribute sigma_Cx : Real = 28.721044428837228;
                                attribute Cy : Real = -51.4374659396708;
                                attribute sigma_Cy : Real = 28.23690002309109;
                                attribute Cz : Real = -27.355687180534005;
                                attribute sigma_Cz : Real = 29.057750463592832;
                                attribute Ixx : Real = 0.09184769553994289;
                                attribute sigma_Ixx : Real = 0.37074144170588635;
                                attribute Iyy : Real = 0.08356440776952441;
                                attribute sigma_Iyy : Real = 0.3723953238821935;
                                attribute Izz : Real = 0.0973344283336313;
                                attribute sigma_Izz : Real = 0.37017423652493897;
                                attribute Ixy : Real = 0.0017784309639501618;
                                attribute sigma_Ixy : Real = 0.02351283871158888;
                                attribute Ixz : Real = -0.001244502880692563;
                                attribute sigma_Ixz : Real = 0.022566176940390956;
                                attribute Iyz : Real = 0.004280943903010156;
                                attribute sigma_Iyz : Real = 0.02209918015384651;
                            }
                            part <'C.1.1.2.3.4.1.3'> 'Part 236' {
                                attribute POIconv : String = "-";
                                attribute Ipoint : Boolean = false;
                                attribute mass : Real = 0.862738692422863;
                                attribute sigma_mass : Real = 0.28909372274994966;
                                attribute Cx : Real = 94.40713622607291;
                                attribute sigma_Cx : Real = 28.721044428837228;
                                attribute Cy : Real = 68.24324573390186;
                                attribute sigma_Cy : Real = 28.23690002309109;
                                attribute Cz : Real = 99.64995072223246;
                                attribute sigma_Cz : Real = 29.057750463592832;
                                attribute Ixx : Real = 1.1817757892294176;
                                attribute sigma_Ixx : Real = 0.37074144170588635;
                                attribute Iyy : Real = 1.257720481406359;
                                attribute sigma_Iyy : Real = 0.3723953238821935;
                                attribute Izz : Real = 1.0375093898927759;
                                attribute sigma_Izz : Real = 0.37017423652493897;
                                attribute Ixy : Real = 0.03869749474441674;
                                attribute sigma_Ixy : Real = 0.02351283871158888;
                                attribute Ixz : Real = 0.0025811752327822715;
                                attribute sigma_Ixz : Real = 0.022566176940390956;
                                attribute Iyz : Real = 0.027866661974746687;
                                attribute sigma_Iyz : Real = 0.02209918015384651;
                            }
                            part <'C.1.1.2.3.4.1.4'> 'Part 237' {
                                attribute POIconv : String = "-";
                                attribute Ipoint : Boolean = false;
                                attribute mass : Real = 0.9244204802676104;
                                attribute sigma_mass : Real = 0.28909372274994966;
                                attribute Cx : Real = -93.82002893835306;
                                attribute sigma_Cx : Real = 28.721044428837228;
                                attribute Cy : Real = 28.217578772455454;
                                attribute sigma_Cy : Real = 28.23690002309109;
                                attribute Cz : Real = -48.54828384704888;
                                attribute sigma_Cz : Real = 29.057750463592832;
                                attribute Ixx : Real = 1.291964255238476;
                                attribute sigma_Ixx : Real = 0.37074144170588635;
                                attribute Iyy : Real = 1.2932585161554613;
                                attribute sigma_Iyy : Real = 0.3723953238821935;
                                attribute Izz : Real = 1.4997073295702223;
                                attribute sigma_Izz : Real = 0.37017423652493897;
                                attribute Ixy : Real = 0.006319896740008379;
                                attribute sigma_Ixy : Real = 0.02351283871158888;
                                attribute Ixz : Real = -0.06675934375577333;
                                attribute sigma_Ixz : Real = 0.022566176940390956;
                                attribute Iyz : Real = -0.02549416487631085;
                                attribute sigma_Iyz : Real = 0.02209918015384651;
                            }
                        }
                        part <'C.1.1.2.3.4.2'> 'Subassembly 69' {
                            attribute POIconv : String = "-";
                            attribute Ipoint : Boolean = false;
                            attribute mass : Real = 1.1813122391416693;
                            attribute sigma_mass : Real = 0.5007250159521434;
                            attribute Cx : Real = -77.29017227292594;
                            attribute sigma_Cx : Real = 24.75111697400508;
                            attribute Cy : Real = 78.97624439505509;
                            attribute sigma_Cy : Real = 31.350440489289706;
                            attribute Cz : Real = 11.791955371807886;
                            attribute sigma_Cz : Real = 33.82822136206128;
                            attribute Ixx : Real = 857.3168977905092;
                            attribute sigma_Ixx : Real = 3820.5810722721967;
                            attribute Iyy : Real = 432.08632802761366;
                            attribute sigma_Iyy : Real = 2355.3168185795216;
                            attribute Izz : Real = 560.0469040953789;
                            attribute sigma_Izz : Real = 1737.806703531257;
                            attribute Ixy : Real = -177.81400022830957;
                            attribute sigma_Ixy : Real = 480.8243375483358;
                            attribute Ixz : Real = 150.78089974058153;
                            attribute sigma_Ixz : Real = 449.60678788715785;
                            attribute Iyz : Real = 422.15560393882254;
                            attribute sigma_Iyz : Real = 1868.5342202202494;
                            part <'C.1.1.2.3.4.2.1'> 'Part 238' {
                                attribute POIconv : String = "+";
                                attribute Ipoint : Boolean = false;
                                attribute mass : Real = 0.0019436514207627625;
                                attribute sigma_mass : Real = 0.28909372274994966;
                                attribute Cx : Real = -68.10006583109498;
                                attribute sigma_Cx : Real = 28.721044428837228;
                                attribute Cy : Real = 9.63552058674395;
                                attribute sigma_Cy : Real = 28.23690002309109;
                                attribute Cz : Real = 98.50059025920928;
                                attribute sigma_Cz : Real = 29.057750463592832;
                                attribute Ixx : Real = 0.002584144316889135;
                                attribute sigma_Ixx : Real = 0.37074144170588635;
                                attribute Iyy : Real = 0.002689371680209796;
                                attribute sigma_Iyy : Real = 0.3723953238821935;
                                attribute Izz : Real = 0.00271806309481121;
                                attribute sigma_Izz : Real = 0.37017423652493897;
                                attribute Ixy : Real = -8.529725864750898e-05;
                                attribute sigma_Ixy : Real = 0.02351283871158888;
                                attribute Ixz : Real = -3.44165367412081e-05;
                                attribute sigma_Ixz : Real = 0.022566176940390956;
                                attribute Iyz : Real = 5.08053796833044e-05;
                                attribute sigma_Iyz : Real = 0.02209918015384651;
                            }
                            part <'C.1.1.2.3.4.2.2'> 'Part 239' {
                                attribute POIconv : String = "+";
                                attribute Ipoint : Boolean = false;
                                attribute mass : Real = 0.9790661035573576;
                                attribute sigma_mass : Real = 0.28909372274994966;
                                attribute Cx : Real = -73.9092618227005;
                                attribute sigma_Cx : Real = 28.721044428837228;
                                attribute Cy : Real = 88.23915966786444;
                                attribute sigma_Cy : Real = 28.23690002309109;
                                attribute Cz : Real = 3.864906867966056;
                                attribute sigma_Cz : Real = 29.057750463592832;
                                attribute Ixx : Real = 1.2407586676459126;
                                attribute sigma_Ixx : Real = 0.37074144170588635;
                                attribute Iyy : Real = 1.2054609125229616;
                                attribute sigma_Iyy : Real = 0.3723953238821935;
                                attribute Izz : Real = 1.275079346344032;
                                attribute sigma_Izz : Real = 0.37017423652493897;
                                attribute Ixy : Real = -0.036854777886873635;
                                attribute sigma_Ixy : Real = 0.02351283871158888;
                                attribute Ixz : Real = 0.061095103961103514;
                                attribute sigma_Ixz : Real = 0.022566176940390956;
                                attribute Iyz : Real = 0.07972386482844457;
                                attribute sigma_Iyz : Real = 0.02209918015384651;
                            }
                            part <'C.1.1.2.3.4.2.3'> 'Part 240' {
                                attribute POIconv : String = "-";
                                attribute Ipoint : Boolean = false;
                                attribute mass : Real = 0.2003024841635488;
                                attribute sigma_mass : Real = 0.28909372274994966;
                                attribute Cx : Real = -93.90502953901887;
                                attribute sigma_Cx : Real = 28.721044428837228;
                                attribute Cy : Real = 34.372543124482036;
                                attribute sigma_Cy : Real = 28.23690002309109;
                                attribute Cz : Real = 49.69749189913273;
                                attribute sigma_Cz : Real = 29.057750463592832;
                                attribute Ixx : Real = 0.28662027833267745;
                                attribute sigma_Ixx : Real = 0.37074144170588635;
                                attribute Iyy : Real = 0.29221896998465985;
                                attribute sigma_Iyy : Real = 0.3723953238821935;
                                attribute Izz : Real = 0.2688814984333837;
                                attribute sigma_Izz : Real = 0.37017423652493897;
                                attribute Ixy : Real = 0.012961118038136304;
                                attribute sigma_Ixy : Real = 0.02351283871158888;
                                attribute Ixz : Real = 0.001663460913538437;
                                attribute sigma_Ixz : Real = 0.022566176940390956;
                                attribute Iyz : Real = 0.001974934410863552;
                                attribute sigma_Iyz : Real = 0.02209918015384651;
                            }
                        }
                    }
                    part <'C.1.1.2.3.5'> 'Assembly 19' {
                        attribute POIconv : String = "-";
                        attribute Ipoint : Boolean = false;
                        attribute mass : Real = 6.064570502744056;
                        attribute sigma_mass : Real = 1.0014500319042867;
                        attribute Cx : Real = 16.50907667505881;
                        attribute sigma_Cx : Real = 13.383536039059488;
                        attribute Cy : Real = -21.77190951307458;
                        attribute sigma_Cy : Real = 12.75584356790396;
                        attribute Cz : Real = 12.809410167339315;
                        attribute sigma_Cz : Real = 13.009497008728966;
                        attribute Ixx : Real = 35216.20402834881;
                        attribute sigma_Ixx : Real = 10474.670755988576;
                        attribute Iyy : Real = 36967.02321501229;
                        attribute sigma_Iyy : Real = 12381.389666531612;
                        attribute Izz : Real = 37435.859347399455;
                        attribute sigma_Izz : Real = 11407.983675733878;
                        attribute Ixy : Real = -83.43151290140759;
                        attribute sigma_Ixy : Real = 5471.428558425191;
                        attribute Ixz : Real = 8061.855785321939;
                        attribute sigma_Ixz : Real = 6132.6736687709445;
                        attribute Iyz : Real = 3079.5469911087785;
                        attribute sigma_Iyz : Real = 5089.643165724998;
                        part <'C.1.1.2.3.5.1'> 'Subassembly 70' {
                            attribute POIconv : String = "-";
                            attribute Ipoint : Boolean = false;
                            attribute mass : Real = 0.672759840320563;
                            attribute sigma_mass : Real = 0.40884026350990615;
                            attribute Cx : Real = 61.867224221825836;
                            attribute sigma_Cx : Real = 20.77484999417757;
                            attribute Cy : Real = -14.017417635788297;
                            attribute sigma_Cy : Real = 41.97417473763255;
                            attribute Cz : Real = -7.775784225151657;
                            attribute sigma_Cz : Real = 23.560225738771372;
                            attribute Ixx : Real = 2432.0457836145797;
                            attribute sigma_Ixx : Real = 2353.9124040586244;
                            attribute Iyy : Real = 191.94646023260879;
                            attribute sigma_Iyy : Real = 475.69161424923004;
                            attribute Izz : Real = 2243.2567907699813;
                            attribute sigma_Izz : Real = 2209.642386802378;
                            attribute Ixy : Real = 51.99226795199533;
                            attribute sigma_Ixy : Real = 771.8957347904066;
                            attribute Ixz : Real = -15.104256847318748;
                            attribute sigma_Ixz : Real = 225.41301125102586;
                            attribute Iyz : Real = 652.5754274766327;
                            attribute sigma_Iyz : Real = 935.764966388452;
                            part <'C.1.1.2.3.5.1.1'> 'Part 241' {
                                attribute POIconv : String = "-";
                                attribute Ipoint : Boolean = false;
                                attribute mass : Real = 0.40747015800722874;
                                attribute sigma_mass : Real = 0.28909372274994966;
                                attribute Cx : Real = 60.78723571263254;
                                attribute sigma_Cx : Real = 28.721044428837228;
                                attribute Cy : Real = 32.55494451150298;
                                attribute sigma_Cy : Real = 28.23690002309109;
                                attribute Cz : Real = -21.33576483465731;
                                attribute sigma_Cz : Real = 29.057750463592832;
                                attribute Ixx : Real = 0.4791398664944725;
                                attribute sigma_Ixx : Real = 0.37074144170588635;
                                attribute Iyy : Real = 0.4639180009684186;
                                attribute sigma_Iyy : Real = 0.3723953238821935;
                                attribute Izz : Real = 0.4648673295844197;
                                attribute sigma_Izz : Real = 0.37017423652493897;
                                attribute Ixy : Real = 0.026220854424162734;
                                attribute sigma_Ixy : Real = 0.02351283871158888;
                                attribute Ixz : Real = 0.031630515653453;
                                attribute sigma_Ixz : Real = 0.022566176940390956;
                                attribute Iyz : Real = 0.012390263391158172;
                                attribute sigma_Iyz : Real = 0.02209918015384651;
                            }
                            part <'C.1.1.2.3.5.1.2'> 'Part 242' {
                                attribute POIconv : String = "+";
                                attribute Ipoint : Boolean = false;
                                attribute mass : Real = 0.2652896823133342;
                                attribute sigma_mass : Real = 0.28909372274994966;
                                attribute Cx : Real = 63.52602634578943;
                                attribute sigma_Cx : Real = 28.721044428837228;
                                attribute Cy : Real = -85.54996876046062;
                                attribute sigma_Cy : Real = 28.23690002309109;
                                attribute Cz : Real = 13.051589811220765;
                                attribute sigma_Cz : Real = 29.057750463592832;
                                attribute Ixx : Real = 0.3076657600595202;
                                attribute sigma_Ixx : Real = 0.37074144170588635;
                                attribute Iyy : Real = 0.2772827945777175;
                                attribute sigma_Iyy : Real = 0.3723953238821935;
                                attribute Izz : Real = 0.32772355994094815;
                                attribute sigma_Izz : Real = 0.37017423652493897;
                                attribute Ixy : Real = 0.007565802376756121;
                                attribute sigma_Ixy : Real = 0.02351283871158888;
                                attribute Ixz : Real = 0.003281872609789513;
                                attribute sigma_Ixz : Real = 0.022566176940390956;
                                attribute Iyz : Real = 0.000556871355465161;
                                attribute sigma_Iyz : Real = 0.02209918015384651;
                            }
                        }
                        part <'C.1.1.2.3.5.2'> 'Subassembly 71' {
                            attribute POIconv : String = "-";
                            attribute Ipoint : Boolean = false;
                            attribute mass : Real = 1.8645965582812205;
                            attribute sigma_mass : Real = 0.5007250159521434;
                            attribute Cx : Real = 24.761844493038083;
                            attribute sigma_Cx : Real = 18.300911269714792;
                            attribute Cy : Real = -21.12554725379609;
                            attribute sigma_Cy : Real = 21.14036631658685;
                            attribute Cz : Real = -22.155330813830894;
                            attribute sigma_Cz : Real = 18.28056202008535;
                            attribute Ixx : Real = 5805.816790378122;
                            attribute sigma_Ixx : Real = 3903.599959309232;
                            attribute Iyy : Real = 2799.8362826090925;
                            attribute sigma_Iyy : Real = 2521.3883182262384;
                            attribute Izz : Real = 5980.247337650177;
                            attribute sigma_Izz : Real = 3904.828660391052;
                            attribute Ixy : Real = 1787.9648680110163;
                            attribute sigma_Ixy : Real = 1856.8746080158855;
                            attribute Ixz : Real = 637.2838863129118;
                            attribute sigma_Ixz : Real = 1234.7523894235007;
                            attribute Iyz : Real = -2325.8234388035676;
                            attribute sigma_Iyz : Real = 1892.2679493032624;
                            part <'C.1.1.2.3.5.2.1'> 'Part 243' {
                                attribute POIconv : String = "-";
                                attribute Ipoint : Boolean = false;
                                attribute mass : Real = 0.6740902617666871;
                                attribute sigma_mass : Real = 0.28909372274994966;
                                attribute Cx : Real = 6.337791075929999;
                                attribute sigma_Cx : Real = 28.721044428837228;
                                attribute Cy : Real = -39.97856080532074;
                                attribute sigma_Cy : Real = 28.23690002309109;
                                attribute Cz : Real = -41.56942963600159;
                                attribute sigma_Cz : Real = 29.057750463592832;
                                attribute Ixx : Real = 0.9120442700703385;
                                attribute sigma_Ixx : Real = 0.37074144170588635;
                                attribute Iyy : Real = 0.8352067696535924;
                                attribute sigma_Iyy : Real = 0.3723953238821935;
                                attribute Izz : Real = 0.8566534960006296;
                                attribute sigma_Izz : Real = 0.37017423652493897;
                                attribute Ixy : Real = 0.10909237505333497;
                                attribute sigma_Ixy : Real = 0.02351283871158888;
                                attribute Ixz : Real = -0.07060637082347898;
                                attribute sigma_Ixz : Real = 0.022566176940390956;
                                attribute Iyz : Real = -0.0173487109896762;
                                attribute sigma_Iyz : Real = 0.02209918015384651;
                            }
                            part <'C.1.1.2.3.5.2.2'> 'Part 244' {
                                attribute POIconv : String = "+";
                                attribute Ipoint : Boolean = false;
                                attribute mass : Real = 0.5944403135681059;
                                attribute sigma_mass : Real = 0.28909372274994966;
                                attribute Cx : Real = 66.01294544525445;
                                attribute sigma_Cx : Real = 28.721044428837228;
                                attribute Cy : Real = -69.33551244437695;
                                attribute sigma_Cy : Real = 28.23690002309109;
                                attribute Cz : Real = -38.90138026326895;
                                attribute sigma_Cz : Real = 29.057750463592832;
                                attribute Ixx : Real = 0.6950740749304091;
                                attribute sigma_Ixx : Real = 0.37074144170588635;
                                attribute Iyy : Real = 0.7852348276637291;
                                attribute sigma_Iyy : Real = 0.3723953238821935;
                                attribute Izz : Real = 0.6884946302404884;
                                attribute sigma_Izz : Real = 0.37017423652493897;
                                attribute Ixy : Real = 0.04391105620897433;
                                attribute sigma_Ixy : Real = 0.02351283871158888;
                                attribute Ixz : Real = 0.0010093464096753483;
                                attribute sigma_Ixz : Real = 0.022566176940390956;
                                attribute Iyz : Real = 0.047806464977739126;
                                attribute sigma_Iyz : Real = 0.02209918015384651;
                            }
                            part <'C.1.1.2.3.5.2.3'> 'Part 245' {
                                attribute POIconv : String = "+";
                                attribute Ipoint : Boolean = false;
                                attribute mass : Real = 0.5960659829464275;
                                attribute sigma_mass : Real = 0.28909372274994966;
                                attribute Cx : Real = 4.4589875265955925;
                                attribute sigma_Cx : Real = 28.721044428837228;
                                attribute Cy : Real = 48.273782432079315;
                                attribute sigma_Cy : Real = 28.23690002309109;
                                attribute Cz : Real = 16.500426270067692;
                                attribute sigma_Cz : Real = 29.057750463592832;
                                attribute Ixx : Real = 0.7515715892082144;
                                attribute sigma_Ixx : Real = 0.37074144170588635;
                                attribute Iyy : Real = 0.7149020029049378;
                                attribute sigma_Iyy : Real = 0.3723953238821935;
                                attribute Izz : Real = 0.6442586150956495;
                                attribute sigma_Izz : Real = 0.37017423652493897;
                                attribute Ixy : Real = -0.012609304131748197;
                                attribute sigma_Ixy : Real = 0.02351283871158888;
                                attribute Ixz : Real = -0.027343461633190867;
                                attribute sigma_Ixz : Real = 0.022566176940390956;
                                attribute Iyz : Real = 0.06778020234732142;
                                attribute sigma_Iyz : Real = 0.02209918015384651;
                            }
                        }
                        part <'C.1.1.2.3.5.3'> 'Subassembly 72' {
                            attribute POIconv : String = "-";
                            attribute Ipoint : Boolean = false;
                            attribute mass : Real = 1.934354973759968;
                            attribute sigma_mass : Real = 0.6464332159373649;
                            attribute Cx : Real = 26.32334016481258;
                            attribute sigma_Cx : Real = 25.840198772136112;
                            attribute Cy : Real = 17.837505433449213;
                            attribute sigma_Cy : Real = 19.989234944533685;
                            attribute Cz : Real = 2.2500838816994255;
                            attribute sigma_Cz : Real = 26.65104873968416;
                            attribute Ixx : Real = 10465.97712216351;
                            attribute sigma_Ixx : Real = 5913.790953611463;
                            attribute Iyy : Real = 11032.561570196236;
                            attribute sigma_Iyy : Real = 8253.319423823186;
                            attribute Izz : Real = 7860.865273248677;
                            attribute sigma_Izz : Real = 6035.366022771283;
                            attribute Ixy : Real = 3178.3017237025056;
                            attribute sigma_Ixy : Real = 2416.554566383518;
                            attribute Ixz : Real = 2771.327406479765;
                            attribute sigma_Ixz : Real = 3983.0376563463965;
                            attribute Iyz : Real = -1334.8952249673694;
                            attribute sigma_Iyz : Real = 2456.65839473334;
                            part <'C.1.1.2.3.5.3.1'> 'Part 246' {
                                attribute POIconv : String = "-";
                                attribute Ipoint : Boolean = false;
                                attribute mass : Real = 0.426708983233897;
                                attribute sigma_mass : Real = 0.28909372274994966;
                                attribute Cx : Real = 54.957071831449866;
                                attribute sigma_Cx : Real = 28.721044428837228;
                                attribute Cy : Real = -26.894796872511506;
                                attribute sigma_Cy : Real = 28.23690002309109;
                                attribute Cz : Real = 40.740666817873716;
                                attribute sigma_Cz : Real = 29.057750463592832;
                                attribute Ixx : Real = 0.5666966112309123;
                                attribute sigma_Ixx : Real = 0.37074144170588635;
                                attribute Iyy : Real = 0.45225350431721256;
                                attribute sigma_Iyy : Real = 0.3723953238821935;
                                attribute Izz : Real = 0.5075383730044312;
                                attribute sigma_Izz : Real = 0.37017423652493897;
                                attribute Ixy : Real = 0.03395526593589006;
                                attribute sigma_Ixy : Real = 0.02351283871158888;
                                attribute Ixz : Real = -0.0037670822160265614;
                                attribute sigma_Ixz : Real = 0.022566176940390956;
                                attribute Iyz : Real = -0.024623832317804326;
                                attribute sigma_Iyz : Real = 0.02209918015384651;
                            }
                            part <'C.1.1.2.3.5.3.2'> 'Part 247' {
                                attribute POIconv : String = "-";
                                attribute Ipoint : Boolean = false;
                                attribute mass : Real = 0.03967274279939011;
                                attribute sigma_mass : Real = 0.28909372274994966;
                                attribute Cx : Real = -86.93004208616912;
                                attribute sigma_Cx : Real = 28.721044428837228;
                                attribute Cy : Real = -4.279834823682904;
                                attribute sigma_Cy : Real = 28.23690002309109;
                                attribute Cz : Real = -92.0446497388184;
                                attribute sigma_Cz : Real = 29.057750463592832;
                                attribute Ixx : Real = 0.052361918914424724;
                                attribute sigma_Ixx : Real = 0.37074144170588635;
                                attribute Iyy : Real = 0.05453069445344211;
                                attribute sigma_Iyy : Real = 0.3723953238821935;
                                attribute Izz : Real = 0.05101928682565523;
                                attribute sigma_Izz : Real = 0.37017423652493897;
                                attribute Ixy : Real = -0.0006893305535136083;
                                attribute sigma_Ixy : Real = 0.02351283871158888;
                                attribute Ixz : Real = -0.00018528774769578868;
                                attribute sigma_Ixz : Real = 0.022566176940390956;
                                attribute Iyz : Real = 0.00012095919189205661;
                                attribute sigma_Iyz : Real = 0.02209918015384651;
                            }
                            part <'C.1.1.2.3.5.3.3'> 'Part 248' {
                                attribute POIconv : String = "+";
                                attribute Ipoint : Boolean = false;
                                attribute mass : Real = 0.28528343165386466;
                                attribute sigma_mass : Real = 0.28909372274994966;
                                attribute Cx : Real = 13.421092322096229;
                                attribute sigma_Cx : Real = 28.721044428837228;
                                attribute Cy : Real = 3.1691616401076317;
                                attribute sigma_Cy : Real = 28.23690002309109;
                                attribute Cz : Real = 67.5136974081397;
                                attribute sigma_Cz : Real = 29.057750463592832;
                                attribute Ixx : Real = 0.27782003406544536;
                                attribute sigma_Ixx : Real = 0.37074144170588635;
                                attribute Iyy : Real = 0.36603044168395876;
                                attribute sigma_Iyy : Real = 0.3723953238821935;
                                attribute Izz : Real = 0.375824505232686;
                                attribute sigma_Izz : Real = 0.37017423652493897;
                                attribute Ixy : Real = -0.001901370304835307;
                                attribute sigma_Ixy : Real = 0.02351283871158888;
                                attribute Ixz : Real = 0.002387921735145522;
                                attribute sigma_Ixz : Real = 0.022566176940390956;
                                attribute Iyz : Real = -0.015419167725190856;
                                attribute sigma_Iyz : Real = 0.02209918015384651;
                            }
                            part <'C.1.1.2.3.5.3.4'> 'Part 249' {
                                attribute POIconv : String = "+";
                                attribute Ipoint : Boolean = false;
                                attribute mass : Real = 0.7154089570406359;
                                attribute sigma_mass : Real = 0.28909372274994966;
                                attribute Cx : Real = 65.5456108506769;
                                attribute sigma_Cx : Real = 28.721044428837228;
                                attribute Cy : Real = 3.2566203270107508;
                                attribute sigma_Cy : Real = 28.23690002309109;
                                attribute Cz : Real = -69.9621846433729;
                                attribute sigma_Cz : Real = 29.057750463592832;
                                attribute Ixx : Real = 0.8590745322381049;
                                attribute sigma_Ixx : Real = 0.37074144170588635;
                                attribute Iyy : Real = 0.8258846949842853;
                                attribute sigma_Iyy : Real = 0.3723953238821935;
                                attribute Izz : Real = 0.9410905476130074;
                                attribute sigma_Izz : Real = 0.37017423652493897;
                                attribute Ixy : Real = -0.03242001221496807;
                                attribute sigma_Ixy : Real = 0.02351283871158888;
                                attribute Ixz : Real = 0.005518777833620126;
                                attribute sigma_Ixz : Real = 0.022566176940390956;
                                attribute Iyz : Real = -0.006471231020192947;
                                attribute sigma_Iyz : Real = 0.02209918015384651;
                            }
                            part <'C.1.1.2.3.5.3.5'> 'Part 250' {
                                attribute POIconv : String = "+";
                                attribute Ipoint : Boolean = false;
                                attribute mass : Real = 0.46728085903218014;
                                attribute sigma_mass : Real = 0.28909372274994966;
                                attribute Cx : Real = -42.38130250014365;
                                attribute sigma_Cx : Real = 28.721044428837228;
                                attribute Cy : Real = 91.84238146990538;
                                attribute sigma_Cy : Real = 28.23690002309109;
                                attribute Cz : Real = 45.81987471319735;
                                attribute sigma_Cz : Real = 29.057750463592832;
                                attribute Ixx : Real = 0.6514667621166179;
                                attribute sigma_Ixx : Real = 0.37074144170588635;
                                attribute Iyy : Real = 0.6869592564301479;
                                attribute sigma_Iyy : Real = 0.3723953238821935;
                                attribute Izz : Real = 0.6054931263830541;
                                attribute sigma_Izz : Real = 0.37017423652493897;
                                attribute Ixy : Real = -0.03015966653876525;
                                attribute sigma_Ixy : Real = 0.02351283871158888;
                                attribute Ixz : Real = -0.024446808654346737;
                                attribute sigma_Ixz : Real = 0.022566176940390956;
                                attribute Iyz : Real = -0.003821265151584969;
                                attribute sigma_Iyz : Real = 0.02209918015384651;
                            }
                        }
                        part <'C.1.1.2.3.5.4'> 'Subassembly 73' {
                            attribute POIconv : String = "-";
                            attribute Ipoint : Boolean = false;
                            attribute mass : Real = 1.5928591303823052;
                            attribute sigma_mass : Real = 0.40884026350990615;
                            attribute Cx : Real = -24.227414536263808;
                            attribute sigma_Cx : Real = 28.432138411619437;
                            attribute Cy : Real = -73.90507231874194;
                            attribute sigma_Cy : Real = 20.030909958761136;
                            attribute Cz : Real = 75.25656020718766;
                            attribute sigma_Cz : Real = 20.61464281647328;
                            attribute Ixx : Real = 115.2513227674228;
                            attribute sigma_Ixx : Real = 545.1640698353752;
                            attribute Iyy : Real = 9610.088892812499;
                            attribute sigma_Iyy : Real = 5599.496883762936;
                            attribute Izz : Real = 9605.547211309613;
                            attribute sigma_Izz : Real = 5597.132464640766;
                            attribute Ixy : Real = -720.3687041400841;
                            attribute sigma_Ixy : Real = 2475.6920426742595;
                            attribute Ixz : Real = -750.3517005918521;
                            attribute sigma_Ixz : Real = 2548.0213294725863;
                            attribute Iyz : Real = -56.542413594810284;
                            attribute sigma_Iyz : Real = 272.2632593704321;
                            part <'C.1.1.2.3.5.4.1'> 'Part 251' {
                                attribute POIconv : String = "-";
                                attribute Ipoint : Boolean = false;
                                attribute mass : Real = 0.7736773352290038;
                                attribute sigma_mass : Real = 0.28909372274994966;
                                attribute Cx : Real = 55.44500448741019;
                                attribute sigma_Cx : Real = 28.721044428837228;
                                attribute Cy : Real = -67.89552294649184;
                                attribute sigma_Cy : Real = 28.23690002309109;
                                attribute Cz : Real = 81.51691113598645;
                                attribute sigma_Cz : Real = 29.057750463592832;
                                attribute Ixx : Real = 0.9450998219769743;
                                attribute sigma_Ixx : Real = 0.37074144170588635;
                                attribute Iyy : Real = 0.9361747651469021;
                                attribute sigma_Iyy : Real = 0.3723953238821935;
                                attribute Izz : Real = 0.9812421124642215;
                                attribute sigma_Izz : Real = 0.37017423652493897;
                                attribute Ixy : Real = -0.034573533211430515;
                                attribute sigma_Ixy : Real = 0.02351283871158888;
                                attribute Ixz : Real = -0.05875326049368346;
                                attribute sigma_Ixz : Real = 0.022566176940390956;
                                attribute Iyz : Real = 0.0049728838083378775;
                                attribute sigma_Iyz : Real = 0.02209918015384651;
                            }
                            part <'C.1.1.2.3.5.4.2'> 'Part 252' {
                                attribute POIconv : String = "-";
                                attribute Ipoint : Boolean = false;
                                attribute mass : Real = 0.8191817951533013;
                                attribute sigma_mass : Real = 0.28909372274994966;
                                attribute Cx : Real = -99.47413657791913;
                                attribute sigma_Cx : Real = 28.721044428837228;
                                attribute Cy : Real = -79.58079921081662;
                                attribute sigma_Cy : Real = 28.23690002309109;
                                attribute Cz : Real = 69.34396345168352;
                                attribute sigma_Cz : Real = 29.057750463592832;
                                attribute Ixx : Real = 1.0165200114908017;
                                attribute sigma_Ixx : Real = 0.37074144170588635;
                                attribute Iyy : Real = 0.8619024267732524;
                                attribute sigma_Iyy : Real = 0.3723953238821935;
                                attribute Izz : Real = 0.9045909438979252;
                                attribute sigma_Izz : Real = 0.37017423652493897;
                                attribute Ixy : Real = -0.04499799537123948;
                                attribute sigma_Ixy : Real = 0.02351283871158888;
                                attribute Ixz : Real = 0.05661484550008761;
                                attribute sigma_Ixz : Real = 0.022566176940390956;
                                attribute Iyz : Real = 0.050151234001809805;
                                attribute sigma_Iyz : Real = 0.02209918015384651;
                            }
                        }
                    }
                }
            }
            part <'C.1.1.3'> 'Element 3' {
                attribute POIconv : String = "-";
                attribute Ipoint : Boolean = false;
                attribute mass : Real = 124.21314944311953;
                attribute sigma_mass : Real = 4.5342578677466605;
                attribute Cx : Real = 3.7271956212864645;
                attribute sigma_Cx : Real = 3.088007854312033;
                attribute Cy : Real = 7.282725153743474;
                attribute sigma_Cy : Real = 2.9313484185990344;
                attribute Cz : Real = 0.036789295927028016;
                attribute sigma_Cz : Real = 3.06794248468618;
                attribute Ixx : Real = 732250.0763650603;
                attribute sigma_Ixx : Real = 54406.47144448591;
                attribute Iyy : Real = 773959.428078013;
                attribute sigma_Iyy : Real = 58036.15832067158;
                attribute Izz : Real = 737221.3559228815;
                attribute sigma_Izz : Real = 55279.2817655689;
                attribute Ixy : Real = -12285.795577943542;
                attribute sigma_Ixy : Real = 25085.93719382096;
                attribute Ixz : Real = 33805.80546019256;
                attribute sigma_Ixz : Real = 26789.40014291999;
                attribute Iyz : Real = 6819.345597538704;
                attribute sigma_Iyz : Real = 25179.22372046592;
                part <'C.1.1.3.1'> 'Subsystem 6' {
                    attribute POIconv : String = "-";
                    attribute Ipoint : Boolean = false;
                    attribute mass : Real = 21.954797007077605;
                    attribute sigma_mass : Real = 1.7820933926902205;
                    attribute Cx : Real = 3.5817450438169205;
                    attribute sigma_Cx : Real = 7.203619353167992;
                    attribute Cy : Real = 31.355890453945488;
                    attribute sigma_Cy : Real = 6.120720597889054;
                    attribute Cz : Real = -14.190464322917729;
                    attribute sigma_Cz : Real = 7.207565990613079;
                    attribute Ixx : Real = 109609.11228444966;
                    attribute sigma_Ixx : Real = 19735.44376745105;
                    attribute Iyy : Real = 159531.60096202645;
                    attribute sigma_Iyy : Real = 24744.35083083119;
                    attribute Izz : Real = 113961.6772143449;
                    attribute sigma_Izz : Real = 20418.002786741454;
                    attribute Ixy : Real = 9129.865924363376;
                    attribute sigma_Ixy : Real = 9095.287475116693;
                    attribute Ixz : Real = 7716.417856287842;
                    attribute sigma_Ixz : Real = 11609.914750308068;
                    attribute Iyz : Real = -10442.849615141573;
                    attribute sigma_Iyz : Real = 8718.801558885412;
                    part <'C.1.1.3.1.1'> 'Assembly 20' {
                        attribute POIconv : String = "-";
                        attribute Ipoint : Boolean = false;
                        attribute mass : Real = 4.73517044808832;
                        attribute sigma_mass : Real = 0.8176805270198123;
                        attribute Cx : Real = -2.664654332809981;
                        attribute sigma_Cx : Real = 13.785598927091721;
                        attribute Cy : Real = 41.02021658167296;
                        attribute sigma_Cy : Real = 13.675646323798304;
                        attribute Cz : Real = -6.997706504444773;
                        attribute sigma_Cz : Real = 15.23105115252286;
                        attribute Ixx : Real = 28420.496424833866;
                        attribute sigma_Ixx : Real = 9672.070764435859;
                        attribute Iyy : Real = 32489.447081705668;
                        attribute sigma_Iyy : Real = 10808.376023849916;
                        attribute Izz : Real = 20744.024213562;
                        attribute sigma_Izz : Real = 7981.348870993414;
                        attribute Ixy : Real = 2428.6039444630674;
                        attribute sigma_Ixy : Real = 3522.2977921952465;
                        attribute Ixz : Real = -6878.676018570835;
                        attribute sigma_Ixz : Real = 5218.782726556674;
                        attribute Iyz : Real = -1411.3136397420951;
                        attribute sigma_Iyz : Real = 4211.835459836796;
                        part <'C.1.1.3.1.1.1'> 'Subassembly 74' {
                            attribute POIconv : String = "-";
                            attribute Ipoint : Boolean = false;
                            attribute mass : Real = 2.6416965171946214;
                            attribute sigma_mass : Real = 0.6464332159373649;
                            attribute Cx : Real = 10.901826405449638;
                            attribute sigma_Cx : Real = 19.239771017933617;
                            attribute Cy : Real = 33.42184311525554;
                            attribute sigma_Cy : Real = 19.390828347833548;
                            attribute Cz : Real = 6.475037744243574;
                            attribute sigma_Cz : Real = 18.91720123833353;
                            attribute Ixx : Real = 15359.000739854351;
                            attribute sigma_Ixx : Real = 7008.334677131809;
                            attribute Iyy : Real = 18652.747279766645;
                            attribute sigma_Iyy : Real = 8261.29699636686;
                            attribute Izz : Real = 15454.332244647787;
                            attribute sigma_Izz : Real = 6950.658856517474;
                            attribute Ixy : Real = 145.17539578827362;
                            attribute sigma_Ixy : Real = 2937.068755917562;
                            attribute Ixz : Real = -9157.328823366823;
                            attribute sigma_Ixz : Real = 4106.044695149432;
                            attribute Iyz : Real = -458.1487756670187;
                            attribute sigma_Iyz : Real = 3000.977603770748;
                            part <'C.1.1.3.1.1.1.1'> 'Part 253' {
                                attribute POIconv : String = "+";
                                attribute Ipoint : Boolean = false;
                                attribute mass : Real = 0.35033208354143425;
                                attribute sigma_mass : Real = 0.28909372274994966;
                                attribute Cx : Real = 13.602188974618912;
                                attribute sigma_Cx : Real = 28.721044428837228;
                                attribute Cy : Real = -65.77278128825128;
                                attribute sigma_Cy : Real = 28.23690002309109;
                                attribute Cz : Real = -6.666752602905035;
                                attribute sigma_Cz : Real = 29.057750463592832;
                                attribute Ixx : Real = 0.3451315091971734;
                                attribute sigma_Ixx : Real = 0.37074144170588635;
                                attribute Iyy : Real = 0.37349270270549456;
                                attribute sigma_Iyy : Real = 0.3723953238821935;
                                attribute Izz : Real = 0.36684707891031126;
                                attribute sigma_Izz : Real = 0.37017423652493897;
                                attribute Ixy : Real = 0.002415436040320097;
                                attribute sigma_Ixy : Real = 0.02351283871158888;
                                attribute Ixz : Real = -0.027704416596818528;
                                attribute sigma_Ixz : Real = 0.022566176940390956;
                                attribute Iyz : Real = -0.009512960607667983;
                                attribute sigma_Iyz : Real = 0.02209918015384651;
                            }
                            part <'C.1.1.3.1.1.1.2'> 'Part 254' {
                                attribute POIconv : String = "+";
                                attribute Ipoint : Boolean = false;
                                attribute mass : Real = 0.37120659729721955;
                                attribute sigma_mass : Real = 0.28909372274994966;
                                attribute Cx : Real = -62.285100715234876;
                                attribute sigma_Cx : Real = 28.721044428837228;
                                attribute Cy : Real = 57.06980703398585;
                                attribute sigma_Cy : Real = 28.23690002309109;
                                attribute Cz : Real = -43.37607226334512;
                                attribute sigma_Cz : Real = 29.057750463592832;
                                attribute Ixx : Real = 0.49607162528760934;
                                attribute sigma_Ixx : Real = 0.37074144170588635;
                                attribute Iyy : Real = 0.4775353950779882;
                                attribute sigma_Iyy : Real = 0.3723953238821935;
                                attribute Izz : Real = 0.4539264988517809;
                                attribute sigma_Izz : Real = 0.37017423652493897;
                                attribute Ixy : Real = -0.005497845660090447;
                                attribute sigma_Ixy : Real = 0.02351283871158888;
                                attribute Ixz : Real = 0.017209049791670917;
                                attribute sigma_Ixz : Real = 0.022566176940390956;
                                attribute Iyz : Real = -0.02672127156081648;
                                attribute sigma_Iyz : Real = 0.02209918015384651;
                            }
                            part <'C.1.1.3.1.1.1.3'> 'Part 255' {
                                attribute POIconv : String = "+";
                                attribute Ipoint : Boolean = false;
                                attribute mass : Real = 0.6543512409906834;
                                attribute sigma_mass : Real = 0.28909372274994966;
                                attribute Cx : Real = -51.047305250540376;
                                attribute sigma_Cx : Real = 28.721044428837228;
                                attribute Cy : Real = 64.39496669918299;
                                attribute sigma_Cy : Real = 28.23690002309109;
                                attribute Cz : Real = -63.441044837236404;
                                attribute sigma_Cz : Real = 29.057750463592832;
                                attribute Ixx : Real = 0.7911021543726762;
                                attribute sigma_Ixx : Real = 0.37074144170588635;
                                attribute Iyy : Real = 0.7677910643895419;
                                attribute sigma_Iyy : Real = 0.3723953238821935;
                                attribute Izz : Real = 0.7822651732118955;
                                attribute sigma_Izz : Real = 0.37017423652493897;
                                attribute Ixy : Real = 0.05353398171293455;
                                attribute sigma_Ixy : Real = 0.02351283871158888;
                                attribute Ixz : Real = -0.022248246027141726;
                                attribute sigma_Ixz : Real = 0.022566176940390956;
                                attribute Iyz : Real = 0.05630771579297367;
                                attribute sigma_Iyz : Real = 0.02209918015384651;
                            }
                            part <'C.1.1.3.1.1.1.4'> 'Part 256' {
                                attribute POIconv : String = "+";
                                attribute Ipoint : Boolean = false;
                                attribute mass : Real = 0.9333964975576382;
                                attribute sigma_mass : Real = 0.28909372274994966;
                                attribute Cx : Real = 83.1282596103847;
                                attribute sigma_Cx : Real = 28.721044428837228;
                                attribute Cy : Real = 60.246955370530486;
                                attribute sigma_Cy : Real = 28.23690002309109;
                                attribute Cz : Real = 80.36078028380871;
                                attribute sigma_Cz : Real = 29.057750463592832;
                                attribute Ixx : Real = 1.1941203888105794;
                                attribute sigma_Ixx : Real = 0.37074144170588635;
                                attribute Iyy : Real = 0.9467571635607344;
                                attribute sigma_Iyy : Real = 0.3723953238821935;
                                attribute Izz : Real = 1.2086177127420223;
                                attribute sigma_Izz : Real = 0.37017423652493897;
                                attribute Ixy : Real = -0.10079783510275;
                                attribute sigma_Ixy : Real = 0.02351283871158888;
                                attribute Ixz : Real = 0.011651422040814175;
                                attribute sigma_Ixz : Real = 0.022566176940390956;
                                attribute Iyz : Real = -0.06477818727760966;
                                attribute sigma_Iyz : Real = 0.02209918015384651;
                            }
                            part <'C.1.1.3.1.1.1.5'> 'Part 257' {
                                attribute POIconv : String = "+";
                                attribute Ipoint : Boolean = false;
                                attribute mass : Real = 0.3324100978076458;
                                attribute sigma_mass : Real = 0.28909372274994966;
                                attribute Cx : Real = 8.922457927837968;
                                attribute sigma_Cx : Real = 28.721044428837228;
                                attribute Cy : Real = -24.73820853047073;
                                attribute sigma_Cy : Real = 28.23690002309109;
                                attribute Cz : Real = 6.15625623613596;
                                attribute sigma_Cz : Real = 29.057750463592832;
                                attribute Ixx : Real = 0.4767158223678171;
                                attribute sigma_Ixx : Real = 0.37074144170588635;
                                attribute Iyy : Real = 0.4287285618635684;
                                attribute sigma_Iyy : Real = 0.3723953238821935;
                                attribute Izz : Real = 0.4339084575214057;
                                attribute sigma_Izz : Real = 0.37017423652493897;
                                attribute Ixy : Real = 0.006328744820123114;
                                attribute sigma_Ixy : Real = 0.02351283871158888;
                                attribute Ixz : Real = 0.01758982153966447;
                                attribute sigma_Ixz : Real = 0.022566176940390956;
                                attribute Iyz : Real = -0.02893292084444509;
                                attribute sigma_Iyz : Real = 0.02209918015384651;
                            }
                        }
                        part <'C.1.1.3.1.1.2'> 'Subassembly 75' {
                            attribute POIconv : String = "-";
                            attribute Ipoint : Boolean = false;
                            attribute mass : Real = 2.0934739308936985;
                            attribute sigma_mass : Real = 0.5007250159521434;
                            attribute Cx : Real = -19.783818984432358;
                            attribute sigma_Cx : Real = 18.668924058292845;
                            attribute Cy : Real = 50.608392687601345;
                            attribute sigma_Cy : Real = 18.637049090377207;
                            attribute Cz : Real = -23.99858768743625;
                            attribute sigma_Cz : Real = 24.149099012418784;
                            attribute Ixx : Real = 11631.933203482122;
                            attribute sigma_Ixx : Real = 6199.840120361436;
                            attribute Iyy : Real = 11652.387732165082;
                            attribute sigma_Iyy : Real = 6322.237000863021;
                            attribute Izz : Real = 3844.9850234010464;
                            attribute sigma_Izz : Real = 3235.820051046183;
                            attribute Ixy : Real = 1667.4879635916295;
                            attribute sigma_Ixy : Real = 1596.9911652343908;
                            attribute Ixz : Real = 3370.782589135948;
                            attribute sigma_Ixz : Real = 2867.3747970863456;
                            attribute Iyz : Real = -1564.8496580401106;
                            attribute sigma_Iyz : Real = 2725.294123476129;
                            part <'C.1.1.3.1.1.2.1'> 'Part 258' {
                                attribute POIconv : String = "-";
                                attribute Ipoint : Boolean = false;
                                attribute mass : Real = 0.9713401052930858;
                                attribute sigma_mass : Real = 0.28909372274994966;
                                attribute Cx : Real = 11.97202461771667;
                                attribute sigma_Cx : Real = 28.721044428837228;
                                attribute Cy : Real = 19.448707485571504;
                                attribute sigma_Cy : Real = 28.23690002309109;
                                attribute Cz : Real = -68.73131752945483;
                                attribute sigma_Cz : Real = 29.057750463592832;
                                attribute Ixx : Real = 1.030563715857309;
                                attribute sigma_Ixx : Real = 0.37074144170588635;
                                attribute Iyy : Real = 1.0010890770162502;
                                attribute sigma_Iyy : Real = 0.3723953238821935;
                                attribute Izz : Real = 1.147349795278835;
                                attribute sigma_Izz : Real = 0.37017423652493897;
                                attribute Ixy : Real = 0.030591710421028935;
                                attribute sigma_Ixy : Real = 0.02351283871158888;
                                attribute Ixz : Real = -0.0042139216655627115;
                                attribute sigma_Ixz : Real = 0.022566176940390956;
                                attribute Iyz : Real = 0.040984992218540586;
                                attribute sigma_Iyz : Real = 0.02209918015384651;
                            }
                            part <'C.1.1.3.1.1.2.2'> 'Part 259' {
                                attribute POIconv : String = "+";
                                attribute Ipoint : Boolean = false;
                                attribute mass : Real = 0.6721225370683241;
                                attribute sigma_mass : Real = 0.28909372274994966;
                                attribute Cx : Real = -55.15542821958661;
                                attribute sigma_Cx : Real = 28.721044428837228;
                                attribute Cy : Real = 68.07067100889981;
                                attribute sigma_Cy : Real = 28.23690002309109;
                                attribute Cz : Real = 75.01546856947243;
                                attribute sigma_Cz : Real = 29.057750463592832;
                                attribute Ixx : Real = 0.6224034653634422;
                                attribute sigma_Ixx : Real = 0.37074144170588635;
                                attribute Iyy : Real = 0.6288802860472109;
                                attribute sigma_Iyy : Real = 0.3723953238821935;
                                attribute Izz : Real = 0.6216715156389743;
                                attribute sigma_Izz : Real = 0.37017423652493897;
                                attribute Ixy : Real = -0.002980722553823145;
                                attribute sigma_Ixy : Real = 0.02351283871158888;
                                attribute Ixz : Real = 0.0012678343995902587;
                                attribute sigma_Ixz : Real = 0.022566176940390956;
                                attribute Iyz : Real = -0.012983322297216344;
                                attribute sigma_Iyz : Real = 0.02209918015384651;
                            }
                            part <'C.1.1.3.1.1.2.3'> 'Part 260' {
                                attribute POIconv : String = "+";
                                attribute Ipoint : Boolean = false;
                                attribute mass : Real = 0.4500112885322887;
                                attribute sigma_mass : Real = 0.28909372274994966;
                                attribute Cx : Real = -35.49824417568743;
                                attribute sigma_Cx : Real = 28.721044428837228;
                                attribute Cy : Real = 91.78482885472476;
                                attribute sigma_Cy : Real = 28.23690002309109;
                                attribute Cz : Real = -75.32815379090607;
                                attribute sigma_Cz : Real = 29.057750463592832;
                                attribute Ixx : Real = 0.568529815188794;
                                attribute sigma_Ixx : Real = 0.37074144170588635;
                                attribute Iyy : Real = 0.5043313559220088;
                                attribute sigma_Iyy : Real = 0.3723953238821935;
                                attribute Izz : Real = 0.5860855112191878;
                                attribute sigma_Izz : Real = 0.37017423652493897;
                                attribute Ixy : Real = 0.023967253528599523;
                                attribute sigma_Ixy : Real = 0.02351283871158888;
                                attribute Ixz : Real = 0.0053934726510995795;
                                attribute sigma_Ixz : Real = 0.022566176940390956;
                                attribute Iyz : Real = 0.016128148044183502;
                                attribute sigma_Iyz : Real = 0.02209918015384651;
                            }
                        }
                    }
                    part <'C.1.1.3.1.2'> 'Assembly 21' {
                        attribute POIconv : String = "-";
                        attribute Ipoint : Boolean = false;
                        attribute mass : Real = 6.4585098842883015;
                        attribute sigma_mass : Real = 0.8176805270198123;
                        attribute Cx : Real = -27.422124617296184;
                        attribute sigma_Cx : Real = 13.156381164481877;
                        attribute Cy : Real = 25.88825502955012;
                        attribute sigma_Cy : Real = 11.038894113833761;
                        attribute Cz : Real = -21.866916856218445;
                        attribute sigma_Cz : Real = 12.423131694259718;
                        attribute Ixx : Real = 26626.645142350786;
                        attribute sigma_Ixx : Real = 10106.303250837092;
                        attribute Iyy : Real = 44296.751005499995;
                        attribute sigma_Iyy : Real = 12832.269823607736;
                        attribute Izz : Real = 33864.94211163425;
                        attribute sigma_Izz : Real = 11046.80896760236;
                        attribute Ixy : Real = 1334.8088086198022;
                        attribute sigma_Ixy : Real = 4961.151496385732;
                        attribute Ixz : Real = 3750.267910123922;
                        attribute sigma_Ixz : Real = 5966.326159012762;
                        attribute Iyz : Real = -7660.931059264119;
                        attribute sigma_Iyz : Real = 4767.96072088524;
                        part <'C.1.1.3.1.2.1'> 'Subassembly 76' {
                            attribute POIconv : String = "-";
                            attribute Ipoint : Boolean = false;
                            attribute mass : Real = 1.610968574834522;
                            attribute sigma_mass : Real = 0.40884026350990615;
                            attribute Cx : Real = 69.37372663420251;
                            attribute sigma_Cx : Real = 22.012081390018583;
                            attribute Cy : Real = 24.24372768667736;
                            attribute sigma_Cy : Real = 20.175403177398714;
                            attribute Cz : Real = -37.294047367439774;
                            attribute sigma_Cz : Real = 20.880982086162714;
                            attribute Ixx : Real = 131.08471800736248;
                            attribute sigma_Ixx : Real = 587.077497312871;
                            attribute Iyy : Real = 1653.8410119811933;
                            attribute sigma_Iyy : Real = 2124.27653429017;
                            attribute Izz : Real = 1534.1974252451278;
                            attribute sigma_Izz : Real = 2040.8811255544156;
                            attribute Ixy : Real = -86.63789692751718;
                            attribute sigma_Ixy : Real = 982.0778779467179;
                            attribute Ixz : Real = 435.57880239021455;
                            attribute sigma_Ixz : Real = 1054.7762493652856;
                            attribute Iyz : Real = 24.707862652956624;
                            attribute sigma_Iyz : Real = 285.4271821563574;
                            part <'C.1.1.3.1.2.1.1'> 'Part 261' {
                                attribute POIconv : String = "-";
                                attribute Ipoint : Boolean = false;
                                attribute mass : Real = 0.9208727725881618;
                                attribute sigma_mass : Real = 0.28909372274994966;
                                attribute Cx : Real = 96.02795224636793;
                                attribute sigma_Cx : Real = 28.721044428837228;
                                attribute Cy : Real = 25.754825212061405;
                                attribute sigma_Cy : Real = 28.23690002309109;
                                attribute Cz : Real = -44.89626814611256;
                                attribute sigma_Cz : Real = 29.057750463592832;
                                attribute Ixx : Real = 1.1780845293487074;
                                attribute sigma_Ixx : Real = 0.37074144170588635;
                                attribute Iyy : Real = 1.468029121522247;
                                attribute sigma_Iyy : Real = 0.3723953238821935;
                                attribute Izz : Real = 1.1407529997326853;
                                attribute sigma_Izz : Real = 0.37017423652493897;
                                attribute Ixy : Real = -0.04012158849002713;
                                attribute sigma_Ixy : Real = 0.02351283871158888;
                                attribute Ixz : Real = 0.010713916873302944;
                                attribute sigma_Ixz : Real = 0.022566176940390956;
                                attribute Iyz : Real = 0.002397577920364697;
                                attribute sigma_Iyz : Real = 0.02209918015384651;
                            }
                            part <'C.1.1.3.1.2.1.2'> 'Part 262' {
                                attribute POIconv : String = "+";
                                attribute Ipoint : Boolean = false;
                                attribute mass : Real = 0.6900958022463601;
                                attribute sigma_mass : Real = 0.28909372274994966;
                                attribute Cx : Real = 33.805982908234;
                                attribute sigma_Cx : Real = 28.721044428837228;
                                attribute Cy : Real = 22.227299585938454;
                                attribute sigma_Cy : Real = 28.23690002309109;
                                attribute Cz : Real = -27.14954554103315;
                                attribute sigma_Cz : Real = 29.057750463592832;
                                attribute Ixx : Real = 0.7588880408306196;
                                attribute sigma_Ixx : Real = 0.37074144170588635;
                                attribute Iyy : Real = 0.8862795417196262;
                                attribute sigma_Iyy : Real = 0.3723953238821935;
                                attribute Izz : Real = 0.9004089994697978;
                                attribute sigma_Izz : Real = 0.37017423652493897;
                                attribute Ixy : Real = 0.014127457032560888;
                                attribute sigma_Ixy : Real = 0.02351283871158888;
                                attribute Ixz : Real = 0.027891246430802874;
                                attribute sigma_Ixz : Real = 0.022566176940390956;
                                attribute Iyz : Real = -0.01039358433194291;
                                attribute sigma_Iyz : Real = 0.02209918015384651;
                            }
                        }
                        part <'C.1.1.3.1.2.2'> 'Subassembly 77' {
                            attribute POIconv : String = "-";
                            attribute Ipoint : Boolean = false;
                            attribute mass : Real = 3.6909713220461273;
                            attribute sigma_mass : Real = 0.5781874454998993;
                            attribute Cx : Real = -66.90261917407994;
                            attribute sigma_Cx : Real = 14.77137451055628;
                            attribute Cy : Real = 23.445848253993557;
                            attribute sigma_Cy : Real = 15.848723522168106;
                            attribute Cz : Real = -30.280304687863858;
                            attribute sigma_Cz : Real = 17.520008733970354;
                            attribute Ixx : Real = 22705.135491625617;
                            attribute sigma_Ixx : Real = 9559.4080127513;
                            attribute Iyy : Real = 16436.480072576032;
                            attribute sigma_Iyy : Real = 8011.234572313236;
                            attribute Izz : Real = 9616.892084907871;
                            attribute sigma_Izz : Real = 5712.5826187943085;
                            attribute Ixy : Real = 1499.8563123674571;
                            attribute sigma_Ixy : Real = 2751.2889705753087;
                            attribute Ixz : Real = 2332.518531502365;
                            attribute sigma_Ixz : Real = 3650.023763615649;
                            attribute Iyz : Real = -6970.275726506686;
                            attribute sigma_Iyz : Real = 4531.038461084472;
                            part <'C.1.1.3.1.2.2.1'> 'Part 263' {
                                attribute POIconv : String = "+";
                                attribute Ipoint : Boolean = false;
                                attribute mass : Real = 0.9413825466895942;
                                attribute sigma_mass : Real = 0.28909372274994966;
                                attribute Cx : Real = -84.61358374916017;
                                attribute sigma_Cx : Real = 28.721044428837228;
                                attribute Cy : Real = 45.72876738384366;
                                attribute sigma_Cy : Real = 28.23690002309109;
                                attribute Cz : Real = -69.54333679750562;
                                attribute sigma_Cz : Real = 29.057750463592832;
                                attribute Ixx : Real = 1.2695341479387285;
                                attribute sigma_Ixx : Real = 0.37074144170588635;
                                attribute Iyy : Real = 1.2036281343311614;
                                attribute sigma_Iyy : Real = 0.3723953238821935;
                                attribute Izz : Real = 1.1547955480858163;
                                attribute sigma_Izz : Real = 0.37017423652493897;
                                attribute Ixy : Real = -0.06875479925575317;
                                attribute sigma_Ixy : Real = 0.02351283871158888;
                                attribute Ixz : Real = -0.010738434992778009;
                                attribute sigma_Ixz : Real = 0.022566176940390956;
                                attribute Iyz : Real = 0.039220520668120984;
                                attribute sigma_Iyz : Real = 0.02209918015384651;
                            }
                            part <'C.1.1.3.1.2.2.2'> 'Part 264' {
                                attribute POIconv : String = "+";
                                attribute Ipoint : Boolean = false;
                                attribute mass : Real = 0.953823660824215;
                                attribute sigma_mass : Real = 0.28909372274994966;
                                attribute Cx : Real = -55.915615474805236;
                                attribute sigma_Cx : Real = 28.721044428837228;
                                attribute Cy : Real = -53.96787775680423;
                                attribute sigma_Cy : Real = 28.23690002309109;
                                attribute Cz : Real = -85.33980087377131;
                                attribute sigma_Cz : Real = 29.057750463592832;
                                attribute Ixx : Real = 0.9618780277315447;
                                attribute sigma_Ixx : Real = 0.37074144170588635;
                                attribute Iyy : Real = 0.9508211853745024;
                                attribute sigma_Iyy : Real = 0.3723953238821935;
                                attribute Izz : Real = 0.9059315953604018;
                                attribute sigma_Izz : Real = 0.37017423652493897;
                                attribute Ixy : Real = 0.0346433284407284;
                                attribute sigma_Ixy : Real = 0.02351283871158888;
                                attribute Ixz : Real = 0.024045305289706928;
                                attribute sigma_Ixz : Real = 0.022566176940390956;
                                attribute Iyz : Real = -0.013406080941731473;
                                attribute sigma_Iyz : Real = 0.02209918015384651;
                            }
                            part <'C.1.1.3.1.2.2.3'> 'Part 265' {
                                attribute POIconv : String = "-";
                                attribute Ipoint : Boolean = false;
                                attribute mass : Real = 0.9507657685515005;
                                attribute sigma_mass : Real = 0.28909372274994966;
                                attribute Cx : Real = -88.23057794943452;
                                attribute sigma_Cx : Real = 28.721044428837228;
                                attribute Cy : Real = 62.856541480869055;
                                attribute sigma_Cy : Real = 28.23690002309109;
                                attribute Cz : Real = 73.85254860855639;
                                attribute sigma_Cz : Real = 29.057750463592832;
                                attribute Ixx : Real = 1.245257917211919;
                                attribute sigma_Ixx : Real = 0.37074144170588635;
                                attribute Iyy : Real = 1.1715836147943077;
                                attribute sigma_Iyy : Real = 0.3723953238821935;
                                attribute Izz : Real = 1.088693176443494;
                                attribute sigma_Izz : Real = 0.37017423652493897;
                                attribute Ixy : Real = -0.023702967493313847;
                                attribute sigma_Ixy : Real = 0.02351283871158888;
                                attribute Ixz : Real = 0.06826779494755832;
                                attribute sigma_Ixz : Real = 0.022566176940390956;
                                attribute Iyz : Real = -0.0012854224717464267;
                                attribute sigma_Iyz : Real = 0.02209918015384651;
                            }
                            part <'C.1.1.3.1.2.2.4'> 'Part 266' {
                                attribute POIconv : String = "+";
                                attribute Ipoint : Boolean = false;
                                attribute mass : Real = 0.8449993459808175;
                                attribute sigma_mass : Real = 0.28909372274994966;
                                attribute Cx : Real = -35.575941717252135;
                                attribute sigma_Cx : Real = 28.721044428837228;
                                attribute Cy : Real = 41.66119294241071;
                                attribute sigma_Cy : Real = 28.23690002309109;
                                attribute Cz : Real = -41.5553062222898;
                                attribute sigma_Cz : Real = 29.057750463592832;
                                attribute Ixx : Real = 1.000740602264269;
                                attribute sigma_Ixx : Real = 0.37074144170588635;
                                attribute Iyy : Real = 1.0098566950774743;
                                attribute sigma_Iyy : Real = 0.3723953238821935;
                                attribute Izz : Real = 0.8955893944788258;
                                attribute sigma_Izz : Real = 0.37017423652493897;
                                attribute Ixy : Real = -0.07052705647277463;
                                attribute sigma_Ixy : Real = 0.02351283871158888;
                                attribute Ixz : Real = -0.02726766454590198;
                                attribute sigma_Ixz : Real = 0.022566176940390956;
                                attribute Iyz : Real = -0.029959999045877584;
                                attribute sigma_Iyz : Real = 0.02209918015384651;
                            }
                        }
                        part <'C.1.1.3.1.2.3'> 'Subassembly 78' {
                            attribute POIconv : String = "-";
                            attribute Ipoint : Boolean = false;
                            attribute mass : Real = 1.1565699874076527;
                            attribute sigma_mass : Real = 0.40884026350990615;
                            attribute Cx : Real = -36.25315210585073;
                            attribute sigma_Cx : Real = 25.79154634433539;
                            attribute Cy : Real = 35.97336476105772;
                            attribute sigma_Cy : Real = 20.916180192007538;
                            attribute Cz : Real = 26.471010178021967;
                            attribute sigma_Cz : Real = 22.387183939223892;
                            attribute Ixx : Real = 299.3560818042556;
                            attribute sigma_Ixx : Real = 739.4714123667427;
                            attribute Iyy : Real = 1922.1522706981807;
                            attribute sigma_Iyy : Real = 2054.1145948907065;
                            attribute Izz : Real = 1632.6261237822932;
                            attribute sigma_Izz : Real = 1859.7074668081862;
                            attribute Ixy : Real = -81.94453028604936;
                            attribute sigma_Ixy : Real = 825.5806880745282;
                            attribute Ixz : Real = -691.1588926463769;
                            attribute sigma_Ixz : Real = 980.1209328414119;
                            attribute Iyz : Real = -34.82680272011376;
                            attribute sigma_Iyz : Real = 352.8544730138323;
                            part <'C.1.1.3.1.2.3.1'> 'Part 267' {
                                attribute POIconv : String = "-";
                                attribute Ipoint : Boolean = false;
                                attribute mass : Real = 0.3990789232524112;
                                attribute sigma_mass : Real = 0.28909372274994966;
                                attribute Cx : Real = -87.92814319022;
                                attribute sigma_Cx : Real = 28.721044428837228;
                                attribute Cy : Real = 33.370931120589375;
                                attribute sigma_Cy : Real = 28.23690002309109;
                                attribute Cz : Real = 4.518514405936003;
                                attribute sigma_Cz : Real = 29.057750463592832;
                                attribute Ixx : Real = 0.4993905052332954;
                                attribute sigma_Ixx : Real = 0.37074144170588635;
                                attribute Iyy : Real = 0.4680890662663117;
                                attribute sigma_Iyy : Real = 0.3723953238821935;
                                attribute Izz : Real = 0.5236262643573312;
                                attribute sigma_Izz : Real = 0.37017423652493897;
                                attribute Ixy : Real = 0.035250958535723916;
                                attribute sigma_Ixy : Real = 0.02351283871158888;
                                attribute Ixz : Real = -0.01848529808548552;
                                attribute sigma_Ixz : Real = 0.022566176940390956;
                                attribute Iyz : Real = -0.007443518717315208;
                                attribute sigma_Iyz : Real = 0.02209918015384651;
                            }
                            part <'C.1.1.3.1.2.3.2'> 'Part 268' {
                                attribute POIconv : String = "-";
                                attribute Ipoint : Boolean = false;
                                attribute mass : Real = 0.7574910641552415;
                                attribute sigma_mass : Real = 0.28909372274994966;
                                attribute Cx : Real = -9.028540784493089;
                                attribute sigma_Cx : Real = 28.721044428837228;
                                attribute Cy : Real = 37.34443890862167;
                                attribute sigma_Cy : Real = 28.23690002309109;
                                attribute Cz : Real = 38.036530604586005;
                                attribute sigma_Cz : Real = 29.057750463592832;
                                attribute Ixx : Real = 1.085988324908633;
                                attribute sigma_Ixx : Real = 0.37074144170588635;
                                attribute Iyy : Real = 0.9411251785101542;
                                attribute sigma_Iyy : Real = 0.3723953238821935;
                                attribute Izz : Real = 0.8765610911194566;
                                attribute sigma_Izz : Real = 0.37017423652493897;
                                attribute Ixy : Real = -0.036515027284567736;
                                attribute sigma_Ixy : Real = 0.02351283871158888;
                                attribute Ixz : Real = 0.08152323760279603;
                                attribute sigma_Ixz : Real = 0.022566176940390956;
                                attribute Iyz : Real = -0.008338097411659216;
                                attribute sigma_Iyz : Real = 0.02209918015384651;
                            }
                        }
                    }
                    part <'C.1.1.3.1.3'> 'Assembly 22' {
                        attribute POIconv : String = "-";
                        attribute Ipoint : Boolean = false;
                        attribute mass : Real = 7.178835646673571;
                        attribute sigma_mass : Real = 1.081689663197327;
                        attribute Cx : Real = 40.48911827052698;
                        attribute sigma_Cx : Real = 11.996177847307651;
                        attribute Cy : Real = 26.11918186797147;
                        attribute sigma_Cy : Real = 9.914369713705224;
                        attribute Cz : Real = -24.40753816147842;
                        attribute sigma_Cz : Real = 13.68328822676147;
                        attribute Ixx : Real = 36406.41559549707;
                        attribute sigma_Ixx : Real = 11474.992081328444;
                        attribute Iyy : Real = 47069.07744970075;
                        attribute sigma_Iyy : Real = 13724.623818036755;
                        attribute Izz : Real = 25148.6563808691;
                        attribute sigma_Izz : Real = 9447.171022015764;
                        attribute Ixy : Real = 6836.25507176213;
                        attribute sigma_Ixy : Real = 4024.3046271796825;
                        attribute Ixz : Real = 3024.306995322408;
                        attribute sigma_Ixz : Real = 6052.374942422058;
                        attribute Iyz : Real = 2887.6857650339653;
                        attribute sigma_Iyz : Real = 4766.7342356121435;
                        part <'C.1.1.3.1.3.1'> 'Subassembly 79' {
                            attribute POIconv : String = "-";
                            attribute Ipoint : Boolean = false;
                            attribute mass : Real = 2.895505491018062;
                            attribute sigma_mass : Real = 0.5781874454998993;
                            attribute Cx : Real = 68.725719550301;
                            attribute sigma_Cx : Real = 15.648556222344574;
                            attribute Cy : Real = 20.346631151570175;
                            attribute sigma_Cy : Real = 14.954167508031205;
                            attribute Cz : Real = -69.63704070737383;
                            attribute sigma_Cz : Real = 16.335868636104294;
                            attribute Ixx : Real = 5496.676477674757;
                            attribute sigma_Ixx : Real = 3816.7427214635773;
                            attribute Iyy : Real = 6623.305258458119;
                            attribute sigma_Iyy : Real = 4300.516008931383;
                            attribute Izz : Real = 4494.341872082425;
                            attribute sigma_Izz : Real = 3458.4468497858925;
                            attribute Ixy : Real = 1172.3692352629805;
                            attribute sigma_Ixy : Real = 1682.7657854102938;
                            attribute Ixz : Real = -1431.064118652118;
                            attribute sigma_Ixz : Real = 2063.033683051891;
                            attribute Iyz : Real = 1340.1200185984333;
                            attribute sigma_Iyz : Real = 1795.742635689315;
                            part <'C.1.1.3.1.3.1.1'> 'Part 269' {
                                attribute POIconv : String = "-";
                                attribute Ipoint : Boolean = false;
                                attribute mass : Real = 0.7552149838383775;
                                attribute sigma_mass : Real = 0.28909372274994966;
                                attribute Cx : Real = 16.30487642250955;
                                attribute sigma_Cx : Real = 28.721044428837228;
                                attribute Cy : Real = 41.70290273614228;
                                attribute sigma_Cy : Real = 28.23690002309109;
                                attribute Cz : Real = -96.58639398403466;
                                attribute sigma_Cz : Real = 29.057750463592832;
                                attribute Ixx : Real = 0.9806093264436713;
                                attribute sigma_Ixx : Real = 0.37074144170588635;
                                attribute Iyy : Real = 1.0074705016244765;
                                attribute sigma_Iyy : Real = 0.3723953238821935;
                                attribute Izz : Real = 0.9560956446860153;
                                attribute sigma_Izz : Real = 0.37017423652493897;
                                attribute Ixy : Real = -0.08405008993904409;
                                attribute sigma_Ixy : Real = 0.02351283871158888;
                                attribute Ixz : Real = -0.08412041250075607;
                                attribute sigma_Ixz : Real = 0.022566176940390956;
                                attribute Iyz : Real = 0.03650060023863229;
                                attribute sigma_Iyz : Real = 0.02209918015384651;
                            }
                            part <'C.1.1.3.1.3.1.2'> 'Part 270' {
                                attribute POIconv : String = "-";
                                attribute Ipoint : Boolean = false;
                                attribute mass : Real = 0.6606783553028945;
                                attribute sigma_mass : Real = 0.28909372274994966;
                                attribute Cx : Real = 86.63584208115935;
                                attribute sigma_Cx : Real = 28.721044428837228;
                                attribute Cy : Real = 12.109112739562988;
                                attribute sigma_Cy : Real = 28.23690002309109;
                                attribute Cz : Real = -7.506129052489996;
                                attribute sigma_Cz : Real = 29.057750463592832;
                                attribute Ixx : Real = 0.9930458614088498;
                                attribute sigma_Ixx : Real = 0.37074144170588635;
                                attribute Iyy : Real = 0.991372570388312;
                                attribute sigma_Iyy : Real = 0.3723953238821935;
                                attribute Izz : Real = 0.9812374841152306;
                                attribute sigma_Izz : Real = 0.37017423652493897;
                                attribute Ixy : Real = 0.0025908724554307046;
                                attribute sigma_Ixy : Real = 0.02351283871158888;
                                attribute Ixz : Real = 0.00018148602731744411;
                                attribute sigma_Ixz : Real = 0.022566176940390956;
                                attribute Iyz : Real = 0.0001964727865071506;
                                attribute sigma_Iyz : Real = 0.02209918015384651;
                            }
                            part <'C.1.1.3.1.3.1.3'> 'Part 271' {
                                attribute POIconv : String = "+";
                                attribute Ipoint : Boolean = false;
                                attribute mass : Real = 0.6912593172150664;
                                attribute sigma_mass : Real = 0.28909372274994966;
                                attribute Cx : Real = 88.21610664017498;
                                attribute sigma_Cx : Real = 28.721044428837228;
                                attribute Cy : Real = -17.485354654490948;
                                attribute sigma_Cy : Real = 28.23690002309109;
                                attribute Cz : Real = -65.57553191669285;
                                attribute sigma_Cz : Real = 29.057750463592832;
                                attribute Ixx : Real = 0.6100052526675863;
                                attribute sigma_Ixx : Real = 0.37074144170588635;
                                attribute Iyy : Real = 0.6529572923972892;
                                attribute sigma_Iyy : Real = 0.3723953238821935;
                                attribute Izz : Real = 0.678571295636607;
                                attribute sigma_Izz : Real = 0.37017423652493897;
                                attribute Ixy : Real = 0.04316205983161274;
                                attribute sigma_Ixy : Real = 0.02351283871158888;
                                attribute Ixz : Real = 0.008023826489047753;
                                attribute sigma_Ixz : Real = 0.022566176940390956;
                                attribute Iyz : Real = 0.004693404630064313;
                                attribute sigma_Iyz : Real = 0.02209918015384651;
                            }
                            part <'C.1.1.3.1.3.1.4'> 'Part 272' {
                                attribute POIconv : String = "-";
                                attribute Ipoint : Boolean = false;
                                attribute mass : Real = 0.788352834661724;
                                attribute sigma_mass : Real = 0.28909372274994966;
                                attribute Cx : Real = 86.8435769341886;
                                attribute sigma_Cx : Real = 28.721044428837228;
                                attribute Cy : Real = 39.96409913524985;
                                attribute sigma_Cy : Real = 28.23690002309109;
                                attribute Cz : Real = -99.45053015835583;
                                attribute sigma_Cz : Real = 29.057750463592832;
                                attribute Ixx : Real = 1.0525254060784688;
                                attribute sigma_Ixx : Real = 0.37074144170588635;
                                attribute Iyy : Real = 1.0648584150233433;
                                attribute sigma_Iyy : Real = 0.3723953238821935;
                                attribute Izz : Real = 1.0924118762277755;
                                attribute sigma_Izz : Real = 0.37017423652493897;
                                attribute Ixy : Real = 0.041606553373961644;
                                attribute sigma_Ixy : Real = 0.02351283871158888;
                                attribute Ixz : Real = -0.0031064086413085355;
                                attribute sigma_Ixz : Real = 0.022566176940390956;
                                attribute Iyz : Real = -0.00038925071180354693;
                                attribute sigma_Iyz : Real = 0.02209918015384651;
                            }
                        }
                        part <'C.1.1.3.1.3.2'> 'Subassembly 80' {
                            attribute POIconv : String = "-";
                            attribute Ipoint : Boolean = false;
                            attribute mass : Real = 1.7097435189750976;
                            attribute sigma_mass : Real = 0.5007250159521434;
                            attribute Cx : Real = 1.975755124921633;
                            attribute sigma_Cx : Real = 25.63004313043411;
                            attribute Cy : Real = 41.802308445517134;
                            attribute sigma_Cy : Real = 21.5437676475663;
                            attribute Cz : Real = -6.510310188903581;
                            attribute sigma_Cz : Real = 24.483580921580533;
                            attribute Ixx : Real = 5114.324656361997;
                            attribute sigma_Ixx : Real = 3927.0889714212467;
                            attribute Iyy : Real = 8200.465935356951;
                            attribute sigma_Iyy : Real = 5367.891891546551;
                            attribute Izz : Real = 8092.473510819575;
                            attribute sigma_Izz : Real = 4985.54655941014;
                            attribute Ixy : Real = 3622.3972266432747;
                            attribute sigma_Ixy : Real = 2419.383319364016;
                            attribute Ixz : Real = -2681.4754581335783;
                            attribute sigma_Ixz : Real = 2502.6032660707197;
                            attribute Iyz : Real = 1286.3807097161434;
                            attribute sigma_Iyz : Real = 1591.6337326849325;
                            part <'C.1.1.3.1.3.2.1'> 'Part 273' {
                                attribute POIconv : String = "-";
                                attribute Ipoint : Boolean = false;
                                attribute mass : Real = 0.9768240581154823;
                                attribute sigma_mass : Real = 0.28909372274994966;
                                attribute Cx : Real = -47.41086442954838;
                                attribute sigma_Cx : Real = 28.721044428837228;
                                attribute Cy : Real = 73.20753554813564;
                                attribute sigma_Cy : Real = 28.23690002309109;
                                attribute Cz : Real = -31.987325195223093;
                                attribute sigma_Cz : Real = 29.057750463592832;
                                attribute Ixx : Real = 0.8800924858894497;
                                attribute sigma_Ixx : Real = 0.37074144170588635;
                                attribute Iyy : Real = 0.9159050114096706;
                                attribute sigma_Iyy : Real = 0.3723953238821935;
                                attribute Izz : Real = 0.9523200161105341;
                                attribute sigma_Izz : Real = 0.37017423652493897;
                                attribute Ixy : Real = 0.001086591242318731;
                                attribute sigma_Ixy : Real = 0.02351283871158888;
                                attribute Ixz : Real = -0.012586614579215042;
                                attribute sigma_Ixz : Real = 0.022566176940390956;
                                attribute Iyz : Real = 0.012104638069395893;
                                attribute sigma_Iyz : Real = 0.02209918015384651;
                            }
                            part <'C.1.1.3.1.3.2.2'> 'Part 274' {
                                attribute POIconv : String = "+";
                                attribute Ipoint : Boolean = false;
                                attribute mass : Real = 0.25537284385273235;
                                attribute sigma_mass : Real = 0.28909372274994966;
                                attribute Cx : Real = 58.97910385392606;
                                attribute sigma_Cx : Real = 28.721044428837228;
                                attribute Cy : Real = 25.44229393824935;
                                attribute sigma_Cy : Real = 28.23690002309109;
                                attribute Cz : Real = 81.1688160058111;
                                attribute sigma_Cz : Real = 29.057750463592832;
                                attribute Ixx : Real = 0.29186901986818004;
                                attribute sigma_Ixx : Real = 0.37074144170588635;
                                attribute Iyy : Real = 0.29349861922566334;
                                attribute sigma_Iyy : Real = 0.3723953238821935;
                                attribute Izz : Real = 0.3122881687375152;
                                attribute sigma_Izz : Real = 0.37017423652493897;
                                attribute Ixy : Real = 0.014870443509481166;
                                attribute sigma_Ixy : Real = 0.02351283871158888;
                                attribute Ixz : Real = 0.0016174942667759751;
                                attribute sigma_Ixz : Real = 0.022566176940390956;
                                attribute Iyz : Real = 0.0016197103779840784;
                                attribute sigma_Iyz : Real = 0.02209918015384651;
                            }
                            part <'C.1.1.3.1.3.2.3'> 'Part 275' {
                                attribute POIconv : String = "+";
                                attribute Ipoint : Boolean = false;
                                attribute mass : Real = 0.477546617006883;
                                attribute sigma_mass : Real = 0.28909372274994966;
                                attribute Cx : Real = 72.51322655938566;
                                attribute sigma_Cx : Real = 28.721044428837228;
                                attribute Cy : Real = -13.688563043251634;
                                attribute sigma_Cy : Real = 28.23690002309109;
                                attribute Cz : Real = -1.2842373922467232;
                                attribute sigma_Cz : Real = 29.057750463592832;
                                attribute Ixx : Real = 0.603187338049231;
                                attribute sigma_Ixx : Real = 0.37074144170588635;
                                attribute Iyy : Real = 0.6019458182092132;
                                attribute sigma_Iyy : Real = 0.3723953238821935;
                                attribute Izz : Real = 0.5841928516360604;
                                attribute sigma_Izz : Real = 0.37017423652493897;
                                attribute Ixy : Real = 0.0018082758596553341;
                                attribute sigma_Ixy : Real = 0.02351283871158888;
                                attribute Ixz : Real = 0.003778141957881892;
                                attribute sigma_Ixz : Real = 0.022566176940390956;
                                attribute Iyz : Real = 0.0010040443577650823;
                                attribute sigma_Iyz : Real = 0.02209918015384651;
                            }
                        }
                        part <'C.1.1.3.1.3.3'> 'Subassembly 81' {
                            attribute POIconv : String = "-";
                            attribute Ipoint : Boolean = false;
                            attribute mass : Real = 0.8630290277875028;
                            attribute sigma_mass : Real = 0.5007250159521434;
                            attribute Cx : Real = 41.0467209407394;
                            attribute sigma_Cx : Real = 48.493738693322435;
                            attribute Cy : Real = 40.97199990024505;
                            attribute sigma_Cy : Real = 19.478842035139575;
                            attribute Cz : Real = 24.431580756857755;
                            attribute sigma_Cz : Real = 42.63341099072716;
                            attribute Ixx : Real = 3923.050153902923;
                            attribute sigma_Ixx : Real = 3651.5395285263608;
                            attribute Iyy : Real = 7982.750891778032;
                            attribute sigma_Iyy : Real = 6529.2690353056105;
                            attribute Izz : Real = 4486.856020592198;
                            attribute sigma_Izz : Real = 4924.454195497775;
                            attribute Ixy : Real = 592.4374167188622;
                            attribute sigma_Ixy : Real = 1156.9977355922574;
                            attribute Ixz : Real = 1349.2703006398328;
                            attribute sigma_Ixz : Real = 2325.4169574813413;
                            attribute Iyz : Real = -842.6646132397706;
                            attribute sigma_Iyz : Real = 1163.8838331258862;
                            part <'C.1.1.3.1.3.3.1'> 'Part 276' {
                                attribute POIconv : String = "+";
                                attribute Ipoint : Boolean = false;
                                attribute mass : Real = 0.3882750416311901;
                                attribute sigma_mass : Real = 0.28909372274994966;
                                attribute Cx : Real = 82.98041033558547;
                                attribute sigma_Cx : Real = 28.721044428837228;
                                attribute Cy : Real = 46.63001396693289;
                                attribute sigma_Cy : Real = 28.23690002309109;
                                attribute Cz : Real = 68.63532420247793;
                                attribute sigma_Cz : Real = 29.057750463592832;
                                attribute Ixx : Real = 0.5134519744349403;
                                attribute sigma_Ixx : Real = 0.37074144170588635;
                                attribute Iyy : Real = 0.5266967115668738;
                                attribute sigma_Iyy : Real = 0.3723953238821935;
                                attribute Izz : Real = 0.4363105052574482;
                                attribute sigma_Izz : Real = 0.37017423652493897;
                                attribute Ixy : Real = -0.002509714717017153;
                                attribute sigma_Ixy : Real = 0.02351283871158888;
                                attribute Ixz : Real = -0.0364854809768939;
                                attribute sigma_Ixz : Real = 0.022566176940390956;
                                attribute Iyz : Real = 0.0028371410191746927;
                                attribute sigma_Iyz : Real = 0.02209918015384651;
                            }
                            part <'C.1.1.3.1.3.3.2'> 'Part 277' {
                                attribute POIconv : String = "-";
                                attribute Ipoint : Boolean = false;
                                attribute mass : Real = 0.26259506153757683;
                                attribute sigma_mass : Real = 0.28909372274994966;
                                attribute Cx : Real = 78.57895875349641;
                                attribute sigma_Cx : Real = 28.721044428837228;
                                attribute Cy : Real = 18.341201590374112;
                                attribute sigma_Cy : Real = 28.23690002309109;
                                attribute Cz : Real = -74.68567094765604;
                                attribute sigma_Cz : Real = 29.057750463592832;
                                attribute Ixx : Real = 0.3317300256891948;
                                attribute sigma_Ixx : Real = 0.37074144170588635;
                                attribute Iyy : Real = 0.3187521032327962;
                                attribute sigma_Iyy : Real = 0.3723953238821935;
                                attribute Izz : Real = 0.31066051621656837;
                                attribute sigma_Izz : Real = 0.37017423652493897;
                                attribute Ixy : Real = 0.005221628987863486;
                                attribute sigma_Ixy : Real = 0.02351283871158888;
                                attribute Ixz : Real = 0.005274844018927083;
                                attribute sigma_Ixz : Real = 0.022566176940390956;
                                attribute Iyz : Real = -0.012544664523111773;
                                attribute sigma_Iyz : Real = 0.02209918015384651;
                            }
                            part <'C.1.1.3.1.3.3.3'> 'Part 278' {
                                attribute POIconv : String = "+";
                                attribute Ipoint : Boolean = false;
                                attribute mass : Real = 0.21215892461873592;
                                attribute sigma_mass : Real = 0.28909372274994966;
                                attribute Cx : Real = -82.1514209266752;
                                attribute sigma_Cx : Real = 28.721044428837228;
                                attribute Cy : Real = 58.627963392063975;
                                attribute sigma_Cy : Real = 28.23690002309109;
                                attribute Cz : Real = 66.21389323845506;
                                attribute sigma_Cz : Real = 29.057750463592832;
                                attribute Ixx : Real = 0.29804026080744483;
                                attribute sigma_Ixx : Real = 0.37074144170588635;
                                attribute Iyy : Real = 0.28662850783559407;
                                attribute sigma_Iyy : Real = 0.3723953238821935;
                                attribute Izz : Real = 0.28576333851084784;
                                attribute sigma_Izz : Real = 0.37017423652493897;
                                attribute Ixy : Real = -0.023939250208943632;
                                attribute sigma_Ixy : Real = 0.02351283871158888;
                                attribute Ixz : Real = 0.021341632877149998;
                                attribute sigma_Ixz : Real = 0.022566176940390956;
                                attribute Iyz : Real = 0.0007780960577164109;
                                attribute sigma_Iyz : Real = 0.02209918015384651;
                            }
                        }
                        part <'C.1.1.3.1.3.4'> 'Subassembly 82' {
                            attribute POIconv : String = "-";
                            attribute Ipoint : Boolean = false;
                            attribute mass : Real = 1.7105576088929084;
                            attribute sigma_mass : Real = 0.5781874454998993;
                            attribute Cx : Real = 30.905992729309638;
                            attribute sigma_Cx : Real = 18.692236647751965;
                            attribute Cy : Real = 12.72116199781042;
                            attribute sigma_Cy : Real = 21.585354210761132;
                            attribute Cz : Real = 9.624069907841234;
                            attribute sigma_Cz : Real = 29.557484811699172;
                            attribute Ixx : Real = 10347.264640318614;
                            attribute sigma_Ixx : Real = 6033.343353549113;
                            attribute Iyy : Real = 8749.927137143846;
                            attribute sigma_Iyy : Real = 5415.5437506156995;
                            attribute Izz : Real = 2058.5347416304194;
                            attribute sigma_Izz : Real = 2456.326205743636;
                            attribute Ixy : Real = 171.1642375874992;
                            attribute sigma_Ixy : Real = 1149.8433977856703;
                            attribute Ixz : Real = 376.79058118008174;
                            attribute sigma_Ixz : Real = 2282.3872519050656;
                            attribute Iyz : Real = 2185.8352244930966;
                            attribute sigma_Iyz : Real = 2753.006999858458;
                            part <'C.1.1.3.1.3.4.1'> 'Part 279' {
                                attribute POIconv : String = "-";
                                attribute Ipoint : Boolean = false;
                                attribute mass : Real = 0.0796404043759685;
                                attribute sigma_mass : Real = 0.28909372274994966;
                                attribute Cx : Real = -20.937465084716678;
                                attribute sigma_Cx : Real = 28.721044428837228;
                                attribute Cy : Real = 69.190364331007;
                                attribute sigma_Cy : Real = 28.23690002309109;
                                attribute Cz : Real = 86.66236279532313;
                                attribute sigma_Cz : Real = 29.057750463592832;
                                attribute Ixx : Real = 0.10368158308599461;
                                attribute sigma_Ixx : Real = 0.37074144170588635;
                                attribute Iyy : Real = 0.11016089598137602;
                                attribute sigma_Iyy : Real = 0.3723953238821935;
                                attribute Izz : Real = 0.10466910909698864;
                                attribute sigma_Izz : Real = 0.37017423652493897;
                                attribute Ixy : Real = -0.005090819739572896;
                                attribute sigma_Ixy : Real = 0.02351283871158888;
                                attribute Ixz : Real = -0.0018534140864118255;
                                attribute sigma_Ixz : Real = 0.022566176940390956;
                                attribute Iyz : Real = 0.0001970398635431634;
                                attribute sigma_Iyz : Real = 0.02209918015384651;
                            }
                            part <'C.1.1.3.1.3.4.2'> 'Part 280' {
                                attribute POIconv : String = "-";
                                attribute Ipoint : Boolean = false;
                                attribute mass : Real = 0.5992493163826875;
                                attribute sigma_mass : Real = 0.28909372274994966;
                                attribute Cx : Real = 33.10775747522712;
                                attribute sigma_Cx : Real = 28.721044428837228;
                                attribute Cy : Real = -17.123185843229294;
                                attribute sigma_Cy : Real = 28.23690002309109;
                                attribute Cz : Real = 97.63681297190487;
                                attribute sigma_Cz : Real = 29.057750463592832;
                                attribute Ixx : Real = 0.7468408203521136;
                                attribute sigma_Ixx : Real = 0.37074144170588635;
                                attribute Iyy : Real = 0.7708896742742051;
                                attribute sigma_Iyy : Real = 0.3723953238821935;
                                attribute Izz : Real = 0.7961123529012294;
                                attribute sigma_Izz : Real = 0.37017423652493897;
                                attribute Ixy : Real = 0.008264479374425884;
                                attribute sigma_Ixy : Real = 0.02351283871158888;
                                attribute Ixz : Real = -0.02350251201482062;
                                attribute sigma_Ixz : Real = 0.022566176940390956;
                                attribute Iyz : Real = 0.01888485359550897;
                                attribute sigma_Iyz : Real = 0.02209918015384651;
                            }
                            part <'C.1.1.3.1.3.4.3'> 'Part 281' {
                                attribute POIconv : String = "+";
                                attribute Ipoint : Boolean = false;
                                attribute mass : Real = 0.33510842293617316;
                                attribute sigma_mass : Real = 0.28909372274994966;
                                attribute Cx : Real = 36.76092238165438;
                                attribute sigma_Cx : Real = 28.721044428837228;
                                attribute Cy : Real = 67.45433560572565;
                                attribute sigma_Cy : Real = 28.23690002309109;
                                attribute Cz : Real = -56.81755640543997;
                                attribute sigma_Cz : Real = 29.057750463592832;
                                attribute Ixx : Real = 0.36463873443370753;
                                attribute sigma_Ixx : Real = 0.37074144170588635;
                                attribute Iyy : Real = 0.4309386004329424;
                                attribute sigma_Iyy : Real = 0.3723953238821935;
                                attribute Izz : Real = 0.37829257303458796;
                                attribute sigma_Izz : Real = 0.37017423652493897;
                                attribute Ixy : Real = -0.004504852986252152;
                                attribute sigma_Ixy : Real = 0.02351283871158888;
                                attribute Ixz : Real = 0.038181641686040435;
                                attribute sigma_Ixz : Real = 0.022566176940390956;
                                attribute Iyz : Real = -0.012584964318461352;
                                attribute sigma_Iyz : Real = 0.02209918015384651;
                            }
                            part <'C.1.1.3.1.3.4.4'> 'Part 282' {
                                attribute POIconv : String = "-";
                                attribute Ipoint : Boolean = false;
                                attribute mass : Real = 0.6965594651980791;
                                attribute sigma_mass : Real = 0.28909372274994966;
                                attribute Cx : Real = 32.12253162637353;
                                attribute sigma_Cx : Real = 28.721044428837228;
                                attribute Cy : Real = 5.608240840956569;
                                attribute sigma_Cy : Real = 28.23690002309109;
                                attribute Cz : Real = -42.93682421557605;
                                attribute sigma_Cz : Real = 29.057750463592832;
                                attribute Ixx : Real = 0.9499373043627023;
                                attribute sigma_Ixx : Real = 0.37074144170588635;
                                attribute Iyy : Real = 0.8691069344418099;
                                attribute sigma_Iyy : Real = 0.3723953238821935;
                                attribute Izz : Real = 0.949128355553683;
                                attribute sigma_Izz : Real = 0.37017423652493897;
                                attribute Ixy : Real = -0.01117247453881469;
                                attribute sigma_Ixy : Real = 0.02351283871158888;
                                attribute Ixz : Real = -0.00020040106540835425;
                                attribute sigma_Ixz : Real = 0.022566176940390956;
                                attribute Iyz : Real = -0.0009360542018633984;
                                attribute sigma_Iyz : Real = 0.02209918015384651;
                            }
                        }
                    }
                    part <'C.1.1.3.1.4'> 'Assembly 23' {
                        attribute POIconv : String = "-";
                        attribute Ipoint : Boolean = false;
                        attribute mass : Real = 3.5822810280274133;
                        attribute sigma_mass : Real = 0.8176805270198123;
                        attribute Cx : Real = -6.226363777755104;
                        attribute sigma_Cx : Real = 17.181508939390234;
                        attribute Cy : Real = 38.933189947563946;
                        attribute sigma_Cy : Real = 16.66237266004845;
                        attribute Cz : Real = 10.616691643344664;
                        attribute sigma_Cz : Real = 15.652922020997515;
                        attribute Ixx : Real = 13538.201594324091;
                        attribute sigma_Ixx : Real = 6623.644704272737;
                        attribute Iyy : Real = 15580.629692394961;
                        attribute sigma_Iyy : Real = 7363.281325641498;
                        attribute Izz : Real = 16649.946480858045;
                        attribute sigma_Izz : Real = 8070.152485355091;
                        attribute Ixy : Real = -2314.526028811614;
                        attribute sigma_Ixy : Real = 4014.140467044787;
                        attribute Ixz : Real = 5566.253689894514;
                        attribute sigma_Ixz : Real = 3390.045153457603;
                        attribute Iyz : Real = -2600.596067628476;
                        attribute sigma_Iyz : Real = 2903.469454977278;
                        part <'C.1.1.3.1.4.1'> 'Subassembly 83' {
                            attribute POIconv : String = "-";
                            attribute Ipoint : Boolean = false;
                            attribute mass : Real = 0.919804460500367;
                            attribute sigma_mass : Real = 0.40884026350990615;
                            attribute Cx : Real = -10.94322952240565;
                            attribute sigma_Cx : Real = 36.22126672425843;
                            attribute Cy : Real = 6.301250308309261;
                            attribute sigma_Cy : Real = 36.62120034861112;
                            attribute Cz : Real = 9.244205208580459;
                            attribute sigma_Cz : Real = 23.572295819404005;
                            attribute Ixx : Real = 2088.0820146149754;
                            attribute sigma_Ixx : Real = 2682.2541805058363;
                            attribute Iyy : Real = 1969.955790915671;
                            attribute sigma_Iyy : Real = 2566.462630522987;
                            attribute Izz : Real = 4020.3568044682797;
                            attribute sigma_Izz : Real = 4787.751455197138;
                            attribute Ixy : Real = -2008.6977536501688;
                            attribute sigma_Ixy : Real = 2393.249625531841;
                            attribute Ixz : Real = -188.78411930286327;
                            attribute sigma_Ixz : Real = 759.6963064595897;
                            attribute Iyz : Real = -194.38771863303595;
                            attribute sigma_Iyz : Real = 782.0855237678004;
                            part <'C.1.1.3.1.4.1.1'> 'Part 283' {
                                attribute POIconv : String = "-";
                                attribute Ipoint : Boolean = false;
                                attribute mass : Real = 0.2084483498572372;
                                attribute sigma_mass : Real = 0.28909372274994966;
                                attribute Cx : Real = -96.01093241944909;
                                attribute sigma_Cx : Real = 28.721044428837228;
                                attribute Cy : Real = -81.30620876327157;
                                attribute sigma_Cy : Real = 28.23690002309109;
                                attribute Cz : Real = 1.0111707728356123;
                                attribute sigma_Cz : Real = 29.057750463592832;
                                attribute Ixx : Real = 0.26681576158109216;
                                attribute sigma_Ixx : Real = 0.37074144170588635;
                                attribute Iyy : Real = 0.2376899871101428;
                                attribute sigma_Iyy : Real = 0.3723953238821935;
                                attribute Izz : Real = 0.27077906223512227;
                                attribute sigma_Izz : Real = 0.37017423652493897;
                                attribute Ixy : Real = -0.012964369702082378;
                                attribute sigma_Ixy : Real = 0.02351283871158888;
                                attribute Ixz : Real = 0.019659304800306393;
                                attribute sigma_Ixz : Real = 0.022566176940390956;
                                attribute Iyz : Real = 0.017664549741799974;
                                attribute sigma_Iyz : Real = 0.02209918015384651;
                            }
                            part <'C.1.1.3.1.4.1.2'> 'Part 284' {
                                attribute POIconv : String = "-";
                                attribute Ipoint : Boolean = false;
                                attribute mass : Real = 0.7113561106431298;
                                attribute sigma_mass : Real = 0.28909372274994966;
                                attribute Cx : Real = 13.984119845554233;
                                attribute sigma_Cx : Real = 28.721044428837228;
                                attribute Cy : Real = 31.972823245450854;
                                attribute sigma_Cy : Real = 28.23690002309109;
                                attribute Cz : Real = 11.656727455556393;
                                attribute sigma_Cz : Real = 29.057750463592832;
                                attribute Ixx : Real = 0.8858934281676961;
                                attribute sigma_Ixx : Real = 0.37074144170588635;
                                attribute Iyy : Real = 0.9918782537469021;
                                attribute sigma_Iyy : Real = 0.3723953238821935;
                                attribute Izz : Real = 0.9695064216949099;
                                attribute sigma_Izz : Real = 0.37017423652493897;
                                attribute Ixy : Real = 0.004187664518983513;
                                attribute sigma_Ixy : Real = 0.02351283871158888;
                                attribute Ixz : Real = -0.03440105526948157;
                                attribute sigma_Ixz : Real = 0.022566176940390956;
                                attribute Iyz : Real = -0.00016293245020117535;
                                attribute sigma_Iyz : Real = 0.02209918015384651;
                            }
                        }
                        part <'C.1.1.3.1.4.2'> 'Subassembly 84' {
                            attribute POIconv : String = "-";
                            attribute Ipoint : Boolean = false;
                            attribute mass : Real = 1.941307207124075;
                            attribute sigma_mass : Real = 0.5781874454998993;
                            attribute Cx : Real = 3.563063766696666;
                            attribute sigma_Cx : Real = 21.61657150563345;
                            attribute Cy : Real = 69.7903526388524;
                            attribute sigma_Cy : Real = 17.01779692739347;
                            attribute Cz : Real = 17.99993692317833;
                            attribute sigma_Cz : Real = 23.99869840990527;
                            attribute Ixx : Real = 6282.87209144243;
                            attribute sigma_Ixx : Real = 4405.282320398181;
                            attribute Iyy : Real = 11526.112331451404;
                            attribute sigma_Iyy : Real = 6246.586552628209;
                            attribute Izz : Real = 6553.420352897399;
                            attribute sigma_Izz : Real = 4276.44141918783;
                            attribute Ixy : Real = 1742.774751828959;
                            attribute sigma_Ixy : Real = 1966.949469151211;
                            attribute Ixz : Real = 5676.204853779502;
                            attribute sigma_Ixz : Real = 3032.579429002485;
                            attribute Iyz : Real = -1733.9020702128737;
                            attribute sigma_Iyz : Real = 1911.7376178885702;
                            part <'C.1.1.3.1.4.2.1'> 'Part 285' {
                                attribute POIconv : String = "+";
                                attribute Ipoint : Boolean = false;
                                attribute mass : Real = 0.5259021329942625;
                                attribute sigma_mass : Real = 0.28909372274994966;
                                attribute Cx : Real = -17.64671364799142;
                                attribute sigma_Cx : Real = 28.721044428837228;
                                attribute Cy : Real = 89.54165210016072;
                                attribute sigma_Cy : Real = 28.23690002309109;
                                attribute Cz : Real = 43.38798294775188;
                                attribute sigma_Cz : Real = 29.057750463592832;
                                attribute Ixx : Real = 0.5699289325638927;
                                attribute sigma_Ixx : Real = 0.37074144170588635;
                                attribute Iyy : Real = 0.5951089484357659;
                                attribute sigma_Iyy : Real = 0.3723953238821935;
                                attribute Izz : Real = 0.601127148301748;
                                attribute sigma_Izz : Real = 0.37017423652493897;
                                attribute Ixy : Real = 0.022493407523167995;
                                attribute sigma_Ixy : Real = 0.02351283871158888;
                                attribute Ixz : Real = 0.019144821259585804;
                                attribute sigma_Ixz : Real = 0.022566176940390956;
                                attribute Iyz : Real = 0.01057045903422532;
                                attribute sigma_Iyz : Real = 0.02209918015384651;
                            }
                            part <'C.1.1.3.1.4.2.2'> 'Part 286' {
                                attribute POIconv : String = "+";
                                attribute Ipoint : Boolean = false;
                                attribute mass : Real = 0.02628880715300329;
                                attribute sigma_mass : Real = 0.28909372274994966;
                                attribute Cx : Real = 0.01230696216225624;
                                attribute sigma_Cx : Real = 28.721044428837228;
                                attribute Cy : Real = 62.76070298627019;
                                attribute sigma_Cy : Real = 28.23690002309109;
                                attribute Cz : Real = -53.94966620951891;
                                attribute sigma_Cz : Real = 29.057750463592832;
                                attribute Ixx : Real = 0.029127629948469222;
                                attribute sigma_Ixx : Real = 0.37074144170588635;
                                attribute Iyy : Real = 0.026762449049083932;
                                attribute sigma_Iyy : Real = 0.3723953238821935;
                                attribute Izz : Real = 0.027475363535445323;
                                attribute sigma_Izz : Real = 0.37017423652493897;
                                attribute Ixy : Real = -0.00021024904939354158;
                                attribute sigma_Ixy : Real = 0.02351283871158888;
                                attribute Ixz : Real = 0.0016200013543922697;
                                attribute sigma_Ixz : Real = 0.022566176940390956;
                                attribute Iyz : Real = 0.0006147594074536535;
                                attribute sigma_Iyz : Real = 0.02209918015384651;
                            }
                            part <'C.1.1.3.1.4.2.3'> 'Part 287' {
                                attribute POIconv : String = "+";
                                attribute Ipoint : Boolean = false;
                                attribute mass : Real = 0.7893841061438434;
                                attribute sigma_mass : Real = 0.28909372274994966;
                                attribute Cx : Real = 66.85028658248484;
                                attribute sigma_Cx : Real = 28.721044428837228;
                                attribute Cy : Real = 48.17043375223875;
                                attribute sigma_Cy : Real = 28.23690002309109;
                                attribute Cz : Real = -42.84108933061361;
                                attribute sigma_Cz : Real = 29.057750463592832;
                                attribute Ixx : Real = 1.091784143986187;
                                attribute sigma_Ixx : Real = 0.37074144170588635;
                                attribute Iyy : Real = 1.067747839567025;
                                attribute sigma_Iyy : Real = 0.3723953238821935;
                                attribute Izz : Real = 0.9870523454670007;
                                attribute sigma_Izz : Real = 0.37017423652493897;
                                attribute Ixy : Real = -0.018251024293104035;
                                attribute sigma_Ixy : Real = 0.02351283871158888;
                                attribute Ixz : Real = -0.03305758531602982;
                                attribute sigma_Ixz : Real = 0.022566176940390956;
                                attribute Iyz : Real = 0.06358601399355998;
                                attribute sigma_Iyz : Real = 0.02209918015384651;
                            }
                            part <'C.1.1.3.1.4.2.4'> 'Part 288' {
                                attribute POIconv : String = "-";
                                attribute Ipoint : Boolean = false;
                                attribute mass : Real = 0.5997321608329658;
                                attribute sigma_mass : Real = 0.28909372274994966;
                                attribute Cx : Real = -60.982941929250956;
                                attribute sigma_Cx : Real = 28.721044428837228;
                                attribute Cy : Real = 81.23541325330734;
                                attribute sigma_Cy : Real = 28.23690002309109;
                                attribute Cz : Real = 78.97178935818374;
                                attribute sigma_Cz : Real = 29.057750463592832;
                                attribute Ixx : Real = 0.5724571920338896;
                                attribute sigma_Ixx : Real = 0.37074144170588635;
                                attribute Iyy : Real = 0.602166344081884;
                                attribute sigma_Iyy : Real = 0.3723953238821935;
                                attribute Izz : Real = 0.6050067643493143;
                                attribute sigma_Izz : Real = 0.37017423652493897;
                                attribute Ixy : Real = -0.004557661028207018;
                                attribute sigma_Ixy : Real = 0.02351283871158888;
                                attribute Ixz : Real = -0.007580448849620853;
                                attribute sigma_Ixz : Real = 0.022566176940390956;
                                attribute Iyz : Real = 0.028612424439612358;
                                attribute sigma_Iyz : Real = 0.02209918015384651;
                            }
                        }
                        part <'C.1.1.3.1.4.3'> 'Subassembly 85' {
                            attribute POIconv : String = "-";
                            attribute Ipoint : Boolean = false;
                            attribute mass : Real = 0.7211693604029714;
                            attribute sigma_mass : Real = 0.40884026350990615;
                            attribute Cx : Real = -26.56235265831067;
                            attribute sigma_Cx : Real = 39.522746707027785;
                            attribute Cy : Real = -2.510928910081897;
                            attribute sigma_Cy : Real = 32.61843834653009;
                            attribute Cz : Real = -7.5076614513707645;
                            attribute sigma_Cz : Real = 28.758207626214002;
                            attribute Ixx : Real = 756.2083266695985;
                            attribute sigma_Ixx : Real = 1486.4107780132938;
                            attribute Iyy : Real = 1235.3582823859792;
                            attribute sigma_Iyy : Real = 2313.425332187343;
                            attribute Izz : Real = 1504.8394480942368;
                            attribute sigma_Izz : Real = 2771.96215691409;
                            attribute Ixy : Real = -712.8012457251521;
                            attribute sigma_Ixy : Real = 1323.175252786777;
                            attribute Ixz : Real = 490.9071056494623;
                            attribute sigma_Ixz : Real = 965.9025975006049;
                            attribute Iyz : Real = 352.8739739844035;
                            attribute sigma_Iyz : Real = 708.7018027730799;
                            part <'C.1.1.3.1.4.3.1'> 'Part 289' {
                                attribute POIconv : String = "+";
                                attribute Ipoint : Boolean = false;
                                attribute mass : Real = 0.5838619578559883;
                                attribute sigma_mass : Real = 0.28909372274994966;
                                attribute Cx : Real = -44.54403277486563;
                                attribute sigma_Cx : Real = 28.721044428837228;
                                attribute Cy : Real = -15.438520535826683;
                                attribute sigma_Cy : Real = 28.23690002309109;
                                attribute Cz : Real = 1.3942868448793888;
                                attribute sigma_Cz : Real = 29.057750463592832;
                                attribute Ixx : Real = 0.5610682329908524;
                                attribute sigma_Ixx : Real = 0.37074144170588635;
                                attribute Iyy : Real = 0.6361642061100627;
                                attribute sigma_Iyy : Real = 0.3723953238821935;
                                attribute Izz : Real = 0.6411788066437182;
                                attribute sigma_Izz : Real = 0.37017423652493897;
                                attribute Ixy : Real = -0.043219678325177244;
                                attribute sigma_Ixy : Real = 0.02351283871158888;
                                attribute Ixz : Real = -0.03578488802047932;
                                attribute sigma_Ixz : Real = 0.022566176940390956;
                                attribute Iyz : Real = 0.02160606419841678;
                                attribute sigma_Iyz : Real = 0.02209918015384651;
                            }
                            part <'C.1.1.3.1.4.3.2'> 'Part 290' {
                                attribute POIconv : String = "+";
                                attribute Ipoint : Boolean = false;
                                attribute mass : Real = 0.1373074025469832;
                                attribute sigma_mass : Real = 0.28909372274994966;
                                attribute Cx : Real = 49.899795511737466;
                                attribute sigma_Cx : Real = 28.721044428837228;
                                attribute Cy : Real = 52.46009826660156;
                                attribute sigma_Cy : Real = 28.23690002309109;
                                attribute Cz : Real = -45.36074777133763;
                                attribute sigma_Cz : Real = 29.057750463592832;
                                attribute Ixx : Real = 0.14359605070649073;
                                attribute sigma_Ixx : Real = 0.37074144170588635;
                                attribute Iyy : Real = 0.16375187259050455;
                                attribute sigma_Iyy : Real = 0.3723953238821935;
                                attribute Izz : Real = 0.15566337197996727;
                                attribute sigma_Izz : Real = 0.37017423652493897;
                                attribute Ixy : Real = -0.010840928079334247;
                                attribute sigma_Ixy : Real = 0.02351283871158888;
                                attribute Ixz : Real = 0.0013230675657378201;
                                attribute sigma_Ixz : Real = 0.022566176940390956;
                                attribute Iyz : Real = 0.008099615278531801;
                                attribute sigma_Iyz : Real = 0.02209918015384651;
                            }
                        }
                    }
                }
                part <'C.1.1.3.2'> 'Subsystem 7' {
                    attribute POIconv : String = "-";
                    attribute Ipoint : Boolean = false;
                    attribute mass : Real = 24.58382684952789;
                    attribute sigma_mass : Real = 2.0029000638085734;
                    attribute Cx : Real = 2.67972580892662;
                    attribute sigma_Cx : Real = 6.9842455447562966;
                    attribute Cy : Real = 5.465927234815022;
                    attribute sigma_Cy : Real = 7.067623451719996;
                    attribute Cz : Real = -2.379195358704115;
                    attribute sigma_Cz : Real = 7.070003613200977;
                    attribute Ixx : Real = 152685.98246578747;
                    attribute sigma_Ixx : Real = 26645.736940587223;
                    attribute Iyy : Real = 150788.93518369133;
                    attribute sigma_Iyy : Real = 27251.014111720895;
                    attribute Izz : Real = 144993.16098324518;
                    attribute sigma_Izz : Real = 26318.923473032144;
                    attribute Ixy : Real = -13028.601179231267;
                    attribute sigma_Ixy : Real = 11764.476633159511;
                    attribute Ixz : Real = 9792.025927336226;
                    attribute sigma_Ixz : Real = 12269.223452874465;
                    attribute Iyz : Real = 18382.577786408052;
                    attribute sigma_Iyz : Real = 11869.431755070511;
                    part <'C.1.1.3.2.1'> 'Assembly 24' {
                        attribute POIconv : String = "-";
                        attribute Ipoint : Boolean = false;
                        attribute mass : Real = 8.021209506025306;
                        attribute sigma_mass : Real = 1.1919639546010696;
                        attribute Cx : Real = -16.009715763169545;
                        attribute sigma_Cx : Real = 11.977074295155004;
                        attribute Cy : Real = -16.00892999522716;
                        attribute sigma_Cy : Real = 11.762803255222487;
                        attribute Cz : Real = 9.684183667774278;
                        attribute sigma_Cz : Real = 10.484466447495196;
                        attribute Ixx : Real = 48092.11901170148;
                        attribute sigma_Ixx : Real = 12897.350016385932;
                        attribute Iyy : Real = 35665.489636160135;
                        attribute sigma_Iyy : Real = 13348.378685910886;
                        attribute Izz : Real = 41102.723367123144;
                        attribute sigma_Izz : Real = 14497.690820496411;
                        attribute Ixy : Real = -3381.208994300372;
                        attribute sigma_Ixy : Real = 6423.455481906356;
                        attribute Ixz : Real = 4942.171493446998;
                        attribute sigma_Ixz : Real = 4958.789113462961;
                        attribute Iyz : Real = 5279.378697546487;
                        attribute sigma_Iyz : Real = 6178.095755281718;
                        part <'C.1.1.3.2.1.1'> 'Subassembly 86' {
                            attribute POIconv : String = "-";
                            attribute Ipoint : Boolean = false;
                            attribute mass : Real = 1.5597652341928332;
                            attribute sigma_mass : Real = 0.6464332159373649;
                            attribute Cx : Real = -50.95422483080978;
                            attribute sigma_Cx : Real = 19.22352029101153;
                            attribute Cy : Real = -22.88357959429486;
                            attribute sigma_Cy : Real = 24.221514690863902;
                            attribute Cz : Real = 3.761585657428117;
                            attribute sigma_Cz : Real = 17.293734137402613;
                            attribute Ixx : Real = 4125.091961885459;
                            attribute sigma_Ixx : Real = 3058.3202041635627;
                            attribute Iyy : Real = 2440.181636777229;
                            attribute sigma_Iyy : Real = 2268.52270420932;
                            attribute Izz : Real = 5803.313305439635;
                            attribute sigma_Izz : Real = 3774.2693982753826;
                            attribute Ixy : Real = -2145.2186666206776;
                            attribute sigma_Ixy : Real = 1748.0225333713352;
                            attribute Ixz : Real = -739.9830218373392;
                            attribute sigma_Ixz : Real = 1087.5798297800384;
                            attribute Iyz : Real = -954.3317289445613;
                            attribute sigma_Iyz : Real = 1300.1003797512317;
                            part <'C.1.1.3.2.1.1.1'> 'Part 291' {
                                attribute POIconv : String = "+";
                                attribute Ipoint : Boolean = false;
                                attribute mass : Real = 0.20872391965100542;
                                attribute sigma_mass : Real = 0.28909372274994966;
                                attribute Cx : Real = -42.453552316874266;
                                attribute sigma_Cx : Real = 28.721044428837228;
                                attribute Cy : Real = -91.48890930227935;
                                attribute sigma_Cy : Real = 28.23690002309109;
                                attribute Cz : Real = -1.6845434438437223;
                                attribute sigma_Cz : Real = 29.057750463592832;
                                attribute Ixx : Real = 0.3030029730743317;
                                attribute sigma_Ixx : Real = 0.37074144170588635;
                                attribute Iyy : Real = 0.30041611316587397;
                                attribute sigma_Iyy : Real = 0.3723953238821935;
                                attribute Izz : Real = 0.2710764406007241;
                                attribute sigma_Izz : Real = 0.37017423652493897;
                                attribute Ixy : Real = 0.021860966315056476;
                                attribute sigma_Ixy : Real = 0.02351283871158888;
                                attribute Ixz : Real = 0.0015074379416920045;
                                attribute sigma_Ixz : Real = 0.022566176940390956;
                                attribute Iyz : Real = -0.0018500085562770416;
                                attribute sigma_Iyz : Real = 0.02209918015384651;
                            }
                            part <'C.1.1.3.2.1.1.2'> 'Part 292' {
                                attribute POIconv : String = "+";
                                attribute Ipoint : Boolean = false;
                                attribute mass : Real = 0.09709896455309354;
                                attribute sigma_mass : Real = 0.28909372274994966;
                                attribute Cx : Real = -63.63059016875923;
                                attribute sigma_Cx : Real = 28.721044428837228;
                                attribute Cy : Real = -33.34314785897732;
                                attribute sigma_Cy : Real = 28.23690002309109;
                                attribute Cz : Real = -29.783048667013645;
                                attribute sigma_Cz : Real = 29.057750463592832;
                                attribute Ixx : Real = 0.12761271868433127;
                                attribute sigma_Ixx : Real = 0.37074144170588635;
                                attribute Iyy : Real = 0.1259134873340282;
                                attribute sigma_Iyy : Real = 0.3723953238821935;
                                attribute Izz : Real = 0.15196374709935354;
                                attribute sigma_Izz : Real = 0.37017423652493897;
                                attribute Ixy : Real = -0.0003372534402745728;
                                attribute sigma_Ixy : Real = 0.02351283871158888;
                                attribute Ixz : Real = -0.0023482677694220333;
                                attribute sigma_Ixz : Real = 0.022566176940390956;
                                attribute Iyz : Real = -4.0643321109515175e-05;
                                attribute sigma_Iyz : Real = 0.02209918015384651;
                            }
                            part <'C.1.1.3.2.1.1.3'> 'Part 293' {
                                attribute POIconv : String = "+";
                                attribute Ipoint : Boolean = false;
                                attribute mass : Real = 0.1320042049740441;
                                attribute sigma_mass : Real = 0.28909372274994966;
                                attribute Cx : Real = -51.368594728410244;
                                attribute sigma_Cx : Real = 28.721044428837228;
                                attribute Cy : Real = 6.137400772422552;
                                attribute sigma_Cy : Real = 28.23690002309109;
                                attribute Cz : Real = 5.860640527680516;
                                attribute sigma_Cz : Real = 29.057750463592832;
                                attribute Ixx : Real = 0.1403687501784012;
                                attribute sigma_Ixx : Real = 0.37074144170588635;
                                attribute Iyy : Real = 0.13532897377185216;
                                attribute sigma_Iyy : Real = 0.3723953238821935;
                                attribute Izz : Real = 0.15687191133581685;
                                attribute sigma_Izz : Real = 0.37017423652493897;
                                attribute Ixy : Real = 0.0014135462505616815;
                                attribute sigma_Ixy : Real = 0.02351283871158888;
                                attribute Ixz : Real = -0.0029205264864954673;
                                attribute sigma_Ixz : Real = 0.022566176940390956;
                                attribute Iyz : Real = -0.0001900350111307211;
                                attribute sigma_Iyz : Real = 0.02209918015384651;
                            }
                            part <'C.1.1.3.2.1.1.4'> 'Part 294' {
                                attribute POIconv : String = "+";
                                attribute Ipoint : Boolean = false;
                                attribute mass : Real = 0.5710190714714117;
                                attribute sigma_mass : Real = 0.28909372274994966;
                                attribute Cx : Real = -93.14301228150725;
                                attribute sigma_Cx : Real = 28.721044428837228;
                                attribute Cy : Real = -59.18976194225252;
                                attribute sigma_Cy : Real = 28.23690002309109;
                                attribute Cz : Real = -7.19731543213129;
                                attribute sigma_Cz : Real = 29.057750463592832;
                                attribute Ixx : Real = 0.7935785843580989;
                                attribute sigma_Ixx : Real = 0.37074144170588635;
                                attribute Iyy : Real = 0.797762672320005;
                                attribute sigma_Iyy : Real = 0.3723953238821935;
                                attribute Izz : Real = 0.7653546626028505;
                                attribute sigma_Izz : Real = 0.37017423652493897;
                                attribute Ixy : Real = 0.0009849175668522937;
                                attribute sigma_Ixy : Real = 0.02351283871158888;
                                attribute Ixz : Real = 0.007588358096666954;
                                attribute sigma_Ixz : Real = 0.022566176940390956;
                                attribute Iyz : Real = -0.0010469011182626;
                                attribute sigma_Iyz : Real = 0.02209918015384651;
                            }
                            part <'C.1.1.3.2.1.1.5'> 'Part 295' {
                                attribute POIconv : String = "-";
                                attribute Ipoint : Boolean = false;
                                attribute mass : Real = 0.5509190735432785;
                                attribute sigma_mass : Real = 0.28909372274994966;
                                attribute Cx : Real = -8.113324595615268;
                                attribute sigma_Cx : Real = 28.721044428837228;
                                attribute Cy : Real = 35.629220586270094;
                                attribute sigma_Cy : Real = 28.23690002309109;
                                attribute Cz : Real = 22.592925187200308;
                                attribute sigma_Cz : Real = 29.057750463592832;
                                attribute Ixx : Real = 0.6620054601795933;
                                attribute sigma_Ixx : Real = 0.37074144170588635;
                                attribute Iyy : Real = 0.6585418270075559;
                                attribute sigma_Iyy : Real = 0.3723953238821935;
                                attribute Izz : Real = 0.6926666756982013;
                                attribute sigma_Izz : Real = 0.37017423652493897;
                                attribute Ixy : Real = 0.015376956555522788;
                                attribute sigma_Ixy : Real = 0.02351283871158888;
                                attribute Ixz : Real = -0.006891601694035384;
                                attribute sigma_Ixz : Real = 0.022566176940390956;
                                attribute Iyz : Real = -0.0006528032837741772;
                                attribute sigma_Iyz : Real = 0.02209918015384651;
                            }
                        }
                        part <'C.1.1.3.2.1.2'> 'Subassembly 87' {
                            attribute POIconv : String = "-";
                            attribute Ipoint : Boolean = false;
                            attribute mass : Real = 2.9359368637814187;
                            attribute sigma_mass : Real = 0.5781874454998993;
                            attribute Cx : Real = -6.7055215057422535;
                            attribute sigma_Cx : Real = 16.052316905978525;
                            attribute Cy : Real = -43.15299347898984;
                            attribute sigma_Cy : Real = 17.127615392472617;
                            attribute Cz : Real = -19.251996630328385;
                            attribute sigma_Cz : Real = 18.865006805929138;
                            attribute Ixx : Real = 18207.82623630177;
                            attribute sigma_Ixx : Real = 8143.252406382519;
                            attribute Iyy : Real = 13527.794003623281;
                            attribute sigma_Iyy : Real = 6914.195400285536;
                            attribute Izz : Real = 10180.589118021802;
                            attribute sigma_Izz : Real = 5548.241258029285;
                            attribute Ixy : Real = -90.48074164181487;
                            attribute sigma_Ixy : Real = 2679.9712421530066;
                            attribute Ixz : Real = 2667.8877948761815;
                            attribute sigma_Ixz : Real = 3274.5230261342103;
                            attribute Iyz : Real = 7792.469615895139;
                            attribute sigma_Iyz : Real = 3924.3028596109602;
                            part <'C.1.1.3.2.1.2.1'> 'Part 296' {
                                attribute POIconv : String = "-";
                                attribute Ipoint : Boolean = false;
                                attribute mass : Real = 0.7267857742926571;
                                attribute sigma_mass : Real = 0.28909372274994966;
                                attribute Cx : Real = 17.65443291515112;
                                attribute sigma_Cx : Real = 28.721044428837228;
                                attribute Cy : Real = -99.3824243079871;
                                attribute sigma_Cy : Real = 28.23690002309109;
                                attribute Cz : Real = 7.7377688605338335;
                                attribute sigma_Cz : Real = 29.057750463592832;
                                attribute Ixx : Real = 1.0189699300613975;
                                attribute sigma_Ixx : Real = 0.37074144170588635;
                                attribute Iyy : Real = 1.011737945280532;
                                attribute sigma_Iyy : Real = 0.3723953238821935;
                                attribute Izz : Real = 1.1016671032062197;
                                attribute sigma_Izz : Real = 0.37017423652493897;
                                attribute Ixy : Real = 0.01032309855838883;
                                attribute sigma_Ixy : Real = 0.02351283871158888;
                                attribute Ixz : Real = -0.0376202693240189;
                                attribute sigma_Ixz : Real = 0.022566176940390956;
                                attribute Iyz : Real = -0.026749786745504305;
                                attribute sigma_Iyz : Real = 0.02209918015384651;
                            }
                            part <'C.1.1.3.2.1.2.2'> 'Part 297' {
                                attribute POIconv : String = "+";
                                attribute Ipoint : Boolean = false;
                                attribute mass : Real = 0.6219178375320044;
                                attribute sigma_mass : Real = 0.28909372274994966;
                                attribute Cx : Real = -62.12940663099289;
                                attribute sigma_Cx : Real = 28.721044428837228;
                                attribute Cy : Real = -75.98449559882283;
                                attribute sigma_Cy : Real = 28.23690002309109;
                                attribute Cz : Real = 68.68572356179357;
                                attribute sigma_Cz : Real = 29.057750463592832;
                                attribute Ixx : Real = 0.7294250165007358;
                                attribute sigma_Ixx : Real = 0.37074144170588635;
                                attribute Iyy : Real = 0.7688521813045557;
                                attribute sigma_Iyy : Real = 0.3723953238821935;
                                attribute Izz : Real = 0.8059909878297835;
                                attribute sigma_Izz : Real = 0.37017423652493897;
                                attribute Ixy : Real = 0.0014787089402329059;
                                attribute sigma_Ixy : Real = 0.02351283871158888;
                                attribute Ixz : Real = -0.011753972019579508;
                                attribute sigma_Ixz : Real = 0.022566176940390956;
                                attribute Iyz : Real = -0.012296948840622305;
                                attribute sigma_Iyz : Real = 0.02209918015384651;
                            }
                            part <'C.1.1.3.2.1.2.3'> 'Part 298' {
                                attribute POIconv : String = "-";
                                attribute Ipoint : Boolean = false;
                                attribute mass : Real = 0.9906643488102127;
                                attribute sigma_mass : Real = 0.28909372274994966;
                                attribute Cx : Real = -5.472022807225585;
                                attribute sigma_Cx : Real = 28.721044428837228;
                                attribute Cy : Real = 23.642810713499784;
                                attribute sigma_Cy : Real = 28.23690002309109;
                                attribute Cz : Real = -93.32370357587934;
                                attribute sigma_Cz : Real = 29.057750463592832;
                                attribute Ixx : Real = 1.3695070907128233;
                                attribute sigma_Ixx : Real = 0.37074144170588635;
                                attribute Iyy : Real = 1.5401452426070448;
                                attribute sigma_Iyy : Real = 0.3723953238821935;
                                attribute Izz : Real = 1.3913389016039324;
                                attribute sigma_Izz : Real = 0.37017423652493897;
                                attribute Ixy : Real = -0.0515723913759841;
                                attribute sigma_Ixy : Real = 0.02351283871158888;
                                attribute Ixz : Real = 0.010653319753149162;
                                attribute sigma_Ixz : Real = 0.022566176940390956;
                                attribute Iyz : Real = -0.007955411765144669;
                                attribute sigma_Iyz : Real = 0.02209918015384651;
                            }
                            part <'C.1.1.3.2.1.2.4'> 'Part 299' {
                                attribute POIconv : String = "-";
                                attribute Ipoint : Boolean = false;
                                attribute mass : Real = 0.5965689031465444;
                                attribute sigma_mass : Real = 0.28909372274994966;
                                attribute Cx : Real = 19.347883528098464;
                                attribute sigma_Cx : Real = 28.721044428837228;
                                attribute Cy : Real = -51.34479599073529;
                                attribute sigma_Cy : Real = 28.23690002309109;
                                attribute Cz : Real = -20.803561015054584;
                                attribute sigma_Cz : Real = 29.057750463592832;
                                attribute Ixx : Real = 0.7892307138756195;
                                attribute sigma_Ixx : Real = 0.37074144170588635;
                                attribute Iyy : Real = 0.7601693816530307;
                                attribute sigma_Iyy : Real = 0.3723953238821935;
                                attribute Izz : Real = 0.8082400186559422;
                                attribute sigma_Izz : Real = 0.37017423652493897;
                                attribute Ixy : Real = 0.023249749580558605;
                                attribute sigma_Ixy : Real = 0.02351283871158888;
                                attribute Ixz : Real = -0.021664098105181082;
                                attribute sigma_Ixz : Real = 0.022566176940390956;
                                attribute Iyz : Real = 0.044985378330058015;
                                attribute sigma_Iyz : Real = 0.02209918015384651;
                            }
                        }
                        part <'C.1.1.3.2.1.3'> 'Subassembly 88' {
                            attribute POIconv : String = "-";
                            attribute Ipoint : Boolean = false;
                            attribute mass : Real = 1.0781655693587382;
                            attribute sigma_mass : Real = 0.5781874454998993;
                            attribute Cx : Real = 51.338589982629244;
                            attribute sigma_Cx : Real = 43.1677039568792;
                            attribute Cy : Real = 19.513449885737316;
                            attribute sigma_Cy : Real = 32.54344698074651;
                            attribute Cz : Real = -9.270801841580855;
                            attribute sigma_Cz : Real = 17.063533570364562;
                            attribute Ixx : Real = 2317.411602856895;
                            attribute sigma_Ixx : Real = 2491.4993470097393;
                            attribute Iyy : Real = 1052.2201308397262;
                            attribute sigma_Iyy : Real = 5791.226627727743;
                            attribute Izz : Real = 3312.5037417122735;
                            attribute sigma_Izz : Real = 7413.157556600724;
                            attribute Ixy : Real = -1065.2711668055463;
                            attribute sigma_Ixy : Real = 2934.2472165339373;
                            attribute Ixz : Real = -76.00824453680825;
                            attribute sigma_Ixz : Real = 581.873913002774;
                            attribute Iyz : Real = 49.676999742750894;
                            attribute sigma_Iyz : Real = 825.5623897586447;
                            part <'C.1.1.3.2.1.3.1'> 'Part 300' {
                                attribute POIconv : String = "-";
                                attribute Ipoint : Boolean = false;
                                attribute mass : Real = 0.3302818592193071;
                                attribute sigma_mass : Real = 0.28909372274994966;
                                attribute Cx : Real = 18.362718960270286;
                                attribute sigma_Cx : Real = 28.721044428837228;
                                attribute Cy : Real = -49.72509811632335;
                                attribute sigma_Cy : Real = 28.23690002309109;
                                attribute Cz : Real = -7.727361470460892;
                                attribute sigma_Cz : Real = 29.057750463592832;
                                attribute Ixx : Real = 0.469462949777523;
                                attribute sigma_Ixx : Real = 0.37074144170588635;
                                attribute Iyy : Real = 0.4981432648281274;
                                attribute sigma_Iyy : Real = 0.3723953238821935;
                                attribute Izz : Real = 0.4917618774933188;
                                attribute sigma_Izz : Real = 0.37017423652493897;
                                attribute Ixy : Real = -0.010115855753077836;
                                attribute sigma_Ixy : Real = 0.02351283871158888;
                                attribute Ixz : Real = -0.02150208003476731;
                                attribute sigma_Ixz : Real = 0.022566176940390956;
                                attribute Iyz : Real = -0.00087923625547887;
                                attribute sigma_Iyz : Real = 0.02209918015384651;
                            }
                            part <'C.1.1.3.2.1.3.2'> 'Part 301' {
                                attribute POIconv : String = "-";
                                attribute Ipoint : Boolean = false;
                                attribute mass : Real = 0.3170500951097347;
                                attribute sigma_mass : Real = 0.28909372274994966;
                                attribute Cx : Real = 39.879792649298906;
                                attribute sigma_Cx : Real = 28.721044428837228;
                                attribute Cy : Real = 49.74324256181717;
                                attribute sigma_Cy : Real = 28.23690002309109;
                                attribute Cz : Real = -16.910056164488196;
                                attribute sigma_Cz : Real = 29.057750463592832;
                                attribute Ixx : Real = 0.3868403339358573;
                                attribute sigma_Ixx : Real = 0.37074144170588635;
                                attribute Iyy : Real = 0.4332074035148762;
                                attribute sigma_Iyy : Real = 0.3723953238821935;
                                attribute Izz : Real = 0.3714825106179182;
                                attribute sigma_Izz : Real = 0.37017423652493897;
                                attribute Ixy : Real = 0.016979672110440942;
                                attribute sigma_Ixy : Real = 0.02351283871158888;
                                attribute Ixz : Real = 3.085962524271642e-05;
                                attribute sigma_Ixz : Real = 0.022566176940390956;
                                attribute Iyz : Real = 0.0005943747919141626;
                                attribute sigma_Iyz : Real = 0.02209918015384651;
                            }
                            part <'C.1.1.3.2.1.3.3'> 'Part 302' {
                                attribute POIconv : String = "-";
                                attribute Ipoint : Boolean = false;
                                attribute mass : Real = 0.004349761590827257;
                                attribute sigma_mass : Real = 0.28909372274994966;
                                attribute Cx : Real = -88.5775972623378;
                                attribute sigma_Cx : Real = 28.721044428837228;
                                attribute Cy : Real = 85.53621731698513;
                                attribute sigma_Cy : Real = 28.23690002309109;
                                attribute Cz : Real = -5.550558585673571;
                                attribute sigma_Cz : Real = 29.057750463592832;
                                attribute Ixx : Real = 0.005913005331301421;
                                attribute sigma_Ixx : Real = 0.37074144170588635;
                                attribute Iyy : Real = 0.005501464960847597;
                                attribute sigma_Iyy : Real = 0.3723953238821935;
                                attribute Izz : Real = 0.0052591730843552;
                                attribute sigma_Izz : Real = 0.37017423652493897;
                                attribute Ixy : Real = 0.0004279151971362525;
                                attribute sigma_Ixy : Real = 0.02351283871158888;
                                attribute Ixz : Real = 2.36131770010035e-05;
                                attribute sigma_Ixz : Real = 0.022566176940390956;
                                attribute Iyz : Real = 0.0002209161769528973;
                                attribute sigma_Iyz : Real = 0.02209918015384651;
                            }
                            part <'C.1.1.3.2.1.3.4'> 'Part 303' {
                                attribute POIconv : String = "-";
                                attribute Ipoint : Boolean = false;
                                attribute mass : Real = 0.42648385343886913;
                                attribute sigma_mass : Real = 0.28909372274994966;
                                attribute Cx : Real = 86.82163748890162;
                                attribute sigma_Cx : Real = 28.721044428837228;
                                attribute Cy : Real = 49.98750961385667;
                                attribute sigma_Cy : Real = 28.23690002309109;
                                attribute Cz : Real = -4.82497401535511;
                                attribute sigma_Cz : Real = 29.057750463592832;
                                attribute Ixx : Real = 0.6509581627977518;
                                attribute sigma_Ixx : Real = 0.37074144170588635;
                                attribute Iyy : Real = 0.6067174619344557;
                                attribute sigma_Iyy : Real = 0.3723953238821935;
                                attribute Izz : Real = 0.6184371040711442;
                                attribute sigma_Izz : Real = 0.37017423652493897;
                                attribute Ixy : Real = -0.022935411706845953;
                                attribute sigma_Ixy : Real = 0.02351283871158888;
                                attribute Ixz : Real = -0.029081380340360178;
                                attribute sigma_Ixz : Real = 0.022566176940390956;
                                attribute Iyz : Real = 0.013408712220088409;
                                attribute sigma_Iyz : Real = 0.02209918015384651;
                            }
                        }
                        part <'C.1.1.3.2.1.4'> 'Subassembly 89' {
                            attribute POIconv : String = "-";
                            attribute Ipoint : Boolean = false;
                            attribute mass : Real = 2.447341838692315;
                            attribute sigma_mass : Real = 0.5781874454998993;
                            attribute Cx : Real = -34.57022914554181;
                            attribute sigma_Cx : Real = 17.203059702228497;
                            attribute Cy : Real = 5.286456004137623;
                            attribute sigma_Cy : Real = 21.911792972225115;
                            attribute Cz : Real = 56.52246013510792;
                            attribute sigma_Cz : Real = 17.290799407172088;
                            attribute Ixx : Real = 10465.156407163851;
                            attribute sigma_Ixx : Real = 5889.520891144453;
                            attribute Iyy : Real = 2483.6557333423566;
                            attribute sigma_Iyy : Real = 2664.397507270976;
                            attribute Izz : Real = 9206.83190588984;
                            attribute sigma_Izz : Real = 5638.713061513838;
                            attribute Ixy : Real = 1165.0376985633513;
                            attribute sigma_Ixy : Real = 2578.6403972785315;
                            attribute Ixz : Real = -881.2978249365348;
                            attribute sigma_Ixz : Real = 1281.3054394869932;
                            attribute Iyz : Real = 2476.2068281969005;
                            attribute sigma_Iyz : Real = 2693.2496381040737;
                            part <'C.1.1.3.2.1.4.1'> 'Part 304' {
                                attribute POIconv : String = "+";
                                attribute Ipoint : Boolean = false;
                                attribute mass : Real = 0.7463409944160376;
                                attribute sigma_mass : Real = 0.28909372274994966;
                                attribute Cx : Real = -26.504614809527993;
                                attribute sigma_Cx : Real = 28.721044428837228;
                                attribute Cy : Real = 62.05139560624957;
                                attribute sigma_Cy : Real = 28.23690002309109;
                                attribute Cz : Real = 61.13782003521919;
                                attribute sigma_Cz : Real = 29.057750463592832;
                                attribute Ixx : Real = 1.0452339481371151;
                                attribute sigma_Ixx : Real = 0.37074144170588635;
                                attribute Iyy : Real = 1.1456713743509077;
                                attribute sigma_Iyy : Real = 0.3723953238821935;
                                attribute Izz : Real = 0.9965550771022512;
                                attribute sigma_Izz : Real = 0.37017423652493897;
                                attribute Ixy : Real = -0.0037844778312448903;
                                attribute sigma_Ixy : Real = 0.02351283871158888;
                                attribute Ixz : Real = -0.018690386601199538;
                                attribute sigma_Ixz : Real = 0.022566176940390956;
                                attribute Iyz : Real = -0.0353752081346525;
                                attribute sigma_Iyz : Real = 0.02209918015384651;
                            }
                            part <'C.1.1.3.2.1.4.2'> 'Part 305' {
                                attribute POIconv : String = "-";
                                attribute Ipoint : Boolean = false;
                                attribute mass : Real = 0.07366071792808361;
                                attribute sigma_mass : Real = 0.28909372274994966;
                                attribute Cx : Real = -79.16469965130091;
                                attribute sigma_Cx : Real = 28.721044428837228;
                                attribute Cy : Real = 81.36048577725887;
                                attribute sigma_Cy : Real = 28.23690002309109;
                                attribute Cz : Real = 63.619013130664825;
                                attribute sigma_Cz : Real = 29.057750463592832;
                                attribute Ixx : Real = 0.07950071933095791;
                                attribute sigma_Ixx : Real = 0.37074144170588635;
                                attribute Iyy : Real = 0.08860937141400956;
                                attribute sigma_Iyy : Real = 0.3723953238821935;
                                attribute Izz : Real = 0.08804109037191804;
                                attribute sigma_Izz : Real = 0.37017423652493897;
                                attribute Ixy : Real = -0.008543395605583287;
                                attribute sigma_Ixy : Real = 0.02351283871158888;
                                attribute Ixz : Real = 0.00783892662881568;
                                attribute sigma_Ixz : Real = 0.022566176940390956;
                                attribute Iyz : Real = 0.002312820694277688;
                                attribute sigma_Iyz : Real = 0.02209918015384651;
                            }
                            part <'C.1.1.3.2.1.4.3'> 'Part 306' {
                                attribute POIconv : String = "+";
                                attribute Ipoint : Boolean = false;
                                attribute mass : Real = 0.7772379204537719;
                                attribute sigma_mass : Real = 0.28909372274994966;
                                attribute Cx : Real = -19.621654599905014;
                                attribute sigma_Cx : Real = 28.721044428837228;
                                attribute Cy : Real = -78.24674462899566;
                                attribute sigma_Cy : Real = 28.23690002309109;
                                attribute Cz : Real = 89.25165296532214;
                                attribute sigma_Cz : Real = 29.057750463592832;
                                attribute Ixx : Real = 0.9711164702176183;
                                attribute sigma_Ixx : Real = 0.37074144170588635;
                                attribute Iyy : Real = 0.9466826681114774;
                                attribute sigma_Iyy : Real = 0.3723953238821935;
                                attribute Izz : Real = 0.8791674095456459;
                                attribute sigma_Izz : Real = 0.37017423652493897;
                                attribute Ixy : Real = 0.0035185979756948505;
                                attribute sigma_Ixy : Real = 0.02351283871158888;
                                attribute Ixz : Real = 0.0022976645382708125;
                                attribute sigma_Ixz : Real = 0.022566176940390956;
                                attribute Iyz : Real = 0.0030417589459110278;
                                attribute sigma_Iyz : Real = 0.02209918015384651;
                            }
                            part <'C.1.1.3.2.1.4.4'> 'Part 307' {
                                attribute POIconv : String = "-";
                                attribute Ipoint : Boolean = false;
                                attribute mass : Real = 0.8501022058944218;
                                attribute sigma_mass : Real = 0.28909372274994966;
                                attribute Cx : Real = -51.454595290124416;
                                attribute sigma_Cx : Real = 28.721044428837228;
                                attribute Cy : Real = 25.23170718923211;
                                attribute sigma_Cy : Real = 28.23690002309109;
                                attribute Cz : Real = 21.931632049381733;
                                attribute sigma_Cz : Real = 29.057750463592832;
                                attribute Ixx : Real = 0.9203361436659883;
                                attribute sigma_Ixx : Real = 0.37074144170588635;
                                attribute Iyy : Real = 1.0513699248062658;
                                attribute sigma_Iyy : Real = 0.3723953238821935;
                                attribute Izz : Real = 1.0125844164820472;
                                attribute sigma_Izz : Real = 0.37017423652493897;
                                attribute Ixy : Real = 0.03954797218949646;
                                attribute sigma_Ixy : Real = 0.02351283871158888;
                                attribute Ixz : Real = -0.0855337919866877;
                                attribute sigma_Ixz : Real = 0.022566176940390956;
                                attribute Iyz : Real = 0.019948801103531054;
                                attribute sigma_Iyz : Real = 0.02209918015384651;
                            }
                        }
                    }
                    part <'C.1.1.3.2.2'> 'Assembly 25' {
                        attribute POIconv : String = "-";
                        attribute Ipoint : Boolean = false;
                        attribute mass : Real = 7.964605317942565;
                        attribute sigma_mass : Real = 1.119655173703659;
                        attribute Cx : Real = 23.177263931937752;
                        attribute sigma_Cx : Real = 12.22252303192224;
                        attribute Cy : Real = 8.845085666922255;
                        attribute sigma_Cy : Real = 12.525150142985952;
                        attribute Cz : Real = -17.001687518335324;
                        attribute sigma_Cz : Real = 13.314681153521803;
                        attribute Ixx : Real = 45022.91940671184;
                        attribute sigma_Ixx : Real = 15826.395618096787;
                        attribute Iyy : Real = 46067.939854299046;
                        attribute sigma_Iyy : Real = 16373.713670510599;
                        attribute Izz : Real = 45883.885529156585;
                        attribute sigma_Izz : Real = 13991.099464960414;
                        attribute Ixy : Real = 1985.3246176596856;
                        attribute sigma_Ixy : Real = 6427.912552654499;
                        attribute Ixz : Real = 1752.5400102426715;
                        attribute sigma_Ixz : Real = 7605.6138453846215;
                        attribute Iyz : Real = -268.39365297905215;
                        attribute sigma_Iyz : Real = 6716.269501817188;
                        part <'C.1.1.3.2.2.1'> 'Subassembly 90' {
                            attribute POIconv : String = "-";
                            attribute Ipoint : Boolean = false;
                            attribute mass : Real = 1.5497204273643437;
                            attribute sigma_mass : Real = 0.5007250159521434;
                            attribute Cx : Real = -12.200028901379685;
                            attribute sigma_Cx : Real = 32.09434791154767;
                            attribute Cy : Real = 49.05796249586195;
                            attribute sigma_Cy : Real = 21.06058192240431;
                            attribute Cz : Real = -73.35737246590675;
                            attribute sigma_Cz : Real = 34.689754358912104;
                            attribute Ixx : Real = 1209.26422038928;
                            attribute sigma_Ixx : Real = 6274.152158331834;
                            attribute Iyy : Real = 8765.101740225009;
                            attribute sigma_Iyy : Real = 9305.834494599176;
                            attribute Izz : Real = 8080.122408565616;
                            attribute sigma_Izz : Real = 5412.500142398559;
                            attribute Ixy : Real = -1411.8737106749807;
                            attribute sigma_Ixy : Real = 2237.282079093111;
                            attribute Ixz : Real = -2451.463999745645;
                            attribute sigma_Ixz : Real = 3967.912964763528;
                            attribute Iyz : Real = -475.8309167013161;
                            attribute sigma_Iyz : Real = 1089.654182504393;
                            part <'C.1.1.3.2.2.1.1'> 'Part 308' {
                                attribute POIconv : String = "-";
                                attribute Ipoint : Boolean = false;
                                attribute mass : Real = 0.9628821893972345;
                                attribute sigma_mass : Real = 0.28909372274994966;
                                attribute Cx : Real = -67.02563893049955;
                                attribute sigma_Cx : Real = 28.721044428837228;
                                attribute Cy : Real = 38.92446053214371;
                                attribute sigma_Cy : Real = 28.23690002309109;
                                attribute Cz : Real = -91.79585943929851;
                                attribute sigma_Cz : Real = 29.057750463592832;
                                attribute Ixx : Real = 1.325991570317825;
                                attribute sigma_Ixx : Real = 0.37074144170588635;
                                attribute Iyy : Real = 1.3767848150268163;
                                attribute sigma_Iyy : Real = 0.3723953238821935;
                                attribute Izz : Real = 1.331913580574206;
                                attribute sigma_Izz : Real = 0.37017423652493897;
                                attribute Ixy : Real = -0.08235468955166947;
                                attribute sigma_Ixy : Real = 0.02351283871158888;
                                attribute Ixz : Real = -0.005362268663962171;
                                attribute sigma_Ixz : Real = 0.022566176940390956;
                                attribute Iyz : Real = -0.08305653325092678;
                                attribute sigma_Iyz : Real = 0.02209918015384651;
                            }
                            part <'C.1.1.3.2.2.1.2'> 'Part 309' {
                                attribute POIconv : String = "+";
                                attribute Ipoint : Boolean = false;
                                attribute mass : Real = 0.5805594417655375;
                                attribute sigma_mass : Real = 0.28909372274994966;
                                attribute Cx : Real = 79.54693427309394;
                                attribute sigma_Cx : Real = 28.721044428837228;
                                attribute Cy : Real = 65.67559484392405;
                                attribute sigma_Cy : Real = 28.23690002309109;
                                attribute Cz : Real = -44.329586112871766;
                                attribute sigma_Cz : Real = 29.057750463592832;
                                attribute Ixx : Real = 0.7634266870756968;
                                attribute sigma_Ixx : Real = 0.37074144170588635;
                                attribute Iyy : Real = 0.7509323257853486;
                                attribute sigma_Iyy : Real = 0.3723953238821935;
                                attribute Izz : Real = 0.7493895127889785;
                                attribute sigma_Izz : Real = 0.37017423652493897;
                                attribute Ixy : Real = -0.0007868340243789797;
                                attribute sigma_Ixy : Real = 0.02351283871158888;
                                attribute Ixz : Real = -0.003883483413904091;
                                attribute sigma_Ixz : Real = 0.022566176940390956;
                                attribute Iyz : Real = 0.014998158225549642;
                                attribute sigma_Iyz : Real = 0.02209918015384651;
                            }
                            part <'C.1.1.3.2.2.1.3'> 'Part 310' {
                                attribute POIconv : String = "+";
                                attribute Ipoint : Boolean = false;
                                attribute mass : Real = 0.006278796201571822;
                                attribute sigma_mass : Real = 0.28909372274994966;
                                attribute Cx : Real = -87.68620318733156;
                                attribute sigma_Cx : Real = 28.721044428837228;
                                attribute Cy : Real = 66.55258950777352;
                                attribute sigma_Cy : Real = 28.23690002309109;
                                attribute Cz : Real = 70.25857497937977;
                                attribute sigma_Cz : Real = 29.057750463592832;
                                attribute Ixx : Real = 0.009083717793138048;
                                attribute sigma_Ixx : Real = 0.37074144170588635;
                                attribute Iyy : Real = 0.00852770142378268;
                                attribute sigma_Iyy : Real = 0.3723953238821935;
                                attribute Izz : Real = 0.007307598921316748;
                                attribute sigma_Izz : Real = 0.37017423652493897;
                                attribute Ixy : Real = -0.0007172538256833759;
                                attribute sigma_Ixy : Real = 0.02351283871158888;
                                attribute Ixz : Real = -0.0002211488279135332;
                                attribute sigma_Ixz : Real = 0.022566176940390956;
                                attribute Iyz : Real = -2.006876692919036e-05;
                                attribute sigma_Iyz : Real = 0.02209918015384651;
                            }
                        }
                        part <'C.1.1.3.2.2.2'> 'Subassembly 91' {
                            attribute POIconv : String = "-";
                            attribute Ipoint : Boolean = false;
                            attribute mass : Real = 0.8653289071782492;
                            attribute sigma_mass : Real = 0.5781874454998993;
                            attribute Cx : Real = 14.12531633433657;
                            attribute sigma_Cx : Real = 45.784427134217566;
                            attribute Cy : Real = -39.15810217280058;
                            attribute sigma_Cy : Real = 40.740852722065675;
                            attribute Cz : Real = -31.913534681502743;
                            attribute sigma_Cz : Real = 50.18797548039743;
                            attribute Ixx : Real = 3683.2619329516274;
                            attribute sigma_Ixx : Real = 5500.607024365402;
                            attribute Iyy : Real = 5760.912170488314;
                            attribute sigma_Iyy : Real = 6078.193595888625;
                            attribute Izz : Real = 2964.467881187208;
                            attribute sigma_Izz : Real = 4863.88860432609;
                            attribute Ixy : Real = 673.8000814070933;
                            attribute sigma_Ixy : Real = 2265.2718087429184;
                            attribute Ixz : Real = 1999.3710304471547;
                            attribute sigma_Ixz : Real = 2784.3376746560893;
                            attribute Iyz : Real = 60.71496127383115;
                            attribute sigma_Iyz : Real = 2184.5620133179154;
                            part <'C.1.1.3.2.2.2.1'> 'Part 311' {
                                attribute POIconv : String = "-";
                                attribute Ipoint : Boolean = false;
                                attribute mass : Real = 0.507306068098871;
                                attribute sigma_mass : Real = 0.28909372274994966;
                                attribute Cx : Real = 51.52768441475928;
                                attribute sigma_Cx : Real = 28.721044428837228;
                                attribute Cy : Real = -43.57835128903389;
                                attribute sigma_Cy : Real = 28.23690002309109;
                                attribute Cz : Real = -80.80584607087076;
                                attribute sigma_Cz : Real = 29.057750463592832;
                                attribute Ixx : Real = 0.5182907025904251;
                                attribute sigma_Ixx : Real = 0.37074144170588635;
                                attribute Iyy : Real = 0.6396566292883058;
                                attribute sigma_Iyy : Real = 0.3723953238821935;
                                attribute Izz : Real = 0.60675846262782;
                                attribute sigma_Izz : Real = 0.37017423652493897;
                                attribute Ixy : Real = 0.027774789788406237;
                                attribute sigma_Ixy : Real = 0.02351283871158888;
                                attribute Ixz : Real = -0.05421418779891808;
                                attribute sigma_Ixz : Real = 0.022566176940390956;
                                attribute Iyz : Real = 0.013214062933677433;
                                attribute sigma_Iyz : Real = 0.02209918015384651;
                            }
                            part <'C.1.1.3.2.2.2.2'> 'Part 312' {
                                attribute POIconv : String = "-";
                                attribute Ipoint : Boolean = false;
                                attribute mass : Real = 0.27923376768874003;
                                attribute sigma_mass : Real = 0.28909372274994966;
                                attribute Cx : Real = -58.8215580675751;
                                attribute sigma_Cx : Real = 28.721044428837228;
                                attribute Cy : Real = -27.714911568909883;
                                attribute sigma_Cy : Real = 28.23690002309109;
                                attribute Cz : Real = 39.66203657910228;
                                attribute sigma_Cz : Real = 29.057750463592832;
                                attribute Ixx : Real = 0.3003349372228094;
                                attribute sigma_Ixx : Real = 0.37074144170588635;
                                attribute Iyy : Real = 0.30397909106428844;
                                attribute sigma_Iyy : Real = 0.3723953238821935;
                                attribute Izz : Real = 0.3530848292248687;
                                attribute sigma_Izz : Real = 0.37017423652493897;
                                attribute Ixy : Real = -0.0016256423900652857;
                                attribute sigma_Ixy : Real = 0.02351283871158888;
                                attribute Ixz : Real = -0.004426881182763229;
                                attribute sigma_Ixz : Real = 0.022566176940390956;
                                attribute Iyz : Real = 0.01567681694051682;
                                attribute sigma_Iyz : Real = 0.02209918015384651;
                            }
                            part <'C.1.1.3.2.2.2.3'> 'Part 313' {
                                attribute POIconv : String = "+";
                                attribute Ipoint : Boolean = false;
                                attribute mass : Real = 0.053065631135599686;
                                attribute sigma_mass : Real = 0.28909372274994966;
                                attribute Cx : Real = 74.80520722456276;
                                attribute sigma_Cx : Real = 28.721044428837228;
                                attribute Cy : Real = -99.91779676638544;
                                attribute sigma_Cy : Real = 28.23690002309109;
                                attribute Cz : Real = 72.3065145779401;
                                attribute sigma_Cz : Real = 29.057750463592832;
                                attribute Ixx : Real = 0.06803522128108468;
                                attribute sigma_Ixx : Real = 0.37074144170588635;
                                attribute Iyy : Real = 0.06849965363191944;
                                attribute sigma_Iyy : Real = 0.3723953238821935;
                                attribute Izz : Real = 0.07269471227138315;
                                attribute sigma_Izz : Real = 0.37017423652493897;
                                attribute Ixy : Real = 0.00015071735385599846;
                                attribute sigma_Ixy : Real = 0.02351283871158888;
                                attribute Ixz : Real = -0.0007294193082956819;
                                attribute sigma_Ixz : Real = 0.022566176940390956;
                                attribute Iyz : Real = -0.0010525329059136177;
                                attribute sigma_Iyz : Real = 0.02209918015384651;
                            }
                            part <'C.1.1.3.2.2.2.4'> 'Part 314' {
                                attribute POIconv : String = "+";
                                attribute Ipoint : Boolean = false;
                                attribute mass : Real = 0.025723440255038442;
                                attribute sigma_mass : Real = 0.28909372274994966;
                                attribute Cx : Real = -56.83076097629964;
                                attribute sigma_Cx : Real = 28.721044428837228;
                                attribute Cy : Real = 49.14056593552232;
                                attribute sigma_Cy : Real = 28.23690002309109;
                                attribute Cz : Real = -59.64905023574829;
                                attribute sigma_Cz : Real = 29.057750463592832;
                                attribute Ixx : Real = 0.03401345992686182;
                                attribute sigma_Ixx : Real = 0.37074144170588635;
                                attribute Iyy : Real = 0.03412561256690141;
                                attribute sigma_Iyy : Real = 0.3723953238821935;
                                attribute Izz : Real = 0.03451290554819782;
                                attribute sigma_Izz : Real = 0.37017423652493897;
                                attribute Ixy : Real = -0.0003071215644418075;
                                attribute sigma_Ixy : Real = 0.02351283871158888;
                                attribute Ixz : Real = 0.0008896193491510361;
                                attribute sigma_Ixz : Real = 0.022566176940390956;
                                attribute Iyz : Real = -0.0007108032788825308;
                                attribute sigma_Iyz : Real = 0.02209918015384651;
                            }
                        }
                        part <'C.1.1.3.2.2.3'> 'Subassembly 92' {
                            attribute POIconv : String = "-";
                            attribute Ipoint : Boolean = false;
                            attribute mass : Real = 1.6550438557702583;
                            attribute sigma_mass : Real = 0.5007250159521434;
                            attribute Cx : Real = 21.766300233010114;
                            attribute sigma_Cx : Real = 23.233954130420024;
                            attribute Cy : Real = 57.43092795865037;
                            attribute sigma_Cy : Real = 22.799666588150362;
                            attribute Cz : Real = -10.512089942651688;
                            attribute sigma_Cz : Real = 28.15819835914093;
                            attribute Ixx : Real = 6686.226284151897;
                            attribute sigma_Ixx : Real = 5212.629345319063;
                            attribute Iyy : Real = 7795.860806031146;
                            attribute sigma_Iyy : Real = 5418.964334124994;
                            attribute Izz : Real = 1979.0823989945757;
                            attribute sigma_Izz : Real = 3004.436508892993;
                            attribute Ixy : Real = 297.49952229492783;
                            attribute sigma_Ixy : Real = 1471.892455954797;
                            attribute Ixz : Real = 2627.124903280184;
                            attribute sigma_Ixz : Real = 2610.925843636063;
                            attribute Iyz : Real = -1324.6040815572278;
                            attribute sigma_Iyz : Real = 2447.4309877685696;
                            part <'C.1.1.3.2.2.3.1'> 'Part 315' {
                                attribute POIconv : String = "+";
                                attribute Ipoint : Boolean = false;
                                attribute mass : Real = 0.8841884749981109;
                                attribute sigma_mass : Real = 0.28909372274994966;
                                attribute Cx : Real = -2.67761186696589;
                                attribute sigma_Cx : Real = 28.721044428837228;
                                attribute Cy : Real = 69.39258752390742;
                                attribute sigma_Cy : Real = 28.23690002309109;
                                attribute Cz : Real = 46.854346012696624;
                                attribute sigma_Cz : Real = 29.057750463592832;
                                attribute Ixx : Real = 1.189376320613317;
                                attribute sigma_Ixx : Real = 0.37074144170588635;
                                attribute Iyy : Real = 1.205941083905937;
                                attribute sigma_Iyy : Real = 0.3723953238821935;
                                attribute Izz : Real = 1.1648997578996236;
                                attribute sigma_Izz : Real = 0.37017423652493897;
                                attribute Ixy : Real = 0.014061573413145526;
                                attribute sigma_Ixy : Real = 0.02351283871158888;
                                attribute Ixz : Real = -0.013567785908019301;
                                attribute sigma_Ixz : Real = 0.022566176940390956;
                                attribute Iyz : Real = -0.03654059910570495;
                                attribute sigma_Iyz : Real = 0.02209918015384651;
                            }
                            part <'C.1.1.3.2.2.3.2'> 'Part 316' {
                                attribute POIconv : String = "+";
                                attribute Ipoint : Boolean = false;
                                attribute mass : Real = 0.05425436808075756;
                                attribute sigma_mass : Real = 0.28909372274994966;
                                attribute Cx : Real = -33.90569421462715;
                                attribute sigma_Cx : Real = 28.721044428837228;
                                attribute Cy : Real = -9.006574749946594;
                                attribute sigma_Cy : Real = 28.23690002309109;
                                attribute Cz : Real = -83.4563790820539;
                                attribute sigma_Cz : Real = 29.057750463592832;
                                attribute Ixx : Real = 0.06582503402006419;
                                attribute sigma_Ixx : Real = 0.37074144170588635;
                                attribute Iyy : Real = 0.0727462769581792;
                                attribute sigma_Iyy : Real = 0.3723953238821935;
                                attribute Izz : Real = 0.07228960061863357;
                                attribute sigma_Izz : Real = 0.37017423652493897;
                                attribute Ixy : Real = -0.004232131433138974;
                                attribute sigma_Ixy : Real = 0.02351283871158888;
                                attribute Ixz : Real = -0.00023667541681533072;
                                attribute sigma_Ixz : Real = 0.022566176940390956;
                                attribute Iyz : Real = -0.0045218793984314505;
                                attribute sigma_Iyz : Real = 0.02209918015384651;
                            }
                            part <'C.1.1.3.2.2.3.3'> 'Part 317' {
                                attribute POIconv : String = "-";
                                attribute Ipoint : Boolean = false;
                                attribute mass : Real = 0.7166010126913898;
                                attribute sigma_mass : Real = 0.28909372274994966;
                                attribute Cx : Real = 56.1417390126735;
                                attribute sigma_Cx : Real = 28.721044428837228;
                                attribute Cy : Real = 47.701892303302884;
                                attribute sigma_Cy : Real = 28.23690002309109;
                                attribute Cz : Real = -75.77182915993035;
                                attribute sigma_Cz : Real = 29.057750463592832;
                                attribute Ixx : Real = 0.8076271387470669;
                                attribute sigma_Ixx : Real = 0.37074144170588635;
                                attribute Iyy : Real = 0.986578090013967;
                                attribute sigma_Iyy : Real = 0.3723953238821935;
                                attribute Izz : Real = 0.7817123876828004;
                                attribute sigma_Izz : Real = 0.37017423652493897;
                                attribute Ixy : Real = -0.0071684844781875045;
                                attribute sigma_Ixy : Real = 0.02351283871158888;
                                attribute Ixz : Real = -0.0007451193538291595;
                                attribute sigma_Ixz : Real = 0.022566176940390956;
                                attribute Iyz : Real = -0.007232231292846808;
                                attribute sigma_Iyz : Real = 0.02209918015384651;
                            }
                        }
                        part <'C.1.1.3.2.2.4'> 'Subassembly 93' {
                            attribute POIconv : String = "-";
                            attribute Ipoint : Boolean = false;
                            attribute mass : Real = 2.7976520654533523;
                            attribute sigma_mass : Real = 0.5007250159521434;
                            attribute Cx : Real = 41.47903144385975;
                            attribute sigma_Cx : Real = 19.24182025129106;
                            attribute Cy : Real = -7.482026449602659;
                            attribute sigma_Cy : Real = 17.51362983708311;
                            attribute Cz : Real = 16.438307166781026;
                            attribute sigma_Cz : Real = 17.920889412465538;
                            attribute Ixx : Real = 7013.155130346754;
                            attribute sigma_Ixx : Real = 4809.334710921264;
                            attribute Iyy : Real = 11534.661156868357;
                            attribute sigma_Iyy : Real = 6409.515328624735;
                            attribute Izz : Real = 11649.57888515359;
                            attribute sigma_Izz : Real = 6357.199940106987;
                            attribute Ixy : Real = -2510.194729129066;
                            attribute sigma_Ixy : Real = 3061.202093229916;
                            attribute Ixz : Real = 4051.0231609679386;
                            attribute sigma_Ixz : Real = 3138.146114844848;
                            attribute Iyz : Real = -728.2114150059268;
                            attribute sigma_Iyz : Real = 2368.6500331377615;
                            part <'C.1.1.3.2.2.4.1'> 'Part 318' {
                                attribute POIconv : String = "+";
                                attribute Ipoint : Boolean = false;
                                attribute mass : Real = 0.8889756215265952;
                                attribute sigma_mass : Real = 0.28909372274994966;
                                attribute Cx : Real = -32.88555843755603;
                                attribute sigma_Cx : Real = 28.721044428837228;
                                attribute Cy : Real = -45.80324599519372;
                                attribute sigma_Cy : Real = 28.23690002309109;
                                attribute Cz : Real = 42.835584888234735;
                                attribute sigma_Cz : Real = 29.057750463592832;
                                attribute Ixx : Real = 1.1406320663721565;
                                attribute sigma_Ixx : Real = 0.37074144170588635;
                                attribute Iyy : Real = 1.3118710687285449;
                                attribute sigma_Iyy : Real = 0.3723953238821935;
                                attribute Izz : Real = 1.218674073820137;
                                attribute sigma_Izz : Real = 0.37017423652493897;
                                attribute Ixy : Real = 0.07079337227403804;
                                attribute sigma_Ixy : Real = 0.02351283871158888;
                                attribute Ixz : Real = 0.02208765741710296;
                                attribute sigma_Ixz : Real = 0.022566176940390956;
                                attribute Iyz : Real = 0.05792516059510751;
                                attribute sigma_Iyz : Real = 0.02209918015384651;
                            }
                            part <'C.1.1.3.2.2.4.2'> 'Part 319' {
                                attribute POIconv : String = "+";
                                attribute Ipoint : Boolean = false;
                                attribute mass : Real = 0.9409341678854544;
                                attribute sigma_mass : Real = 0.28909372274994966;
                                attribute Cx : Real = 97.86626021377742;
                                attribute sigma_Cx : Real = 28.721044428837228;
                                attribute Cy : Real = -19.441911624744534;
                                attribute sigma_Cy : Real = 28.23690002309109;
                                attribute Cz : Real = -32.84712606109679;
                                attribute sigma_Cz : Real = 29.057750463592832;
                                attribute Ixx : Real = 1.3635594218624387;
                                attribute sigma_Ixx : Real = 0.37074144170588635;
                                attribute Iyy : Real = 1.25727050418053;
                                attribute sigma_Iyy : Real = 0.3723953238821935;
                                attribute Izz : Real = 1.1556787094732983;
                                attribute sigma_Izz : Real = 0.37017423652493897;
                                attribute Ixy : Real = 0.10141737961065309;
                                attribute sigma_Ixy : Real = 0.02351283871158888;
                                attribute Ixz : Real = -0.016584724243580835;
                                attribute sigma_Ixz : Real = 0.022566176940390956;
                                attribute Iyz : Real = 0.008074147491905158;
                                attribute sigma_Iyz : Real = 0.02209918015384651;
                            }
                            part <'C.1.1.3.2.2.4.3'> 'Part 320' {
                                attribute POIconv : String = "-";
                                attribute Ipoint : Boolean = false;
                                attribute mass : Real = 0.9677422760413028;
                                attribute sigma_mass : Real = 0.28909372274994966;
                                attribute Cx : Real = 54.965718602761626;
                                attribute sigma_Cx : Real = 28.721044428837228;
                                attribute Cy : Real = 39.3487214576453;
                                attribute sigma_Cy : Real = 28.23690002309109;
                                attribute Cz : Real = 40.10970429517329;
                                attribute sigma_Cz : Real = 29.057750463592832;
                                attribute Ixx : Real = 0.9196409710813536;
                                attribute sigma_Ixx : Real = 0.37074144170588635;
                                attribute Iyy : Real = 0.940467217425216;
                                attribute sigma_Iyy : Real = 0.3723953238821935;
                                attribute Izz : Real = 0.9065334421784903;
                                attribute sigma_Izz : Real = 0.37017423652493897;
                                attribute Ixy : Real = -0.005298217016151351;
                                attribute sigma_Ixy : Real = 0.02351283871158888;
                                attribute Ixz : Real = -0.021174314867082475;
                                attribute sigma_Ixz : Real = 0.022566176940390956;
                                attribute Iyz : Real = 0.010126942005534816;
                                attribute sigma_Iyz : Real = 0.02209918015384651;
                            }
                        }
                        part <'C.1.1.3.2.2.5'> 'Subassembly 94' {
                            attribute POIconv : String = "-";
                            attribute Ipoint : Boolean = false;
                            attribute mass : Real = 1.0968600621763618;
                            attribute sigma_mass : Real = 0.40884026350990615;
                            attribute Cx : Real = 35.75047621864896;
                            attribute sigma_Cx : Real = 22.41548726430508;
                            attribute Cy : Real = -41.76692340467025;
                            attribute sigma_Cy : Real = 35.9662357137342;
                            attribute Cz : Real = -20.69844917679401;
                            attribute sigma_Cz : Real = 22.70612091804125;
                            attribute Ixx : Real = 6141.279759939006;
                            attribute sigma_Ixx : Real = 4391.821405387105;
                            attribute Iyy : Real = 759.7727837792918;
                            attribute sigma_Iyy : Real = 1190.0918257065134;
                            attribute Izz : Real = 6124.053950187825;
                            attribute sigma_Izz : Real = 4380.851296216056;
                            attribute Ixy : Real = 1459.9993172012782;
                            attribute sigma_Ixy : Real = 1750.7777850315917;
                            attribute Ixz : Real = 379.04071376375043;
                            attribute sigma_Ixz : Real = 594.889230169203;
                            attribute Iyz : Real = -1493.4550342467855;
                            attribute sigma_Iyz : Real = 1775.6720366583202;
                            part <'C.1.1.3.2.2.5.1'> 'Part 321' {
                                attribute POIconv : String = "+";
                                attribute Ipoint : Boolean = false;
                                attribute mass : Real = 0.38982657161960377;
                                attribute sigma_mass : Real = 0.28909372274994966;
                                attribute Cx : Real = 10.995585890486836;
                                attribute sigma_Cx : Real = 28.721044428837228;
                                attribute Cy : Real = 55.75889269821346;
                                attribute sigma_Cy : Real = 28.23690002309109;
                                attribute Cz : Real = 4.62368200533092;
                                attribute sigma_Cz : Real = 29.057750463592832;
                                attribute Ixx : Real = 0.593875336164907;
                                attribute sigma_Ixx : Real = 0.37074144170588635;
                                attribute Iyy : Real = 0.570095051626122;
                                attribute sigma_Iyy : Real = 0.3723953238821935;
                                attribute Izz : Real = 0.5977647188323771;
                                attribute sigma_Izz : Real = 0.37017423652493897;
                                attribute Ixy : Real = -0.008331680534444092;
                                attribute sigma_Ixy : Real = 0.02351283871158888;
                                attribute Ixz : Real = -0.0018383308505807877;
                                attribute sigma_Ixz : Real = 0.022566176940390956;
                                attribute Iyz : Real = -0.00862451112800756;
                                attribute sigma_Iyz : Real = 0.02209918015384651;
                            }
                            part <'C.1.1.3.2.2.5.2'> 'Part 322' {
                                attribute POIconv : String = "-";
                                attribute Ipoint : Boolean = false;
                                attribute mass : Real = 0.7070334905567579;
                                attribute sigma_mass : Real = 0.28909372274994966;
                                attribute Cx : Real = 49.39921302720904;
                                attribute sigma_Cx : Real = 28.721044428837228;
                                attribute Cy : Real = -95.53828649222851;
                                attribute sigma_Cy : Real = 28.23690002309109;
                                attribute Cz : Real = -34.6599371638149;
                                attribute sigma_Cz : Real = 29.057750463592832;
                                attribute Ixx : Real = 0.8683287334960428;
                                attribute sigma_Ixx : Real = 0.37074144170588635;
                                attribute Iyy : Real = 0.8252912129048904;
                                attribute sigma_Iyy : Real = 0.3723953238821935;
                                attribute Izz : Real = 0.8172652405743035;
                                attribute sigma_Izz : Real = 0.37017423652493897;
                                attribute Ixy : Real = -0.04404569806229386;
                                attribute sigma_Ixy : Real = 0.02351283871158888;
                                attribute Ixz : Real = -0.052528960149597084;
                                attribute sigma_Ixz : Real = 0.022566176940390956;
                                attribute Iyz : Real = 0.02704553983832496;
                                attribute sigma_Iyz : Real = 0.02209918015384651;
                            }
                        }
                    }
                    part <'C.1.1.3.2.3'> 'Assembly 26' {
                        attribute POIconv : String = "-";
                        attribute Ipoint : Boolean = false;
                        attribute mass : Real = 2.5698179918832613;
                        attribute sigma_mass : Real = 0.7081321085790055;
                        attribute Cx : Real = 4.449442760771421;
                        attribute sigma_Cx : Real = 20.230864546616516;
                        attribute Cy : Real = 39.93713626320637;
                        attribute sigma_Cy : Real = 24.914140242212206;
                        attribute Cz : Real = -49.85309956323329;
                        attribute sigma_Cz : Real = 19.18156059617906;
                        attribute Ixx : Real = 14949.527023657676;
                        attribute sigma_Ixx : Real = 9041.20105872142;
                        attribute Iyy : Real = 13830.787563692045;
                        attribute sigma_Iyy : Real = 6583.552485248391;
                        attribute Izz : Real = 17440.74364879273;
                        attribute sigma_Izz : Real = 9475.291369760362;
                        attribute Ixy : Real = -3244.7269545407235;
                        attribute sigma_Ixy : Real = 3558.681987893376;
                        attribute Ixz : Real = -1423.0906616012605;
                        attribute sigma_Ixz : Real = 3192.543629668814;
                        attribute Iyz : Real = 2035.242152088312;
                        attribute sigma_Iyz : Real = 2866.3168514423423;
                        part <'C.1.1.3.2.3.1'> 'Subassembly 95' {
                            attribute POIconv : String = "-";
                            attribute Ipoint : Boolean = false;
                            attribute mass : Real = 0.520552234563278;
                            attribute sigma_mass : Real = 0.40884026350990615;
                            attribute Cx : Real = -30.42796814598923;
                            attribute sigma_Cx : Real = 31.965586368192202;
                            attribute Cy : Real = -65.47524187322686;
                            attribute sigma_Cy : Real = 49.71182769286749;
                            attribute Cz : Real = -52.15635553973427;
                            attribute sigma_Cz : Real = 23.569939703760298;
                            attribute Ixx : Real = 1038.823948847909;
                            attribute sigma_Ixx : Real = 1880.2622698678183;
                            attribute Iyy : Real = 280.7954212194919;
                            attribute sigma_Iyy : Real = 626.7907744172105;
                            attribute Izz : Real = 1286.1019914830308;
                            attribute sigma_Izz : Real = 2287.2146128199015;
                            attribute Ixy : Real = -519.0892477608735;
                            attribute sigma_Ixy : Real = 963.4143759110988;
                            attribute Ixz : Real = 65.95835522006001;
                            attribute sigma_Ixz : Real = 241.53870538108555;
                            attribute Iyz : Real = 129.82957113775058;
                            attribute sigma_Iyz : Real = 467.1287821461309;
                            part <'C.1.1.3.2.3.1.1'> 'Part 323' {
                                attribute POIconv : String = "+";
                                attribute Ipoint : Boolean = false;
                                attribute mass : Real = 0.3878688797953073;
                                attribute sigma_mass : Real = 0.28909372274994966;
                                attribute Cx : Real = -43.5926400590688;
                                attribute sigma_Cx : Real = 28.721044428837228;
                                attribute Cy : Real = -91.387655492872;
                                attribute sigma_Cy : Real = 28.23690002309109;
                                attribute Cz : Real = -48.86414282955229;
                                attribute sigma_Cz : Real = 29.057750463592832;
                                attribute Ixx : Real = 0.42184964004594716;
                                attribute sigma_Ixx : Real = 0.37074144170588635;
                                attribute Iyy : Real = 0.41817877777390067;
                                attribute sigma_Iyy : Real = 0.3723953238821935;
                                attribute Izz : Real = 0.4444434323184965;
                                attribute sigma_Izz : Real = 0.37017423652493897;
                                attribute Ixy : Real = -0.005996255359739961;
                                attribute sigma_Ixy : Real = 0.02351283871158888;
                                attribute Ixz : Real = -0.001913937062915384;
                                attribute sigma_Ixz : Real = 0.022566176940390956;
                                attribute Iyz : Real = 0.002494752411062521;
                                attribute sigma_Iyz : Real = 0.02209918015384651;
                            }
                            part <'C.1.1.3.2.3.1.2'> 'Part 324' {
                                attribute POIconv : String = "+";
                                attribute Ipoint : Boolean = false;
                                attribute mass : Real = 0.13268335476797075;
                                attribute sigma_mass : Real = 0.28909372274994966;
                                attribute Cx : Real = 8.055883552879095;
                                attribute sigma_Cx : Real = 28.721044428837228;
                                attribute Cy : Real = 10.273663187399507;
                                attribute sigma_Cy : Real = 28.23690002309109;
                                attribute Cz : Real = -61.78037249483168;
                                attribute sigma_Cz : Real = 29.057750463592832;
                                attribute Ixx : Real = 0.14959516876052975;
                                attribute sigma_Ixx : Real = 0.37074144170588635;
                                attribute Iyy : Real = 0.15794006943016725;
                                attribute sigma_Iyy : Real = 0.3723953238821935;
                                attribute Izz : Real = 0.17241936283603132;
                                attribute sigma_Izz : Real = 0.37017423652493897;
                                attribute Ixy : Real = -0.004380634094447134;
                                attribute sigma_Ixy : Real = 0.02351283871158888;
                                attribute Ixz : Real = -0.004021442459459437;
                                attribute sigma_Ixz : Real = 0.022566176940390956;
                                attribute Iyz : Real = -0.01596463004876237;
                                attribute sigma_Iyz : Real = 0.02209918015384651;
                            }
                        }
                        part <'C.1.1.3.2.3.2'> 'Subassembly 96' {
                            attribute POIconv : String = "-";
                            attribute Ipoint : Boolean = false;
                            attribute mass : Real = 1.0475631772505585;
                            attribute sigma_mass : Real = 0.40884026350990615;
                            attribute Cx : Real = -16.293326675344616;
                            attribute sigma_Cx : Real = 34.18791085761913;
                            attribute Cy : Real = 54.31336680486648;
                            attribute sigma_Cy : Real = 20.214292459491332;
                            attribute Cz : Real = -18.467857182245115;
                            attribute sigma_Cz : Real = 27.917388067863264;
                            attribute Ixx : Real = 2521.5667486038446;
                            attribute sigma_Ixx : Real = 2328.2750587483683;
                            attribute Iyy : Real = 7650.37033851565;
                            attribute sigma_Iyy : Real = 4717.804746377044;
                            attribute Izz : Real = 5264.358879054649;
                            attribute sigma_Izz : Real = 3650.001597770115;
                            attribute Ixy : Real = 590.771334488379;
                            attribute sigma_Ixy : Real = 1500.4345372054506;
                            attribute Ixz : Real = -3570.225491152778;
                            attribute sigma_Ixz : Real = 2303.2262612665027;
                            attribute Iyz : Real = 405.90267030401094;
                            attribute sigma_Iyz : Real = 1038.7012391167477;
                            part <'C.1.1.3.2.3.2.1'> 'Part 325' {
                                attribute POIconv : String = "+";
                                attribute Ipoint : Boolean = false;
                                attribute mass : Real = 0.5126135343068745;
                                attribute sigma_mass : Real = 0.28909372274994966;
                                attribute Cx : Real = -88.23857898823917;
                                attribute sigma_Cx : Real = 28.721044428837228;
                                attribute Cy : Real = 62.4933329410851;
                                attribute sigma_Cy : Real = 28.23690002309109;
                                attribute Cz : Real = -67.9025755263865;
                                attribute sigma_Cz : Real = 29.057750463592832;
                                attribute Ixx : Real = 0.48396662788528616;
                                attribute sigma_Ixx : Real = 0.37074144170588635;
                                attribute Iyy : Real = 0.5335215442545749;
                                attribute sigma_Iyy : Real = 0.3723953238821935;
                                attribute Izz : Real = 0.479101358373085;
                                attribute sigma_Izz : Real = 0.37017423652493897;
                                attribute Ixy : Real = 0.001507180322832044;
                                attribute sigma_Ixy : Real = 0.02351283871158888;
                                attribute Ixz : Real = 0.03241985306728057;
                                attribute sigma_Ixz : Real = 0.022566176940390956;
                                attribute Iyz : Real = 2.4370241434969285e-05;
                                attribute sigma_Iyz : Real = 0.02209918015384651;
                            }
                            part <'C.1.1.3.2.3.2.2'> 'Part 326' {
                                attribute POIconv : String = "+";
                                attribute Ipoint : Boolean = false;
                                attribute mass : Real = 0.534949642943684;
                                attribute sigma_mass : Real = 0.28909372274994966;
                                attribute Cx : Real = 52.64794761314988;
                                attribute sigma_Cx : Real = 28.721044428837228;
                                attribute Cy : Real = 46.47494424134493;
                                attribute sigma_Cy : Real = 28.23690002309109;
                                attribute Cz : Real = 28.902780450880527;
                                attribute sigma_Cz : Real = 29.057750463592832;
                                attribute Ixx : Real = 0.7796976661674203;
                                attribute sigma_Ixx : Real = 0.37074144170588635;
                                attribute Iyy : Real = 0.7908133779174921;
                                attribute sigma_Iyy : Real = 0.3723953238821935;
                                attribute Izz : Real = 0.8014815913535941;
                                attribute sigma_Izz : Real = 0.37017423652493897;
                                attribute Ixy : Real = -0.01290336293397582;
                                attribute sigma_Ixy : Real = 0.02351283871158888;
                                attribute Ixz : Real = 0.0008880044080371539;
                                attribute sigma_Ixz : Real = 0.022566176940390956;
                                attribute Iyz : Real = 0.017782637268793578;
                                attribute sigma_Iyz : Real = 0.02209918015384651;
                            }
                        }
                        part <'C.1.1.3.2.3.3'> 'Subassembly 97' {
                            attribute POIconv : String = "-";
                            attribute Ipoint : Boolean = false;
                            attribute mass : Real = 1.0017025800694246;
                            attribute sigma_mass : Real = 0.40884026350990615;
                            attribute Cx : Real = 44.26652662612905;
                            attribute sigma_Cx : Real = 24.51742395322753;
                            attribute Cy : Real = 79.68210651543662;
                            attribute sigma_Cy : Real = 28.67728947157582;
                            attribute Cz : Real = -81.47831428502478;
                            attribute sigma_Cz : Real = 32.97836277341605;
                            attribute Ixx : Real = 1769.5182354238898;
                            attribute sigma_Ixx : Real = 2773.3578983809966;
                            attribute Iyy : Real = 1191.0745710207168;
                            attribute sigma_Iyy : Real = 1967.8159389792177;
                            attribute Izz : Real = 635.124117754234;
                            attribute sigma_Izz : Real = 1162.874149596063;
                            attribute Ixy : Real = -129.75622894742244;
                            attribute sigma_Ixy : Real = 426.21127724785043;
                            attribute Ixz : Real = 179.64423858841198;
                            attribute sigma_Ixz : Real = 585.4837793681878;
                            attribute Iyz : Real = 839.4744586157211;
                            attribute sigma_Iyz : Real = 1329.198154303366;
                            part <'C.1.1.3.2.3.3.1'> 'Part 327' {
                                attribute POIconv : String = "-";
                                attribute Ipoint : Boolean = false;
                                attribute mass : Real = 0.829036572795827;
                                attribute sigma_mass : Real = 0.28909372274994966;
                                attribute Cx : Real = 46.66926125064492;
                                attribute sigma_Cx : Real = 28.721044428837228;
                                attribute Cy : Real = 90.90984002687037;
                                attribute sigma_Cy : Real = 28.23690002309109;
                                attribute Cz : Real = -97.02342553064227;
                                attribute sigma_Cz : Real = 29.057750463592832;
                                attribute Ixx : Real = 0.792048226688685;
                                attribute sigma_Ixx : Real = 0.37074144170588635;
                                attribute Iyy : Real = 0.9074065093255873;
                                attribute sigma_Iyy : Real = 0.3723953238821935;
                                attribute Izz : Real = 0.8705383520500798;
                                attribute sigma_Izz : Real = 0.37017423652493897;
                                attribute Ixy : Real = -0.002907549974660929;
                                attribute sigma_Ixy : Real = 0.02351283871158888;
                                attribute Ixz : Real = -0.004094885363753678;
                                attribute sigma_Ixz : Real = 0.022566176940390956;
                                attribute Iyz : Real = 0.024382285112802046;
                                attribute sigma_Iyz : Real = 0.02209918015384651;
                            }
                            part <'C.1.1.3.2.3.3.2'> 'Part 328' {
                                attribute POIconv : String = "+";
                                attribute Ipoint : Boolean = false;
                                attribute mass : Real = 0.17266600727359765;
                                attribute sigma_mass : Real = 0.28909372274994966;
                                attribute Cx : Real = 32.73006435483694;
                                attribute sigma_Cx : Real = 28.721044428837228;
                                attribute Cy : Real = 25.773396529257298;
                                attribute sigma_Cy : Real = 28.23690002309109;
                                attribute Cz : Real = -6.840196717530489;
                                attribute sigma_Cz : Real = 29.057750463592832;
                                attribute Ixx : Real = 0.18975978613601396;
                                attribute sigma_Ixx : Real = 0.37074144170588635;
                                attribute Iyy : Real = 0.16764062792869464;
                                attribute sigma_Iyy : Real = 0.3723953238821935;
                                attribute Izz : Real = 0.18417335811917462;
                                attribute sigma_Izz : Real = 0.37017423652493897;
                                attribute Ixy : Real = 0.004465007722107403;
                                attribute sigma_Ixy : Real = 0.02351283871158888;
                                attribute Ixz : Real = -0.007410885440029033;
                                attribute sigma_Ixz : Real = 0.022566176940390956;
                                attribute Iyz : Real = -0.006391626421596712;
                                attribute sigma_Iyz : Real = 0.02209918015384651;
                            }
                        }
                    }
                    part <'C.1.1.3.2.4'> 'Assembly 27' {
                        attribute POIconv : String = "-";
                        attribute Ipoint : Boolean = false;
                        attribute mass : Real = 6.028194033676758;
                        attribute sigma_mass : Real = 0.9141946211470768;
                        attribute Cx : Real = -0.28811582030875765;
                        attribute sigma_Cx : Real = 13.918478870620627;
                        attribute Cy : Real = 14.881007813744745;
                        attribute sigma_Cy : Real = 12.737960681671138;
                        attribute Cz : Real = 21.126813351754226;
                        attribute sigma_Cz : Real = 14.264651444936886;
                        attribute Ixx : Real = 25250.536644563865;
                        attribute sigma_Ixx : Real = 10683.228033042642;
                        attribute Iyy : Real = 37022.667989401765;
                        attribute sigma_Iyy : Real = 12970.80254951201;
                        attribute Izz : Real = 26978.504305899663;
                        attribute sigma_Izz : Real = 11292.921375837657;
                        attribute Ixy : Real = -4628.661509110165;
                        attribute sigma_Ixy : Real = 5231.306397429213;
                        attribute Ixz : Real = -311.67511286700164;
                        attribute sigma_Ixz : Real = 6090.584908188319;
                        attribute Iyz : Real = 5993.478810475741;
                        attribute sigma_Iyz : Real = 5005.56482402894;
                        part <'C.1.1.3.2.4.1'> 'Subassembly 98' {
                            attribute POIconv : String = "-";
                            attribute Ipoint : Boolean = false;
                            attribute mass : Real = 1.8293687644712628;
                            attribute sigma_mass : Real = 0.5007250159521434;
                            attribute Cx : Real = -10.350144871444712;
                            attribute sigma_Cx : Real = 24.76276413310605;
                            attribute Cy : Real = 28.528443448927813;
                            attribute sigma_Cy : Real = 21.711202702602304;
                            attribute Cz : Real = -10.197567510946783;
                            attribute sigma_Cz : Real = 29.77247560402662;
                            attribute Ixx : Real = 11327.003430988043;
                            attribute sigma_Ixx : Real = 7018.523554947837;
                            attribute Iyy : Real = 11432.178352224155;
                            attribute sigma_Iyy : Real = 7979.050626852278;
                            attribute Izz : Real = 2906.413011911943;
                            attribute sigma_Izz : Real = 4292.275842823146;
                            attribute Ixy : Real = 1215.5492771325885;
                            attribute sigma_Ixy : Real = 1964.9140795018568;
                            attribute Ixz : Real = -2632.0285635278888;
                            attribute sigma_Ixz : Real = 3835.238996910599;
                            attribute Iyz : Real = 3616.822497105072;
                            attribute sigma_Iyz : Real = 3193.85039298304;
                            part <'C.1.1.3.2.4.1.1'> 'Part 329' {
                                attribute POIconv : String = "-";
                                attribute Ipoint : Boolean = false;
                                attribute mass : Real = 0.1287167886684183;
                                attribute sigma_mass : Real = 0.28909372274994966;
                                attribute Cx : Real = 87.03090269118547;
                                attribute sigma_Cx : Real = 28.721044428837228;
                                attribute Cy : Real = -30.540409218519926;
                                attribute sigma_Cy : Real = 28.23690002309109;
                                attribute Cz : Real = 90.15979957766831;
                                attribute sigma_Cz : Real = 29.057750463592832;
                                attribute Ixx : Real = 0.16228324661940166;
                                attribute sigma_Ixx : Real = 0.37074144170588635;
                                attribute Iyy : Real = 0.18592483896238873;
                                attribute sigma_Iyy : Real = 0.3723953238821935;
                                attribute Izz : Real = 0.169379665314911;
                                attribute sigma_Izz : Real = 0.37017423652493897;
                                attribute Ixy : Real = -0.005206167910981763;
                                attribute sigma_Ixy : Real = 0.02351283871158888;
                                attribute Ixz : Real = -0.0003557462758003533;
                                attribute sigma_Ixz : Real = 0.022566176940390956;
                                attribute Iyz : Real = -0.012137712710591424;
                                attribute sigma_Iyz : Real = 0.02209918015384651;
                            }
                            part <'C.1.1.3.2.4.1.2'> 'Part 330' {
                                attribute POIconv : String = "-";
                                attribute Ipoint : Boolean = false;
                                attribute mass : Real = 0.7194973043771461;
                                attribute sigma_mass : Real = 0.28909372274994966;
                                attribute Cx : Real = -5.321806250140071;
                                attribute sigma_Cx : Real = 28.721044428837228;
                                attribute Cy : Real = 5.8911309111863375;
                                attribute sigma_Cy : Real = 28.23690002309109;
                                attribute Cz : Real = 64.91381684318185;
                                attribute sigma_Cz : Real = 29.057750463592832;
                                attribute Ixx : Real = 0.7433649994239266;
                                attribute sigma_Ixx : Real = 0.37074144170588635;
                                attribute Iyy : Real = 0.7614583436374497;
                                attribute sigma_Iyy : Real = 0.3723953238821935;
                                attribute Izz : Real = 0.7599770598861778;
                                attribute sigma_Izz : Real = 0.37017423652493897;
                                attribute Ixy : Real = -0.0073631579731272675;
                                attribute sigma_Ixy : Real = 0.02351283871158888;
                                attribute Ixz : Real = 0.01065898338305345;
                                attribute sigma_Ixz : Real = 0.022566176940390956;
                                attribute Iyz : Real = 0.010820393022586878;
                                attribute sigma_Iyz : Real = 0.02209918015384651;
                            }
                            part <'C.1.1.3.2.4.1.3'> 'Part 331' {
                                attribute POIconv : String = "+";
                                attribute Ipoint : Boolean = false;
                                attribute mass : Real = 0.9811546714256983;
                                attribute sigma_mass : Real = 0.28909372274994966;
                                attribute Cx : Real = -26.812841603532434;
                                attribute sigma_Cx : Real = 28.721044428837228;
                                attribute Cy : Real = 52.877956395968795;
                                attribute sigma_Cy : Real = 28.23690002309109;
                                attribute Cz : Real = -78.44380689784884;
                                attribute sigma_Cz : Real = 29.057750463592832;
                                attribute Ixx : Real = 1.1952775255256611;
                                attribute sigma_Ixx : Real = 0.37074144170588635;
                                attribute Iyy : Real = 1.1333585747959691;
                                attribute sigma_Iyy : Real = 0.3723953238821935;
                                attribute Izz : Real = 1.2088887158634742;
                                attribute sigma_Izz : Real = 0.37017423652493897;
                                attribute Ixy : Real = 0.04448588940602053;
                                attribute sigma_Ixy : Real = 0.02351283871158888;
                                attribute Ixz : Real = 0.014076505407049527;
                                attribute sigma_Ixz : Real = 0.022566176940390956;
                                attribute Iyz : Real = 0.030402675473276016;
                                attribute sigma_Iyz : Real = 0.02209918015384651;
                            }
                        }
                        part <'C.1.1.3.2.4.2'> 'Subassembly 99' {
                            attribute POIconv : String = "-";
                            attribute Ipoint : Boolean = false;
                            attribute mass : Real = 1.115462921152124;
                            attribute sigma_mass : Real = 0.5007250159521434;
                            attribute Cx : Real = 18.062270850627925;
                            attribute sigma_Cx : Real = 31.130147468939633;
                            attribute Cy : Real = 20.54678017939325;
                            attribute sigma_Cy : Real = 37.00521914071327;
                            attribute Cz : Real = 76.37912888641077;
                            attribute sigma_Cz : Real = 28.255470284560634;
                            attribute Ixx : Real = 1810.0222254250723;
                            attribute sigma_Ixx : Real = 4372.955199802982;
                            attribute Iyy : Real = 1229.714739765951;
                            attribute sigma_Iyy : Real = 2590.8411862381145;
                            attribute Izz : Real = 2109.37716669385;
                            attribute sigma_Izz : Real = 5233.347224834797;
                            attribute Ixy : Real = 864.1020592994934;
                            attribute sigma_Ixy : Real = 2440.2991988773897;
                            attribute Ixz : Real = 581.2519956406895;
                            attribute sigma_Ixz : Real = 1219.3581895375628;
                            attribute Iyz : Real = -567.5331819407473;
                            attribute sigma_Iyz : Real = 1694.955459517341;
                            part <'C.1.1.3.2.4.2.1'> 'Part 332' {
                                attribute POIconv : String = "+";
                                attribute Ipoint : Boolean = false;
                                attribute mass : Real = 0.8908846303960308;
                                attribute sigma_mass : Real = 0.28909372274994966;
                                attribute Cx : Real = 6.145137874409556;
                                attribute sigma_Cx : Real = 28.721044428837228;
                                attribute Cy : Real = 30.200060736387968;
                                attribute sigma_Cy : Real = 28.23690002309109;
                                attribute Cz : Real = 86.38933976180851;
                                attribute sigma_Cz : Real = 29.057750463592832;
                                attribute Ixx : Real = 1.1732807924076296;
                                attribute sigma_Ixx : Real = 0.37074144170588635;
                                attribute Iyy : Real = 1.2262073962193647;
                                attribute sigma_Iyy : Real = 0.3723953238821935;
                                attribute Izz : Real = 1.1639888072078595;
                                attribute sigma_Izz : Real = 0.37017423652493897;
                                attribute Ixy : Real = 0.08138156012891873;
                                attribute sigma_Ixy : Real = 0.02351283871158888;
                                attribute Ixz : Real = -0.06547237091048538;
                                attribute sigma_Ixz : Real = 0.022566176940390956;
                                attribute Iyz : Real = 0.016495638048970227;
                                attribute sigma_Iyz : Real = 0.02209918015384651;
                            }
                            part <'C.1.1.3.2.4.2.2'> 'Part 333' {
                                attribute POIconv : String = "-";
                                attribute Ipoint : Boolean = false;
                                attribute mass : Real = 0.10032512529427186;
                                attribute sigma_mass : Real = 0.28909372274994966;
                                attribute Cx : Real = 92.65729235485196;
                                attribute sigma_Cx : Real = 28.721044428837228;
                                attribute Cy : Real = -89.4319798797369;
                                attribute sigma_Cy : Real = 28.23690002309109;
                                attribute Cz : Real = 25.90523068793118;
                                attribute sigma_Cz : Real = 29.057750463592832;
                                attribute Ixx : Real = 0.11913864855595321;
                                attribute sigma_Ixx : Real = 0.37074144170588635;
                                attribute Iyy : Real = 0.134912528368046;
                                attribute sigma_Iyy : Real = 0.3723953238821935;
                                attribute Izz : Real = 0.12936075126750263;
                                attribute sigma_Izz : Real = 0.37017423652493897;
                                attribute Ixy : Real = 0.0073934246424274975;
                                attribute sigma_Ixy : Real = 0.02351283871158888;
                                attribute Ixz : Real = -0.007472614650957768;
                                attribute sigma_Ixz : Real = 0.022566176940390956;
                                attribute Iyz : Real = -0.006519047686285644;
                                attribute sigma_Iyz : Real = 0.02209918015384651;
                            }
                            part <'C.1.1.3.2.4.2.3'> 'Part 334' {
                                attribute POIconv : String = "-";
                                attribute Ipoint : Boolean = false;
                                attribute mass : Real = 0.12425316546182148;
                                attribute sigma_mass : Real = 0.28909372274994966;
                                attribute Cx : Real = 43.277207762002945;
                                attribute sigma_Cx : Real = 28.721044428837228;
                                attribute Cy : Real = 40.1331914588809;
                                attribute sigma_Cy : Real = 28.23690002309109;
                                attribute Cz : Real = 45.36066073924303;
                                attribute sigma_Cz : Real = 29.057750463592832;
                                attribute Ixx : Real = 0.16995944008708636;
                                attribute sigma_Ixx : Real = 0.37074144170588635;
                                attribute Iyy : Real = 0.1719286949193182;
                                attribute sigma_Iyy : Real = 0.3723953238821935;
                                attribute Izz : Real = 0.1619421745124618;
                                attribute sigma_Izz : Real = 0.37017423652493897;
                                attribute Ixy : Real = 3.326645094867894e-05;
                                attribute sigma_Ixy : Real = 0.02351283871158888;
                                attribute Ixz : Real = 0.0014322597037123236;
                                attribute sigma_Ixz : Real = 0.022566176940390956;
                                attribute Iyz : Real = -0.001125542427615782;
                                attribute sigma_Iyz : Real = 0.02209918015384651;
                            }
                        }
                        part <'C.1.1.3.2.4.3'> 'Subassembly 100' {
                            attribute POIconv : String = "-";
                            attribute Ipoint : Boolean = false;
                            attribute mass : Real = 1.2583704793360084;
                            attribute sigma_mass : Real = 0.40884026350990615;
                            attribute Cx : Real = -26.005772884248312;
                            attribute sigma_Cx : Real = 21.40413480208315;
                            attribute Cy : Real = -25.40433454352479;
                            attribute sigma_Cy : Real = 22.186351526783163;
                            attribute Cz : Real = 34.3006310786928;
                            attribute sigma_Cz : Real = 24.128041355240182;
                            attribute Ixx : Real = 1836.0232470038945;
                            attribute sigma_Ixx : Real = 2036.1406291740225;
                            attribute Iyy : Real = 1343.8617410976508;
                            attribute sigma_Iyy : Real = 1717.120235901905;
                            attribute Izz : Real = 697.8482316535828;
                            attribute sigma_Izz : Real = 1173.2125025901478;
                            attribute Ixy : Real = -246.12817485416355;
                            attribute sigma_Ixy : Real = 583.3034224685221;
                            attribute Ixz : Real = 355.5840295313873;
                            attribute sigma_Ixz : Real = 813.6442177740158;
                            attribute Iyz : Real = 858.4001196444294;
                            attribute sigma_Iyz : Real = 999.4566304969728;
                            part <'C.1.1.3.2.4.3.1'> 'Part 335' {
                                attribute POIconv : String = "-";
                                attribute Ipoint : Boolean = false;
                                attribute mass : Real = 0.8138346412456594;
                                attribute sigma_mass : Real = 0.28909372274994966;
                                attribute Cx : Real = -19.35315211303532;
                                attribute sigma_Cx : Real = 28.721044428837228;
                                attribute Cy : Real = -9.34449820779264;
                                attribute sigma_Cy : Real = 28.23690002309109;
                                attribute Cz : Real = 11.100184358656406;
                                attribute sigma_Cz : Real = 29.057750463592832;
                                attribute Ixx : Real = 1.254307671626655;
                                attribute sigma_Ixx : Real = 0.37074144170588635;
                                attribute Iyy : Real = 1.2892499073621049;
                                attribute sigma_Iyy : Real = 0.3723953238821935;
                                attribute Izz : Real = 1.2123385561143551;
                                attribute sigma_Izz : Real = 0.37017423652493897;
                                attribute Ixy : Real = 0.00475683828348402;
                                attribute sigma_Ixy : Real = 0.02351283871158888;
                                attribute Ixz : Real = -0.005411595769007989;
                                attribute sigma_Ixz : Real = 0.022566176940390956;
                                attribute Iyz : Real = 0.030432322462455426;
                                attribute sigma_Iyz : Real = 0.02209918015384651;
                            }
                            part <'C.1.1.3.2.4.3.2'> 'Part 336' {
                                attribute POIconv : String = "-";
                                attribute Ipoint : Boolean = false;
                                attribute mass : Real = 0.44453583809034897;
                                attribute sigma_mass : Real = 0.28909372274994966;
                                attribute Cx : Real = -38.185068173334;
                                attribute sigma_Cx : Real = 28.721044428837228;
                                attribute Cy : Real = -54.80590360239148;
                                attribute sigma_Cy : Real = 28.23690002309109;
                                attribute Cz : Real = 76.77488313056529;
                                attribute sigma_Cz : Real = 29.057750463592832;
                                attribute Ixx : Real = 0.5605673530624556;
                                attribute sigma_Ixx : Real = 0.37074144170588635;
                                attribute Iyy : Real = 0.5885100498271254;
                                attribute sigma_Iyy : Real = 0.3723953238821935;
                                attribute Izz : Real = 0.4944968784011927;
                                attribute sigma_Izz : Real = 0.37017423652493897;
                                attribute Ixy : Real = 0.0011743317180756795;
                                attribute sigma_Ixy : Real = 0.02351283871158888;
                                attribute Ixz : Real = 0.017871565634935114;
                                attribute sigma_Ixz : Real = 0.022566176940390956;
                                attribute Iyz : Real = -0.0019844118834329845;
                                attribute sigma_Iyz : Real = 0.02209918015384651;
                            }
                        }
                        part <'C.1.1.3.2.4.4'> 'Subassembly 101' {
                            attribute POIconv : String = "-";
                            attribute Ipoint : Boolean = false;
                            attribute mass : Real = 1.8249918687173632;
                            attribute sigma_mass : Real = 0.40884026350990615;
                            attribute Cx : Real = 16.314876609110016;
                            attribute sigma_Cx : Real = 28.94262548096925;
                            attribute Cy : Real = 25.515430051618807;
                            attribute sigma_Cy : Real = 21.154501918699797;
                            attribute Cz : Real = 9.671634259638058;
                            attribute sigma_Cz : Real = 20.86714247714973;
                            attribute Ixx : Real = 1994.165055979371;
                            attribute sigma_Ixx : Real = 2454.2313199726377;
                            attribute Iyy : Real = 15462.542651982916;
                            attribute sigma_Iyy : Real = 7679.306296005431;
                            attribute Izz : Real = 16743.53301909526;
                            attribute sigma_Izz : Real = 8050.517298781979;
                            attribute Ixy : Real = -4971.467106370172;
                            attribute sigma_Ixy : Real = 3666.6958746206096;
                            attribute Ixz : Real = 2317.648497191415;
                            attribute sigma_Ixz : Real = 3478.2844581504796;
                            attribute Iyz : Real = 762.7801442125196;
                            attribute sigma_Iyz : Real = 1240.3398954178153;
                            part <'C.1.1.3.2.4.4.1'> 'Part 337' {
                                attribute POIconv : String = "+";
                                attribute Ipoint : Boolean = false;
                                attribute mass : Real = 0.9935060153647791;
                                attribute sigma_mass : Real = 0.28909372274994966;
                                attribute Cx : Real = 99.54300043173134;
                                attribute sigma_Cx : Real = 28.721044428837228;
                                attribute Cy : Real = 52.90783024393022;
                                attribute sigma_Cy : Real = 28.23690002309109;
                                attribute Cz : Real = -3.098144009709358;
                                attribute sigma_Cz : Real = 29.057750463592832;
                                attribute Ixx : Real = 1.2726673316890742;
                                attribute sigma_Ixx : Real = 0.37074144170588635;
                                attribute Iyy : Real = 1.104507471678157;
                                attribute sigma_Iyy : Real = 0.3723953238821935;
                                attribute Izz : Real = 1.2862151596833427;
                                attribute sigma_Izz : Real = 0.37017423652493897;
                                attribute Ixy : Real = 0.113966584528572;
                                attribute sigma_Ixy : Real = 0.02351283871158888;
                                attribute Ixz : Real = -0.06579783463571051;
                                attribute sigma_Ixz : Real = 0.022566176940390956;
                                attribute Iyz : Real = 0.04940191283725343;
                                attribute sigma_Iyz : Real = 0.02209918015384651;
                            }
                            part <'C.1.1.3.2.4.4.2'> 'Part 338' {
                                attribute POIconv : String = "+";
                                attribute Ipoint : Boolean = false;
                                attribute mass : Real = 0.831485853352584;
                                attribute sigma_mass : Real = 0.28909372274994966;
                                attribute Cx : Real = -83.13076198101044;
                                attribute sigma_Cx : Real = 28.721044428837228;
                                attribute Cy : Real = -7.214548764750361;
                                attribute sigma_Cy : Real = 28.23690002309109;
                                attribute Cz : Real = 24.929682817310095;
                                attribute sigma_Cz : Real = 29.057750463592832;
                                attribute Ixx : Real = 1.1061638413519386;
                                attribute sigma_Ixx : Real = 0.37074144170588635;
                                attribute Iyy : Real = 0.9906589384755864;
                                attribute sigma_Iyy : Real = 0.3723953238821935;
                                attribute Izz : Real = 1.1828486285053241;
                                attribute sigma_Izz : Real = 0.37017423652493897;
                                attribute Ixy : Real = -0.024591749429249916;
                                attribute sigma_Ixy : Real = 0.02351283871158888;
                                attribute Ixz : Real = -0.027798027141805084;
                                attribute sigma_Ixz : Real = 0.022566176940390956;
                                attribute Iyz : Real = -0.06585028412634386;
                                attribute sigma_Iyz : Real = 0.02209918015384651;
                            }
                        }
                    }
                }
                part <'C.1.1.3.3'> 'Subsystem 8' {
                    attribute POIconv : String = "-";
                    attribute Ipoint : Boolean = false;
                    attribute mass : Real = 31.042946416208988;
                    attribute sigma_mass : Real = 2.201672198793144;
                    attribute Cx : Real = 2.6631761926013446;
                    attribute sigma_Cx : Real = 5.982954469352481;
                    attribute Cy : Real = -0.5989699466023461;
                    attribute sigma_Cy : Real = 5.683461239800526;
                    attribute Cz : Real = 1.6776948831031437;
                    attribute sigma_Cz : Real = 5.93147440424244;
                    attribute Ixx : Real = 178269.57653273578;
                    attribute sigma_Ixx : Real = 25732.24876156434;
                    attribute Iyy : Real = 195264.21905900078;
                    attribute sigma_Iyy : Real = 26881.969452066296;
                    attribute Izz : Real = 190609.8752521568;
                    attribute sigma_Izz : Real = 26661.0456067713;
                    attribute Ixy : Real = -16222.681624074843;
                    attribute sigma_Ixy : Real = 12727.866996903902;
                    attribute Ixz : Real = 1733.1352225143228;
                    attribute sigma_Ixz : Real = 12605.473374463107;
                    attribute Iyz : Real = 1391.3442534966498;
                    attribute sigma_Iyz : Real = 12059.93956864893;
                    part <'C.1.1.3.3.1'> 'Assembly 28' {
                        attribute POIconv : String = "-";
                        attribute Ipoint : Boolean = false;
                        attribute mass : Real = 7.143061533371452;
                        attribute sigma_mass : Real = 1.0014500319042867;
                        attribute Cx : Real = 22.684410166810377;
                        attribute sigma_Cx : Real = 10.704580090468529;
                        attribute Cy : Real = -2.8694936288777666;
                        attribute sigma_Cy : Real = 12.189038789089148;
                        attribute Cz : Real = -13.74745489953297;
                        attribute sigma_Cz : Real = 12.720731291319044;
                        attribute Ixx : Real = 46700.13160725338;
                        attribute sigma_Ixx : Real = 13779.85885389026;
                        attribute Iyy : Real = 32546.26560614103;
                        attribute sigma_Iyy : Real = 11075.949466820128;
                        attribute Izz : Real = 36610.288177552626;
                        attribute sigma_Izz : Real = 10691.519974362927;
                        attribute Ixy : Real = -9674.370920117615;
                        attribute sigma_Ixy : Real = 5002.574885378281;
                        attribute Ixz : Real = -4296.275202901931;
                        attribute sigma_Ixz : Real = 4836.433763504707;
                        attribute Iyz : Real = -306.1448909359543;
                        attribute sigma_Iyz : Real = 6661.992168669573;
                        part <'C.1.1.3.3.1.1'> 'Subassembly 102' {
                            attribute POIconv : String = "-";
                            attribute Ipoint : Boolean = false;
                            attribute mass : Real = 1.1567824624860659;
                            attribute sigma_mass : Real = 0.40884026350990615;
                            attribute Cx : Real = -14.207988396287224;
                            attribute sigma_Cx : Real = 24.801446350828922;
                            attribute Cy : Real = -66.79698315057487;
                            attribute sigma_Cy : Real = 26.480087159501046;
                            attribute Cz : Real = -55.82527213110062;
                            attribute sigma_Cz : Real = 40.26916321513275;
                            attribute Ixx : Real = 3471.6992426069673;
                            attribute sigma_Ixx : Real = 5271.281021867711;
                            attribute Iyy : Real = 3134.7332843702525;
                            attribute sigma_Iyy : Real = 4792.82727380931;
                            attribute Izz : Real = 338.4162465896842;
                            attribute sigma_Izz : Real = 738.7091635379448;
                            attribute Ixy : Real = 3.0176719073096225;
                            attribute sigma_Ixy : Real = 285.97089684166025;
                            attribute Ixz : Real = 9.038495073468399;
                            attribute sigma_Ixz : Real = 872.1150706255747;
                            attribute Iyz : Real = -1027.539092792421;
                            attribute sigma_Iyz : Real = 1718.616962818622;
                            part <'C.1.1.3.3.1.1.1'> 'Part 339' {
                                attribute POIconv : String = "+";
                                attribute Ipoint : Boolean = false;
                                attribute mass : Real = 0.17296256762440315;
                                attribute sigma_mass : Real = 0.28909372274994966;
                                attribute Cx : Real = -14.564425311982632;
                                attribute sigma_Cx : Real = 28.721044428837228;
                                attribute Cy : Real = -26.097243139520288;
                                attribute sigma_Cy : Real = 28.23690002309109;
                                attribute Cz : Real = 68.29932532273233;
                                attribute sigma_Cz : Real = 29.057750463592832;
                                attribute Ixx : Real = 0.23515190848664183;
                                attribute sigma_Ixx : Real = 0.37074144170588635;
                                attribute Iyy : Real = 0.24636589810555753;
                                attribute sigma_Iyy : Real = 0.3723953238821935;
                                attribute Izz : Real = 0.23377505428179532;
                                attribute sigma_Izz : Real = 0.37017423652493897;
                                attribute Ixy : Real = 0.0009190094128724061;
                                attribute sigma_Ixy : Real = 0.02351283871158888;
                                attribute Ixz : Real = -0.010515800318927333;
                                attribute sigma_Ixz : Real = 0.022566176940390956;
                                attribute Iyz : Real = 0.002593748427671645;
                                attribute sigma_Iyz : Real = 0.02209918015384651;
                            }
                            part <'C.1.1.3.3.1.1.2'> 'Part 340' {
                                attribute POIconv : String = "+";
                                attribute Ipoint : Boolean = false;
                                attribute mass : Real = 0.9838198948616628;
                                attribute sigma_mass : Real = 0.28909372274994966;
                                attribute Cx : Real = -14.145324239507318;
                                attribute sigma_Cx : Real = 28.721044428837228;
                                attribute Cy : Real = -73.95228827372193;
                                attribute sigma_Cy : Real = 28.23690002309109;
                                attribute Cz : Real = -77.64726332388818;
                                attribute sigma_Cz : Real = 29.057750463592832;
                                attribute Ixx : Real = 1.272949086677975;
                                attribute sigma_Ixx : Real = 0.37074144170588635;
                                attribute Iyy : Real = 1.1470384580883433;
                                attribute sigma_Iyy : Real = 0.3723953238821935;
                                attribute Izz : Real = 1.2795345707875208;
                                attribute sigma_Izz : Real = 0.37017423652493897;
                                attribute Ixy : Real = -0.06831570111704816;
                                attribute sigma_Ixy : Real = 0.02351283871158888;
                                attribute Ixz : Real = -0.030336452443956587;
                                attribute sigma_Ixz : Real = 0.022566176940390956;
                                attribute Iyz : Real = 0.1408859925617021;
                                attribute sigma_Iyz : Real = 0.02209918015384651;
                            }
                        }
                        part <'C.1.1.3.3.1.2'> 'Subassembly 103' {
                            attribute POIconv : String = "-";
                            attribute Ipoint : Boolean = false;
                            attribute mass : Real = 1.7167463173738218;
                            attribute sigma_mass : Real = 0.5007250159521434;
                            attribute Cx : Real = 34.36209499349572;
                            attribute sigma_Cx : Real = 18.674345382798712;
                            attribute Cy : Real = 4.7440558831696675;
                            attribute sigma_Cy : Real = 26.1444635616413;
                            attribute Cz : Real = -7.6300237641101765;
                            attribute sigma_Cz : Real = 25.879360760142912;
                            attribute Ixx : Real = 15076.555652039657;
                            attribute sigma_Ixx : Real = 7667.058589804854;
                            attribute Iyy : Real = 8601.626803783229;
                            attribute sigma_Iyy : Real = 4982.200643342606;
                            attribute Izz : Real = 9333.38564812182;
                            attribute sigma_Izz : Real = 5175.8112400723785;
                            attribute Ixy : Real = -20.663627980875162;
                            attribute sigma_Ixy : Real = 2202.813170892056;
                            attribute Ixz : Real = -570.2896055232918;
                            attribute sigma_Ixz : Real = 2131.9026150754967;
                            attribute Iyz : Real = 7399.417889698618;
                            attribute sigma_Iyz : Real = 3820.3354695259545;
                            part <'C.1.1.3.3.1.2.1'> 'Part 341' {
                                attribute POIconv : String = "-";
                                attribute Ipoint : Boolean = false;
                                attribute mass : Real = 0.5552727924224455;
                                attribute sigma_mass : Real = 0.28909372274994966;
                                attribute Cx : Real = 45.22345131263137;
                                attribute sigma_Cx : Real = 28.721044428837228;
                                attribute Cy : Real = 99.64423952624202;
                                attribute sigma_Cy : Real = 28.23690002309109;
                                attribute Cz : Real = -92.10035386495292;
                                attribute sigma_Cz : Real = 29.057750463592832;
                                attribute Ixx : Real = 0.6266058186470491;
                                attribute sigma_Ixx : Real = 0.37074144170588635;
                                attribute Iyy : Real = 0.6183279141637241;
                                attribute sigma_Iyy : Real = 0.3723953238821935;
                                attribute Izz : Real = 0.6721429327674253;
                                attribute sigma_Izz : Real = 0.37017423652493897;
                                attribute Ixy : Real = 0.014988545156790763;
                                attribute sigma_Ixy : Real = 0.02351283871158888;
                                attribute Ixz : Real = -0.042082998472465646;
                                attribute sigma_Ixz : Real = 0.022566176940390956;
                                attribute Iyz : Real = -0.0326383529731137;
                                attribute sigma_Iyz : Real = 0.02209918015384651;
                            }
                            part <'C.1.1.3.3.1.2.2'> 'Part 342' {
                                attribute POIconv : String = "+";
                                attribute Ipoint : Boolean = false;
                                attribute mass : Real = 0.6642862837191206;
                                attribute sigma_mass : Real = 0.28909372274994966;
                                attribute Cx : Real = -0.12150341644883156;
                                attribute sigma_Cx : Real = 28.721044428837228;
                                attribute Cy : Real = -22.469228319823742;
                                attribute sigma_Cy : Real = 28.23690002309109;
                                attribute Cz : Real = 3.6420139484107494;
                                attribute sigma_Cz : Real = 29.057750463592832;
                                attribute Ixx : Real = 0.788842049384512;
                                attribute sigma_Ixx : Real = 0.37074144170588635;
                                attribute Iyy : Real = 0.8668521507371356;
                                attribute sigma_Iyy : Real = 0.3723953238821935;
                                attribute Izz : Real = 0.7379916356314895;
                                attribute sigma_Izz : Real = 0.37017423652493897;
                                attribute Ixy : Real = -0.010146073839353233;
                                attribute sigma_Ixy : Real = 0.02351283871158888;
                                attribute Ixz : Real = -0.000711125070657171;
                                attribute sigma_Ixz : Real = 0.022566176940390956;
                                attribute Iyz : Real = 0.0012417534232498;
                                attribute sigma_Iyz : Real = 0.02209918015384651;
                            }
                            part <'C.1.1.3.3.1.2.3'> 'Part 343' {
                                attribute POIconv : String = "-";
                                attribute Ipoint : Boolean = false;
                                attribute mass : Real = 0.4971872412322555;
                                attribute sigma_mass : Real = 0.28909372274994966;
                                attribute Cx : Real = 68.30497281625867;
                                attribute sigma_Cx : Real = 28.721044428837228;
                                attribute Cy : Real = -64.88379389047623;
                                attribute sigma_Cy : Real = 28.23690002309109;
                                attribute Cz : Real = 71.64839040488005;
                                attribute sigma_Cz : Real = 29.057750463592832;
                                attribute Ixx : Real = 0.7390924411943168;
                                attribute sigma_Ixx : Real = 0.37074144170588635;
                                attribute Iyy : Real = 0.6412912874456442;
                                attribute sigma_Iyy : Real = 0.3723953238821935;
                                attribute Izz : Real = 0.5967274879637402;
                                attribute sigma_Izz : Real = 0.37017423652493897;
                                attribute Ixy : Real = -0.007283921236905591;
                                attribute sigma_Ixy : Real = 0.02351283871158888;
                                attribute Ixz : Real = 0.0013296151538236527;
                                attribute sigma_Ixz : Real = 0.022566176940390956;
                                attribute Iyz : Real = 0.010705195410016874;
                                attribute sigma_Iyz : Real = 0.02209918015384651;
                            }
                        }
                        part <'C.1.1.3.3.1.3'> 'Subassembly 104' {
                            attribute POIconv : String = "-";
                            attribute Ipoint : Boolean = false;
                            attribute mass : Real = 3.6786215612986126;
                            attribute sigma_mass : Real = 0.6464332159373649;
                            attribute Cx : Real = 19.558963077032693;
                            attribute sigma_Cx : Real = 14.737191210361171;
                            attribute Cy : Real = 15.468745444627851;
                            attribute sigma_Cy : Real = 16.11173776982775;
                            attribute Cz : Real = -1.466877440554488;
                            attribute sigma_Cz : Real = 15.178955008988757;
                            attribute Ixx : Real = 18589.972338287367;
                            attribute sigma_Ixx : Real = 7501.4043154813135;
                            attribute Iyy : Real = 13613.455248849583;
                            attribute sigma_Iyy : Real = 6534.756753334017;
                            attribute Izz : Real = 16851.23822724458;
                            attribute sigma_Izz : Real = 7131.567846578453;
                            attribute Ixy : Real = -7303.392034961167;
                            attribute sigma_Ixy : Real = 3488.441864317413;
                            attribute Ixz : Real = -2199.7087868203353;
                            attribute sigma_Ixz : Real = 3184.9985371899984;
                            attribute Iyz : Real = -2352.1062849296964;
                            attribute sigma_Iyz : Real = 3583.066489636267;
                            part <'C.1.1.3.3.1.3.1'> 'Part 344' {
                                attribute POIconv : String = "+";
                                attribute Ipoint : Boolean = false;
                                attribute mass : Real = 0.7082670163041912;
                                attribute sigma_mass : Real = 0.28909372274994966;
                                attribute Cx : Real = -7.923644687980413;
                                attribute sigma_Cx : Real = 28.721044428837228;
                                attribute Cy : Real = -49.34416888281703;
                                attribute sigma_Cy : Real = 28.23690002309109;
                                attribute Cz : Real = -5.094885872676969;
                                attribute sigma_Cz : Real = 29.057750463592832;
                                attribute Ixx : Real = 0.8310048517949346;
                                attribute sigma_Ixx : Real = 0.37074144170588635;
                                attribute Iyy : Real = 0.8171105974087458;
                                attribute sigma_Iyy : Real = 0.3723953238821935;
                                attribute Izz : Real = 0.9152684446968447;
                                attribute sigma_Izz : Real = 0.37017423652493897;
                                attribute Ixy : Real = -0.006635538494853262;
                                attribute sigma_Ixy : Real = 0.02351283871158888;
                                attribute Ixz : Real = 0.004183277509689184;
                                attribute sigma_Ixz : Real = 0.022566176940390956;
                                attribute Iyz : Real = -0.04061732463389712;
                                attribute sigma_Iyz : Real = 0.02209918015384651;
                            }
                            part <'C.1.1.3.3.1.3.2'> 'Part 345' {
                                attribute POIconv : String = "+";
                                attribute Ipoint : Boolean = false;
                                attribute mass : Real = 0.7039202037192881;
                                attribute sigma_mass : Real = 0.28909372274994966;
                                attribute Cx : Real = 77.4934052489698;
                                attribute sigma_Cx : Real = 28.721044428837228;
                                attribute Cy : Real = 77.67855464480817;
                                attribute sigma_Cy : Real = 28.23690002309109;
                                attribute Cz : Real = -36.64542925544083;
                                attribute sigma_Cz : Real = 29.057750463592832;
                                attribute Ixx : Real = 0.8978087242555083;
                                attribute sigma_Ixx : Real = 0.37074144170588635;
                                attribute Iyy : Real = 0.9427405973278487;
                                attribute sigma_Iyy : Real = 0.3723953238821935;
                                attribute Izz : Real = 0.9582910226102995;
                                attribute sigma_Izz : Real = 0.37017423652493897;
                                attribute Ixy : Real = 0.047254869640635154;
                                attribute sigma_Ixy : Real = 0.02351283871158888;
                                attribute Ixz : Real = -0.003307730206997259;
                                attribute sigma_Ixz : Real = 0.022566176940390956;
                                attribute Iyz : Real = -0.002696946277858248;
                                attribute sigma_Iyz : Real = 0.02209918015384651;
                            }
                            part <'C.1.1.3.3.1.3.3'> 'Part 346' {
                                attribute POIconv : String = "+";
                                attribute Ipoint : Boolean = false;
                                attribute mass : Real = 0.5958952019563876;
                                attribute sigma_mass : Real = 0.28909372274994966;
                                attribute Cx : Real = 44.66969342902303;
                                attribute sigma_Cx : Real = 28.721044428837228;
                                attribute Cy : Real = 85.3391538374126;
                                attribute sigma_Cy : Real = 28.23690002309109;
                                attribute Cz : Real = 24.265004228800535;
                                attribute sigma_Cz : Real = 29.057750463592832;
                                attribute Ixx : Real = 0.7713652964993101;
                                attribute sigma_Ixx : Real = 0.37074144170588635;
                                attribute Iyy : Real = 0.6968887104444396;
                                attribute sigma_Iyy : Real = 0.3723953238821935;
                                attribute Izz : Real = 0.7985076519388641;
                                attribute sigma_Izz : Real = 0.37017423652493897;
                                attribute Ixy : Real = -0.017454868630698374;
                                attribute sigma_Ixy : Real = 0.02351283871158888;
                                attribute Ixz : Real = 0.09199885539149083;
                                attribute sigma_Ixz : Real = 0.022566176940390956;
                                attribute Iyz : Real = 0.02230476182137807;
                                attribute sigma_Iyz : Real = 0.02209918015384651;
                            }
                            part <'C.1.1.3.3.1.3.4'> 'Part 347' {
                                attribute POIconv : String = "+";
                                attribute Ipoint : Boolean = false;
                                attribute mass : Real = 0.8632667303956114;
                                attribute sigma_mass : Real = 0.28909372274994966;
                                attribute Cx : Real = 30.22816083393991;
                                attribute sigma_Cx : Real = 28.721044428837228;
                                attribute Cy : Real = 19.483605585992336;
                                attribute sigma_Cy : Real = 28.23690002309109;
                                attribute Cz : Real = 65.16060717403889;
                                attribute sigma_Cz : Real = 29.057750463592832;
                                attribute Ixx : Real = 1.310280276323307;
                                attribute sigma_Ixx : Real = 0.37074144170588635;
                                attribute Iyy : Real = 1.3092027430011184;
                                attribute sigma_Iyy : Real = 0.3723953238821935;
                                attribute Izz : Real = 1.219558064498851;
                                attribute sigma_Izz : Real = 0.37017423652493897;
                                attribute Ixy : Real = 0.004857887101179674;
                                attribute sigma_Ixy : Real = 0.02351283871158888;
                                attribute Ixz : Real = -0.002589224195977213;
                                attribute sigma_Ixz : Real = 0.022566176940390956;
                                attribute Iyz : Real = -0.001204902973619892;
                                attribute sigma_Iyz : Real = 0.02209918015384651;
                            }
                            part <'C.1.1.3.3.1.3.5'> 'Part 348' {
                                attribute POIconv : String = "-";
                                attribute Ipoint : Boolean = false;
                                attribute mass : Real = 0.8072724089231342;
                                attribute sigma_mass : Real = 0.28909372274994966;
                                attribute Cx : Real = -36.79119385778904;
                                attribute sigma_Cx : Real = 28.721044428837228;
                                attribute Cy : Real = -37.78122067451477;
                                attribute sigma_Cy : Real = 28.23690002309109;
                                attribute Cz : Real = -57.85218561068177;
                                attribute sigma_Cz : Real = 29.057750463592832;
                                attribute Ixx : Real = 0.8511451997168983;
                                attribute sigma_Ixx : Real = 0.37074144170588635;
                                attribute Iyy : Real = 0.9283186293498258;
                                attribute sigma_Iyy : Real = 0.3723953238821935;
                                attribute Izz : Real = 0.8772118188480884;
                                attribute sigma_Izz : Real = 0.37017423652493897;
                                attribute Ixy : Real = 0.024868290144069972;
                                attribute sigma_Ixy : Real = 0.02351283871158888;
                                attribute Ixz : Real = 0.038762012521037545;
                                attribute sigma_Ixz : Real = 0.022566176940390956;
                                attribute Iyz : Real = 0.05005484338480435;
                                attribute sigma_Iyz : Real = 0.02209918015384651;
                            }
                        }
                        part <'C.1.1.3.3.1.4'> 'Subassembly 105' {
                            attribute POIconv : String = "-";
                            attribute Ipoint : Boolean = false;
                            attribute mass : Real = 0.5909111922129523;
                            attribute sigma_mass : Real = 0.40884026350990615;
                            attribute Cx : Real = 80.43622590163409;
                            attribute sigma_Cx : Real = 25.859660084107695;
                            attribute Cy : Real = -14.004459553105818;
                            attribute sigma_Cy : Real = 27.08497414319622;
                            attribute Cz : Real = -25.598293838501462;
                            attribute sigma_Cz : Real = 41.55479048168975;
                            attribute Ixx : Real = 674.4378397869779;
                            attribute sigma_Ixx : Real = 1629.3879013799813;
                            attribute Iyy : Real = 630.9688754706493;
                            attribute sigma_Iyy : Real = 1532.48024291564;
                            attribute Izz : Real = 134.59988305581703;
                            attribute sigma_Izz : Real = 405.744741726193;
                            attribute Ixy : Real = -63.334083204842614;
                            attribute sigma_Ixy : Real = 197.4887794678707;
                            attribute Ixz : Real = -162.5602153153214;
                            attribute sigma_Ixz : Real = 471.5835949819194;
                            attribute Iyz : Real = -227.87960557796742;
                            attribute sigma_Iyz : Real = 594.1217691640999;
                            part <'C.1.1.3.3.1.4.1'> 'Part 349' {
                                attribute POIconv : String = "-";
                                attribute Ipoint : Boolean = false;
                                attribute mass : Real = 0.48454553055693395;
                                attribute sigma_mass : Real = 0.28909372274994966;
                                attribute Cx : Real = 76.3405176345259;
                                attribute sigma_Cx : Real = 28.721044428837228;
                                attribute Cy : Real = -19.746251730248332;
                                attribute sigma_Cy : Real = 28.23690002309109;
                                attribute Cz : Real = -40.3416823130101;
                                attribute sigma_Cz : Real = 29.057750463592832;
                                attribute Ixx : Real = 0.4435015590057802;
                                attribute sigma_Ixx : Real = 0.37074144170588635;
                                attribute Iyy : Real = 0.5665401783028494;
                                attribute sigma_Iyy : Real = 0.3723953238821935;
                                attribute Izz : Real = 0.5595896048069;
                                attribute sigma_Izz : Real = 0.37017423652493897;
                                attribute Ixy : Real = -0.026817732010076874;
                                attribute sigma_Ixy : Real = 0.02351283871158888;
                                attribute Ixz : Real = -0.012258042220934025;
                                attribute sigma_Ixz : Real = 0.022566176940390956;
                                attribute Iyz : Real = -0.004432627929189525;
                                attribute sigma_Iyz : Real = 0.02209918015384651;
                            }
                            part <'C.1.1.3.3.1.4.2'> 'Part 350' {
                                attribute POIconv : String = "+";
                                attribute Ipoint : Boolean = false;
                                attribute mass : Real = 0.10636566165601835;
                                attribute sigma_mass : Real = 0.28909372274994966;
                                attribute Cx : Real = 99.09410011023283;
                                attribute sigma_Cx : Real = 28.721044428837228;
                                attribute Cy : Real = 12.152099749073386;
                                attribute sigma_Cy : Real = 28.23690002309109;
                                attribute Cz : Real = 41.56476310454309;
                                attribute sigma_Cz : Real = 29.057750463592832;
                                attribute Ixx : Real = 0.12124309108592712;
                                attribute sigma_Ixx : Real = 0.37074144170588635;
                                attribute Iyy : Real = 0.11976485657182949;
                                attribute sigma_Iyy : Real = 0.3723953238821935;
                                attribute Izz : Real = 0.1381998386436675;
                                attribute sigma_Izz : Real = 0.37017423652493897;
                                attribute Ixy : Real = 0.0031644404808769274;
                                attribute sigma_Ixy : Real = 0.02351283871158888;
                                attribute Ixz : Real = -6.34067392692426e-05;
                                attribute sigma_Ixz : Real = 0.022566176940390956;
                                attribute Iyz : Real = -0.001641676819240469;
                                attribute sigma_Iyz : Real = 0.02209918015384651;
                            }
                        }
                    }
                    part <'C.1.1.3.3.2'> 'Assembly 29' {
                        attribute POIconv : String = "-";
                        attribute Ipoint : Boolean = false;
                        attribute mass : Real = 4.003333694955101;
                        attribute sigma_mass : Real = 0.8176805270198123;
                        attribute Cx : Real = 28.1322164751464;
                        attribute sigma_Cx : Real = 17.13094520174855;
                        attribute Cy : Real = -8.478240906956303;
                        attribute sigma_Cy : Real = 16.150852381145985;
                        attribute Cz : Real = 17.67775061652393;
                        attribute sigma_Cz : Real = 14.8346382792481;
                        attribute Ixx : Real = 18502.492347632575;
                        attribute sigma_Ixx : Real = 8245.037889095545;
                        attribute Iyy : Real = 26650.19853338539;
                        attribute sigma_Iyy : Real = 9683.94507932898;
                        attribute Izz : Real = 26744.739707365567;
                        attribute sigma_Izz : Real = 10114.40901375591;
                        attribute Ixy : Real = 8350.078153205754;
                        attribute sigma_Ixy : Real = 4703.605650737948;
                        attribute Ixz : Real = 909.6918895873486;
                        attribute sigma_Ixz : Real = 4476.07942714055;
                        attribute Iyz : Real = -3303.17275722163;
                        attribute sigma_Iyz : Real = 3895.667460827672;
                        part <'C.1.1.3.3.2.1'> 'Subassembly 106' {
                            attribute POIconv : String = "-";
                            attribute Ipoint : Boolean = false;
                            attribute mass : Real = 2.9940569970475046;
                            attribute sigma_mass : Real = 0.6464332159373649;
                            attribute Cx : Real = 30.059899586358846;
                            attribute sigma_Cx : Real = 20.717006971082494;
                            attribute Cy : Real = -21.865274300079566;
                            attribute sigma_Cy : Real = 17.470738675122718;
                            attribute Cz : Real = 25.79865216135028;
                            attribute sigma_Cz : Real = 17.51802736047386;
                            attribute Ixx : Real = 15193.75838027431;
                            attribute sigma_Ixx : Real = 7212.114276279608;
                            attribute Iyy : Real = 24974.559370444054;
                            attribute sigma_Iyy : Real = 9450.312081950931;
                            attribute Izz : Real = 23513.298880072965;
                            attribute sigma_Izz : Real = 9318.81692903457;
                            attribute Ixy : Real = 7836.811988733043;
                            attribute sigma_Ixy : Real = 4345.466272618858;
                            attribute Ixz : Real = 1027.4988871099767;
                            attribute sigma_Ixz : Real = 4341.110642051513;
                            attribute Iyz : Real = -4721.587894963078;
                            attribute sigma_Iyz : Real = 3478.6024073493536;
                            part <'C.1.1.3.3.2.1.1'> 'Part 351' {
                                attribute POIconv : String = "-";
                                attribute Ipoint : Boolean = false;
                                attribute mass : Real = 0.77704927199753;
                                attribute sigma_mass : Real = 0.28909372274994966;
                                attribute Cx : Real = 70.05582912825048;
                                attribute sigma_Cx : Real = 28.721044428837228;
                                attribute Cy : Real = -90.65169123932719;
                                attribute sigma_Cy : Real = 28.23690002309109;
                                attribute Cz : Real = -53.16146709956229;
                                attribute sigma_Cz : Real = 29.057750463592832;
                                attribute Ixx : Real = 0.9895311238446165;
                                attribute sigma_Ixx : Real = 0.37074144170588635;
                                attribute Iyy : Real = 0.84551021282698;
                                attribute sigma_Iyy : Real = 0.3723953238821935;
                                attribute Izz : Real = 0.9724325137632895;
                                attribute sigma_Izz : Real = 0.37017423652493897;
                                attribute Ixy : Real = -0.036116724543611714;
                                attribute sigma_Ixy : Real = 0.02351283871158888;
                                attribute Ixz : Real = -0.0013055538886287076;
                                attribute sigma_Ixz : Real = 0.022566176940390956;
                                attribute Iyz : Real = -0.020873950018523157;
                                attribute sigma_Iyz : Real = 0.02209918015384651;
                            }
                            part <'C.1.1.3.3.2.1.2'> 'Part 352' {
                                attribute POIconv : String = "-";
                                attribute Ipoint : Boolean = false;
                                attribute mass : Real = 0.34672079734317957;
                                attribute sigma_mass : Real = 0.28909372274994966;
                                attribute Cx : Real = 90.2286637108773;
                                attribute sigma_Cx : Real = 28.721044428837228;
                                attribute Cy : Real = -14.014111133292317;
                                attribute sigma_Cy : Real = 28.23690002309109;
                                attribute Cz : Real = 10.395548678934574;
                                attribute sigma_Cz : Real = 29.057750463592832;
                                attribute Ixx : Real = 0.4724925320319602;
                                attribute sigma_Ixx : Real = 0.37074144170588635;
                                attribute Iyy : Real = 0.4765015014220238;
                                attribute sigma_Iyy : Real = 0.3723953238821935;
                                attribute Izz : Real = 0.48873816688708965;
                                attribute sigma_Izz : Real = 0.37017423652493897;
                                attribute Ixy : Real = -0.014557722872197195;
                                attribute sigma_Ixy : Real = 0.02351283871158888;
                                attribute Ixz : Real = -0.03173305962860533;
                                attribute sigma_Ixz : Real = 0.022566176940390956;
                                attribute Iyz : Real = 0.00013034053223681666;
                                attribute sigma_Iyz : Real = 0.02209918015384651;
                            }
                            part <'C.1.1.3.3.2.1.3'> 'Part 353' {
                                attribute POIconv : String = "+";
                                attribute Ipoint : Boolean = false;
                                attribute mass : Real = 0.8570563166863285;
                                attribute sigma_mass : Real = 0.28909372274994966;
                                attribute Cx : Real = -77.57854368537664;
                                attribute sigma_Cx : Real = 28.721044428837228;
                                attribute Cy : Real = 27.805724507197738;
                                attribute sigma_Cy : Real = 28.23690002309109;
                                attribute Cz : Real = 38.91883506439626;
                                attribute sigma_Cz : Real = 29.057750463592832;
                                attribute Ixx : Real = 1.1371704390374393;
                                attribute sigma_Ixx : Real = 0.37074144170588635;
                                attribute Iyy : Real = 1.1473445203900074;
                                attribute sigma_Iyy : Real = 0.3723953238821935;
                                attribute Izz : Real = 1.0822245381959128;
                                attribute sigma_Izz : Real = 0.37017423652493897;
                                attribute Ixy : Real = 0.021969742746294284;
                                attribute sigma_Ixy : Real = 0.02351283871158888;
                                attribute Ixz : Real = 0.08954292109316597;
                                attribute sigma_Ixz : Real = 0.022566176940390956;
                                attribute Iyz : Real = -0.09571725841884535;
                                attribute sigma_Iyz : Real = 0.02209918015384651;
                            }
                            part <'C.1.1.3.3.2.1.4'> 'Part 354' {
                                attribute POIconv : String = "+";
                                attribute Ipoint : Boolean = false;
                                attribute mass : Real = 0.8075060287709348;
                                attribute sigma_mass : Real = 0.28909372274994966;
                                attribute Cx : Real = 95.47860003076494;
                                attribute sigma_Cx : Real = 28.721044428837228;
                                attribute Cy : Real = -29.560013441368937;
                                attribute sigma_Cy : Real = 28.23690002309109;
                                attribute Cz : Real = 87.90220720693469;
                                attribute sigma_Cz : Real = 29.057750463592832;
                                attribute Ixx : Real = 1.0222307270645512;
                                attribute sigma_Ixx : Real = 0.37074144170588635;
                                attribute Iyy : Real = 1.0425468890200875;
                                attribute sigma_Iyy : Real = 0.3723953238821935;
                                attribute Izz : Real = 1.0088720804606368;
                                attribute sigma_Izz : Real = 0.37017423652493897;
                                attribute Ixy : Real = 0.06613813756534859;
                                attribute sigma_Ixy : Real = 0.02351283871158888;
                                attribute Ixz : Real = -0.051207983586662245;
                                attribute sigma_Ixz : Real = 0.022566176940390956;
                                attribute Iyz : Real = 0.056839000670519446;
                                attribute sigma_Iyz : Real = 0.02209918015384651;
                            }
                            part <'C.1.1.3.3.2.1.5'> 'Part 355' {
                                attribute POIconv : String = "-";
                                attribute Ipoint : Boolean = false;
                                attribute mass : Real = 0.20572458224953152;
                                attribute sigma_mass : Real = 0.28909372274994966;
                                attribute Cx : Real = -30.770735954865813;
                                attribute sigma_Cx : Real = 28.721044428837228;
                                attribute Cy : Real = 47.99015307798982;
                                attribute sigma_Cy : Real = 28.23690002309109;
                                attribute Cz : Real = 51.574612967669964;
                                attribute sigma_Cz : Real = 29.057750463592832;
                                attribute Ixx : Real = 0.2839137586999741;
                                attribute sigma_Ixx : Real = 0.37074144170588635;
                                attribute Iyy : Real = 0.2687665489168035;
                                attribute sigma_Iyy : Real = 0.3723953238821935;
                                attribute Izz : Real = 0.27125756260417366;
                                attribute sigma_Izz : Real = 0.37017423652493897;
                                attribute Ixy : Real = 0.0027132013043448767;
                                attribute sigma_Ixy : Real = 0.02351283871158888;
                                attribute Ixz : Real = -0.005324956905221535;
                                attribute sigma_Ixz : Real = 0.022566176940390956;
                                attribute Iyz : Real = -0.00343109518570215;
                                attribute sigma_Iyz : Real = 0.02209918015384651;
                            }
                        }
                        part <'C.1.1.3.3.2.2'> 'Subassembly 107' {
                            attribute POIconv : String = "-";
                            attribute Ipoint : Boolean = false;
                            attribute mass : Real = 1.0092766979075969;
                            attribute sigma_mass : Real = 0.5007250159521434;
                            attribute Cx : Real = 22.413672572189515;
                            attribute sigma_Cx : Real = 28.82088552559873;
                            attribute Cy : Real = 31.23489334402283;
                            attribute sigma_Cy : Real = 30.923333829971686;
                            attribute Cz : Real = -6.41320694053573;
                            attribute sigma_Cz : Real = 24.327581746941398;
                            attribute Ixx : Real = 397.1840379751472;
                            attribute sigma_Ixx : Real = 2131.241612664933;
                            attribute Iyy : Real = 848.2948689816669;
                            attribute sigma_Iyy : Real = 1442.5717847313906;
                            attribute Izz : Real = 1058.973369606776;
                            attribute sigma_Izz : Real = 2553.9931352836147;
                            attribute Ixy : Real = 206.79360290599837;
                            attribute sigma_Ixy : Real = 1077.7898102935646;
                            attribute Ixz : Real = 68.10674644042818;
                            attribute sigma_Ixz : Real = 640.6567040373775;
                            attribute Iyz : Real = 127.31418645043985;
                            attribute sigma_Iyz : Real = 807.174289710943;
                            part <'C.1.1.3.3.2.2.1'> 'Part 356' {
                                attribute POIconv : String = "-";
                                attribute Ipoint : Boolean = false;
                                attribute mass : Real = 0.2372182305334136;
                                attribute sigma_mass : Real = 0.28909372274994966;
                                attribute Cx : Real = -25.50076711922884;
                                attribute sigma_Cx : Real = 28.721044428837228;
                                attribute Cy : Real = 37.69216509535909;
                                attribute sigma_Cy : Real = 28.23690002309109;
                                attribute Cz : Real = 1.8723068293184042;
                                attribute sigma_Cz : Real = 29.057750463592832;
                                attribute Ixx : Real = 0.29134553987413647;
                                attribute sigma_Ixx : Real = 0.37074144170588635;
                                attribute Iyy : Real = 0.3015563682877139;
                                attribute sigma_Iyy : Real = 0.3723953238821935;
                                attribute Izz : Real = 0.3665896343791621;
                                attribute sigma_Izz : Real = 0.37017423652493897;
                                attribute Ixy : Real = -0.008189519011996816;
                                attribute sigma_Ixy : Real = 0.02351283871158888;
                                attribute Ixz : Real = 0.012289423546843217;
                                attribute sigma_Ixz : Real = 0.022566176940390956;
                                attribute Iyz : Real = -0.02760671114873288;
                                attribute sigma_Iyz : Real = 0.02209918015384651;
                            }
                            part <'C.1.1.3.3.2.2.2'> 'Part 357' {
                                attribute POIconv : String = "-";
                                attribute Ipoint : Boolean = false;
                                attribute mass : Real = 0.04752086375420913;
                                attribute sigma_mass : Real = 0.28909372274994966;
                                attribute Cx : Real = 66.05742904357612;
                                attribute sigma_Cx : Real = 28.721044428837228;
                                attribute Cy : Real = -46.46932524628937;
                                attribute sigma_Cy : Real = 28.23690002309109;
                                attribute Cz : Real = 28.583692107349634;
                                attribute sigma_Cz : Real = 29.057750463592832;
                                attribute Ixx : Real = 0.057919704634129085;
                                attribute sigma_Ixx : Real = 0.37074144170588635;
                                attribute Iyy : Real = 0.054995967699237265;
                                attribute sigma_Iyy : Real = 0.3723953238821935;
                                attribute Izz : Real = 0.0649351684678988;
                                attribute sigma_Izz : Real = 0.37017423652493897;
                                attribute Ixy : Real = -0.004256242558669406;
                                attribute sigma_Ixy : Real = 0.02351283871158888;
                                attribute Ixz : Real = 0.001327113246219507;
                                attribute sigma_Ixz : Real = 0.022566176940390956;
                                attribute Iyz : Real = -0.004210082649598986;
                                attribute sigma_Iyz : Real = 0.02209918015384651;
                            }
                            part <'C.1.1.3.3.2.2.3'> 'Part 358' {
                                attribute POIconv : String = "-";
                                attribute Ipoint : Boolean = false;
                                attribute mass : Real = 0.7245376036199741;
                                attribute sigma_mass : Real = 0.28909372274994966;
                                attribute Cx : Real = 35.23866543546319;
                                attribute sigma_Cx : Real = 28.721044428837228;
                                attribute Cy : Real = 34.217194048687816;
                                attribute sigma_Cy : Real = 28.23690002309109;
                                attribute Cz : Real = -11.421308340504766;
                                attribute sigma_Cz : Real = 29.057750463592832;
                                attribute Ixx : Real = 0.9112260261089657;
                                attribute sigma_Ixx : Real = 0.37074144170588635;
                                attribute Iyy : Real = 0.9854030878342958;
                                attribute sigma_Iyy : Real = 0.3723953238821935;
                                attribute Izz : Real = 0.9851808842484352;
                                attribute sigma_Izz : Real = 0.37017423652493897;
                                attribute Ixy : Real = -0.03404675019815247;
                                attribute sigma_Ixy : Real = 0.02351283871158888;
                                attribute Ixz : Real = -0.03454329038095409;
                                attribute sigma_Ixz : Real = 0.022566176940390956;
                                attribute Iyz : Real = -0.012396529647119573;
                                attribute sigma_Iyz : Real = 0.02209918015384651;
                            }
                        }
                    }
                    part <'C.1.1.3.3.3'> 'Assembly 30' {
                        attribute POIconv : String = "-";
                        attribute Ipoint : Boolean = false;
                        attribute mass : Real = 10.514999999251216;
                        attribute sigma_mass : Real = 1.2265207905297186;
                        attribute Cx : Real = -15.31210125086863;
                        attribute sigma_Cx : Real = 9.919525450962563;
                        attribute Cy : Real = 15.108715665082384;
                        attribute sigma_Cy : Real = 9.344055379356384;
                        attribute Cz : Real = -7.242404945677322;
                        attribute sigma_Cz : Real = 9.413278932397635;
                        attribute Ixx : Real = 58357.94329348022;
                        attribute sigma_Ixx : Real = 13528.313538203362;
                        attribute Iyy : Real = 60703.56948270314;
                        attribute sigma_Iyy : Real = 13726.234343497996;
                        attribute Izz : Real = 63602.4084194988;
                        attribute sigma_Izz : Real = 14320.88951978502;
                        attribute Ixy : Real = -9681.538820809023;
                        attribute sigma_Ixy : Real = 6819.518845333132;
                        attribute Ixz : Real = 13965.23492871253;
                        attribute sigma_Ixz : Real = 6628.9974813705885;
                        attribute Iyz : Real = 7126.254048751177;
                        attribute sigma_Iyz : Real = 6527.864411974234;
                        part <'C.1.1.3.3.3.1'> 'Subassembly 108' {
                            attribute POIconv : String = "-";
                            attribute Ipoint : Boolean = false;
                            attribute mass : Real = 2.997771540727234;
                            attribute sigma_mass : Real = 0.5781874454998993;
                            attribute Cx : Real = -59.97227526736987;
                            attribute sigma_Cx : Real = 14.706995920099937;
                            attribute Cy : Real = -12.062514566295148;
                            attribute sigma_Cy : Real = 16.970371880925445;
                            attribute Cz : Real = 13.719707354701466;
                            attribute sigma_Cz : Real = 17.537411714793446;
                            attribute Ixx : Real = 14453.691274094796;
                            attribute sigma_Ixx : Real = 6727.679522556372;
                            attribute Iyy : Real = 8060.396660732785;
                            attribute sigma_Iyy : Real = 4834.264007136745;
                            attribute Izz : Real = 7467.772948182492;
                            attribute sigma_Izz : Real = 4669.354859209784;
                            attribute Ixy : Real = -475.18357009518377;
                            attribute sigma_Ixy : Real = 2161.8543117743525;
                            attribute Ixz : Real = 944.3386571365262;
                            attribute sigma_Ixz : Real = 2289.65931997309;
                            attribute Iyz : Real = 382.2973788029669;
                            attribute sigma_Iyz : Real = 3248.7490218257035;
                            part <'C.1.1.3.3.3.1.1'> 'Part 359' {
                                attribute POIconv : String = "+";
                                attribute Ipoint : Boolean = false;
                                attribute mass : Real = 0.8504522860716097;
                                attribute sigma_mass : Real = 0.28909372274994966;
                                attribute Cx : Real = -49.115600530058146;
                                attribute sigma_Cx : Real = 28.721044428837228;
                                attribute Cy : Real = 44.19183866120875;
                                attribute sigma_Cy : Real = 28.23690002309109;
                                attribute Cz : Real = -43.12542281113565;
                                attribute sigma_Cz : Real = 29.057750463592832;
                                attribute Ixx : Real = 1.2859925581689495;
                                attribute sigma_Ixx : Real = 0.37074144170588635;
                                attribute Iyy : Real = 1.2703321565005177;
                                attribute sigma_Iyy : Real = 0.3723953238821935;
                                attribute Izz : Real = 1.2792177094362849;
                                attribute sigma_Izz : Real = 0.37017423652493897;
                                attribute Ixy : Real = -0.012581350744978818;
                                attribute sigma_Ixy : Real = 0.02351283871158888;
                                attribute Ixz : Real = 0.017977905440962234;
                                attribute sigma_Ixz : Real = 0.022566176940390956;
                                attribute Iyz : Real = 0.011617879109940707;
                                attribute sigma_Iyz : Real = 0.02209918015384651;
                            }
                            part <'C.1.1.3.3.3.1.2'> 'Part 360' {
                                attribute POIconv : String = "-";
                                attribute Ipoint : Boolean = false;
                                attribute mass : Real = 0.6315701652944553;
                                attribute sigma_mass : Real = 0.28909372274994966;
                                attribute Cx : Real = -83.37428821250796;
                                attribute sigma_Cx : Real = 28.721044428837228;
                                attribute Cy : Real = 1.954424660652876;
                                attribute sigma_Cy : Real = 28.23690002309109;
                                attribute Cz : Real = 72.82711169682443;
                                attribute sigma_Cz : Real = 29.057750463592832;
                                attribute Ixx : Real = 0.7236730051605913;
                                attribute sigma_Ixx : Real = 0.37074144170588635;
                                attribute Iyy : Real = 0.7205043949279477;
                                attribute sigma_Iyy : Real = 0.3723953238821935;
                                attribute Izz : Real = 0.8530657457063536;
                                attribute sigma_Izz : Real = 0.37017423652493897;
                                attribute Ixy : Real = 0.016007201976327993;
                                attribute sigma_Ixy : Real = 0.02351283871158888;
                                attribute Ixz : Real = 0.06380973638404938;
                                attribute sigma_Ixz : Real = 0.022566176940390956;
                                attribute Iyz : Real = -0.02362741773822745;
                                attribute sigma_Iyz : Real = 0.02209918015384651;
                            }
                            part <'C.1.1.3.3.3.1.3'> 'Part 361' {
                                attribute POIconv : String = "+";
                                attribute Ipoint : Boolean = false;
                                attribute mass : Real = 0.6996143925464712;
                                attribute sigma_mass : Real = 0.28909372274994966;
                                attribute Cx : Real = -63.59420269727707;
                                attribute sigma_Cx : Real = 28.721044428837228;
                                attribute Cy : Real = -88.62598459236324;
                                attribute sigma_Cy : Real = 28.23690002309109;
                                attribute Cz : Real = -22.760992124676704;
                                attribute sigma_Cz : Real = 29.057750463592832;
                                attribute Ixx : Real = 0.9098811334073331;
                                attribute sigma_Ixx : Real = 0.37074144170588635;
                                attribute Iyy : Real = 0.8575401273555749;
                                attribute sigma_Iyy : Real = 0.3723953238821935;
                                attribute Izz : Real = 0.8742757121999164;
                                attribute sigma_Izz : Real = 0.37017423652493897;
                                attribute Ixy : Real = -0.04562700392134493;
                                attribute sigma_Ixy : Real = 0.02351283871158888;
                                attribute Ixz : Real = -0.022545919239275007;
                                attribute sigma_Ixz : Real = 0.022566176940390956;
                                attribute Iyz : Real = -0.0021049229370553877;
                                attribute sigma_Iyz : Real = 0.02209918015384651;
                            }
                            part <'C.1.1.3.3.3.1.4'> 'Part 362' {
                                attribute POIconv : String = "+";
                                attribute Ipoint : Boolean = false;
                                attribute mass : Real = 0.8161346968146972;
                                attribute sigma_mass : Real = 0.28909372274994966;
                                attribute Cx : Real = -50.07086815312505;
                                attribute sigma_Cx : Real = 28.721044428837228;
                                attribute Cy : Real = -15.8969531301409;
                                attribute sigma_Cy : Real = 28.23690002309109;
                                attribute Cz : Real = 58.48685218952596;
                                attribute sigma_Cz : Real = 29.057750463592832;
                                attribute Ixx : Real = 0.9474334592935165;
                                attribute sigma_Ixx : Real = 0.37074144170588635;
                                attribute Iyy : Real = 0.9142407891330531;
                                attribute sigma_Iyy : Real = 0.3723953238821935;
                                attribute Izz : Real = 0.9510547762293589;
                                attribute sigma_Izz : Real = 0.37017423652493897;
                                attribute Ixy : Real = 0.004616361332841578;
                                attribute sigma_Ixy : Real = 0.02351283871158888;
                                attribute Ixz : Real = -0.0045825795372115685;
                                attribute sigma_Ixz : Real = 0.022566176940390956;
                                attribute Iyz : Real = -0.015149540630757522;
                                attribute sigma_Iyz : Real = 0.02209918015384651;
                            }
                        }
                        part <'C.1.1.3.3.3.2'> 'Subassembly 109' {
                            attribute POIconv : String = "-";
                            attribute Ipoint : Boolean = false;
                            attribute mass : Real = 1.064028270998504;
                            attribute sigma_mass : Real = 0.40884026350990615;
                            attribute Cx : Real = 0.8047684784785102;
                            attribute sigma_Cx : Real = 31.8085228413183;
                            attribute Cy : Real = 4.711309563071165;
                            attribute sigma_Cy : Real = 20.239183014663837;
                            attribute Cz : Real = 16.716060387004102;
                            attribute sigma_Cz : Real = 29.171983622497127;
                            attribute Ixx : Real = 2852.2545619953416;
                            attribute sigma_Ixx : Real = 2541.282601589866;
                            attribute Iyy : Real = 6866.6898419057225;
                            attribute sigma_Iyy : Real = 4515.515606015504;
                            attribute Izz : Real = 4018.136565537364;
                            attribute sigma_Izz : Real = 3128.415718164466;
                            attribute Ixy : Real = 69.05171907811621;
                            attribute sigma_Ixy : Real = 1287.86866477937;
                            attribute Ixz : Real = 3382.7036982751674;
                            attribute sigma_Ixz : Real = 2246.6790999932223;
                            attribute Iyz : Real = -58.11567383863665;
                            attribute sigma_Iyz : Real = 1084.9927584677703;
                            part <'C.1.1.3.3.3.2.1'> 'Part 363' {
                                attribute POIconv : String = "-";
                                attribute Ipoint : Boolean = false;
                                attribute mass : Real = 0.44449189454852606;
                                attribute sigma_mass : Real = 0.28909372274994966;
                                attribute Cx : Real = 73.33115013316274;
                                attribute sigma_Cx : Real = 28.721044428837228;
                                attribute Cy : Real = 3.464101580902934;
                                attribute sigma_Cy : Real = 28.23690002309109;
                                attribute Cz : Real = -44.381224643439054;
                                attribute sigma_Cz : Real = 29.057750463592832;
                                attribute Ixx : Real = 0.6340587886663713;
                                attribute sigma_Ixx : Real = 0.37074144170588635;
                                attribute Iyy : Real = 0.6257638950324168;
                                attribute sigma_Iyy : Real = 0.3723953238821935;
                                attribute Izz : Real = 0.6074280828308877;
                                attribute sigma_Izz : Real = 0.37017423652493897;
                                attribute Ixy : Real = -0.011954897470110134;
                                attribute sigma_Ixy : Real = 0.02351283871158888;
                                attribute Ixz : Real = -0.01721122078046567;
                                attribute sigma_Ixz : Real = 0.022566176940390956;
                                attribute Iyz : Real = 0.011125900437416226;
                                attribute sigma_Iyz : Real = 0.02209918015384651;
                            }
                            part <'C.1.1.3.3.3.2.2'> 'Part 364' {
                                attribute POIconv : String = "-";
                                attribute Ipoint : Boolean = false;
                                attribute mass : Real = 0.6195363764499779;
                                attribute sigma_mass : Real = 0.28909372274994966;
                                attribute Cx : Real = -51.22993038967252;
                                attribute sigma_Cx : Real = 28.721044428837228;
                                attribute Cy : Real = 5.6061300449073315;
                                attribute sigma_Cy : Real = 28.23690002309109;
                                attribute Cz : Real = 60.55085202679038;
                                attribute sigma_Cz : Real = 29.057750463592832;
                                attribute Ixx : Real = 0.766592003874242;
                                attribute sigma_Ixx : Real = 0.37074144170588635;
                                attribute Iyy : Real = 0.8736708767852546;
                                attribute sigma_Iyy : Real = 0.3723953238821935;
                                attribute Izz : Real = 0.8176724382256669;
                                attribute sigma_Izz : Real = 0.37017423652493897;
                                attribute Ixy : Real = 0.01026958985554561;
                                attribute sigma_Ixy : Real = 0.02351283871158888;
                                attribute Ixz : Real = -0.015242290774441194;
                                attribute sigma_Ixz : Real = 0.022566176940390956;
                                attribute Iyz : Real = 0.04479842730099822;
                                attribute sigma_Iyz : Real = 0.02209918015384651;
                            }
                        }
                        part <'C.1.1.3.3.3.3'> 'Subassembly 110' {
                            attribute POIconv : String = "-";
                            attribute Ipoint : Boolean = false;
                            attribute mass : Real = 2.4005059999492953;
                            attribute sigma_mass : Real = 0.6464332159373649;
                            attribute Cx : Real = 21.093815433866173;
                            attribute sigma_Cx : Real = 20.146257484007013;
                            attribute Cy : Real = 2.3472877997857275;
                            attribute sigma_Cy : Real = 20.455895125248926;
                            attribute Cz : Real = -29.23705162603596;
                            attribute sigma_Cz : Real = 20.55145819618231;
                            attribute Ixx : Real = 17998.036326702826;
                            attribute sigma_Ixx : Real = 7648.943280585482;
                            attribute Iyy : Real = 14084.14507098088;
                            attribute sigma_Iyy : Real = 6519.795266833718;
                            attribute Izz : Real = 15842.262239032681;
                            attribute sigma_Izz : Real = 7153.1206008311265;
                            attribute Ixy : Real = -6570.098982667732;
                            attribute sigma_Ixy : Real = 3284.809083439366;
                            attribute Ixz : Real = 2253.8645926700365;
                            attribute sigma_Ixz : Real = 3028.478033785712;
                            attribute Iyz : Real = 5064.073242799943;
                            attribute sigma_Iyz : Real = 3741.560488628619;
                            part <'C.1.1.3.3.3.3.1'> 'Part 365' {
                                attribute POIconv : String = "+";
                                attribute Ipoint : Boolean = false;
                                attribute mass : Real = 0.6631013120673597;
                                attribute sigma_mass : Real = 0.28909372274994966;
                                attribute Cx : Real = -26.361875887960196;
                                attribute sigma_Cx : Real = 28.721044428837228;
                                attribute Cy : Real = -91.08197679743171;
                                attribute sigma_Cy : Real = 28.23690002309109;
                                attribute Cz : Real = 32.93327162973583;
                                attribute sigma_Cz : Real = 29.057750463592832;
                                attribute Ixx : Real = 0.8681920304754445;
                                attribute sigma_Ixx : Real = 0.37074144170588635;
                                attribute Iyy : Real = 0.8343259704647652;
                                attribute sigma_Iyy : Real = 0.3723953238821935;
                                attribute Izz : Real = 0.9656238455132924;
                                attribute sigma_Izz : Real = 0.37017423652493897;
                                attribute Ixy : Real = 0.010485765311351203;
                                attribute sigma_Ixy : Real = 0.02351283871158888;
                                attribute Ixz : Real = 0.07894198419442901;
                                attribute sigma_Ixz : Real = 0.022566176940390956;
                                attribute Iyz : Real = -0.006375601374078912;
                                attribute sigma_Iyz : Real = 0.02209918015384651;
                            }
                            part <'C.1.1.3.3.3.3.2'> 'Part 366' {
                                attribute POIconv : String = "-";
                                attribute Ipoint : Boolean = false;
                                attribute mass : Real = 0.43639439152251;
                                attribute sigma_mass : Real = 0.28909372274994966;
                                attribute Cx : Real = 60.67314734682441;
                                attribute sigma_Cx : Real = 28.721044428837228;
                                attribute Cy : Real = 51.530647557228804;
                                attribute sigma_Cy : Real = 28.23690002309109;
                                attribute Cz : Real = 34.53284106217325;
                                attribute sigma_Cz : Real = 29.057750463592832;
                                attribute Ixx : Real = 0.5965071925441982;
                                attribute sigma_Ixx : Real = 0.37074144170588635;
                                attribute Iyy : Real = 0.6196004966756115;
                                attribute sigma_Iyy : Real = 0.3723953238821935;
                                attribute Izz : Real = 0.6755973245670407;
                                attribute sigma_Izz : Real = 0.37017423652493897;
                                attribute Ixy : Real = 0.019010842469309133;
                                attribute sigma_Ixy : Real = 0.02351283871158888;
                                attribute Ixz : Real = 0.00013449155068283064;
                                attribute sigma_Ixz : Real = 0.022566176940390956;
                                attribute Iyz : Real = -0.00020597936091259472;
                                attribute sigma_Iyz : Real = 0.02209918015384651;
                            }
                            part <'C.1.1.3.3.3.3.3'> 'Part 367' {
                                attribute POIconv : String = "-";
                                attribute Ipoint : Boolean = false;
                                attribute mass : Real = 0.29280219084909187;
                                attribute sigma_mass : Real = 0.28909372274994966;
                                attribute Cx : Real = 51.96624989621341;
                                attribute sigma_Cx : Real = 28.721044428837228;
                                attribute Cy : Real = 20.35210942849517;
                                attribute sigma_Cy : Real = 28.23690002309109;
                                attribute Cz : Real = -84.27569982595742;
                                attribute sigma_Cz : Real = 29.057750463592832;
                                attribute Ixx : Real = 0.38775073085315237;
                                attribute sigma_Ixx : Real = 0.37074144170588635;
                                attribute Iyy : Real = 0.37682545416182517;
                                attribute sigma_Iyy : Real = 0.3723953238821935;
                                attribute Izz : Real = 0.41072470042932147;
                                attribute sigma_Izz : Real = 0.37017423652493897;
                                attribute Ixy : Real = -0.030480396750700398;
                                attribute sigma_Ixy : Real = 0.02351283871158888;
                                attribute Ixz : Real = 0.021042182170702382;
                                attribute sigma_Ixz : Real = 0.022566176940390956;
                                attribute Iyz : Real = 0.0004046926077895442;
                                attribute sigma_Iyz : Real = 0.02209918015384651;
                            }
                            part <'C.1.1.3.3.3.3.4'> 'Part 368' {
                                attribute POIconv : String = "-";
                                attribute Ipoint : Boolean = false;
                                attribute mass : Real = 0.7366351738085505;
                                attribute sigma_mass : Real = 0.28909372274994966;
                                attribute Cx : Real = 61.88151203095913;
                                attribute sigma_Cx : Real = 28.721044428837228;
                                attribute Cy : Real = 62.26568752899766;
                                attribute sigma_Cy : Real = 28.23690002309109;
                                attribute Cz : Real = -88.20957448333502;
                                attribute sigma_Cz : Real = 29.057750463592832;
                                attribute Ixx : Real = 0.8327232536244488;
                                attribute sigma_Ixx : Real = 0.37074144170588635;
                                attribute Iyy : Real = 0.7531982390595652;
                                attribute sigma_Iyy : Real = 0.3723953238821935;
                                attribute Izz : Real = 0.8055498768810735;
                                attribute sigma_Izz : Real = 0.37017423652493897;
                                attribute Ixy : Real = 0.009441943800766153;
                                attribute sigma_Ixy : Real = 0.02351283871158888;
                                attribute Ixz : Real = -0.0004412399267944972;
                                attribute sigma_Ixz : Real = 0.022566176940390956;
                                attribute Iyz : Real = -0.0024008129387950152;
                                attribute sigma_Iyz : Real = 0.02209918015384651;
                            }
                            part <'C.1.1.3.3.3.3.5'> 'Part 369' {
                                attribute POIconv : String = "+";
                                attribute Ipoint : Boolean = false;
                                attribute mass : Real = 0.2715729317017831;
                                attribute sigma_mass : Real = 0.28909372274994966;
                                attribute Cx : Real = -70.55536163970828;
                                attribute sigma_Cx : Real = 28.721044428837228;
                                attribute Cy : Real = -30.49886655062437;
                                attribute sigma_Cy : Real = 28.23690002309109;
                                attribute Cz : Real = -64.20878088101745;
                                attribute sigma_Cz : Real = 29.057750463592832;
                                attribute Ixx : Real = 0.3161118053732044;
                                attribute sigma_Ixx : Real = 0.37074144170588635;
                                attribute Iyy : Real = 0.36828978337773255;
                                attribute sigma_Iyy : Real = 0.3723953238821935;
                                attribute Izz : Real = 0.3312912321796915;
                                attribute sigma_Izz : Real = 0.37017423652493897;
                                attribute Ixy : Real = -0.00846343292733176;
                                attribute sigma_Ixy : Real = 0.02351283871158888;
                                attribute Ixz : Real = -0.033531751516162125;
                                attribute sigma_Ixz : Real = 0.022566176940390956;
                                attribute Iyz : Real = -0.009268383138734036;
                                attribute sigma_Iyz : Real = 0.02209918015384651;
                            }
                        }
                        part <'C.1.1.3.3.3.4'> 'Subassembly 111' {
                            attribute POIconv : String = "-";
                            attribute Ipoint : Boolean = false;
                            attribute mass : Real = 2.1556833896718453;
                            attribute sigma_mass : Real = 0.5007250159521434;
                            attribute Cx : Real = 23.98546645899551;
                            attribute sigma_Cx : Real = 18.996763002755312;
                            attribute Cy : Real = 64.42192378114161;
                            attribute sigma_Cy : Real = 19.998123485015558;
                            attribute Cz : Real = -14.493783461233518;
                            attribute sigma_Cz : Real = 19.71433872687352;
                            attribute Ixx : Real = 5239.517403565071;
                            attribute sigma_Ixx : Real = 3903.7426197375994;
                            attribute Iyy : Real = 4886.071070446039;
                            attribute sigma_Iyy : Real = 3812.8350766905564;
                            attribute Izz : Real = 4801.843761580311;
                            attribute sigma_Izz : Real = 3639.313031086136;
                            attribute Ixy : Real = 35.08772449579442;
                            attribute sigma_Ixy : Real = 1717.6927161818708;
                            attribute Ixz : Real = 2374.6297882516456;
                            attribute sigma_Ixz : Real = 1896.5768225010627;
                            attribute Iyz : Real = -600.5581313727452;
                            attribute sigma_Iyz : Real = 1893.043064720378;
                            part <'C.1.1.3.3.3.4.1'> 'Part 370' {
                                attribute POIconv : String = "-";
                                attribute Ipoint : Boolean = false;
                                attribute mass : Real = 0.9836174107897095;
                                attribute sigma_mass : Real = 0.28909372274994966;
                                attribute Cx : Real = -11.059313593432307;
                                attribute sigma_Cx : Real = 28.721044428837228;
                                attribute Cy : Real = 65.70983855053782;
                                attribute sigma_Cy : Real = 28.23690002309109;
                                attribute Cz : Real = 23.10982048511505;
                                attribute sigma_Cz : Real = 29.057750463592832;
                                attribute Ixx : Real = 1.5057223389342758;
                                attribute sigma_Ixx : Real = 0.37074144170588635;
                                attribute Iyy : Real = 1.53427055622812;
                                attribute sigma_Iyy : Real = 0.3723953238821935;
                                attribute Izz : Real = 1.5314362347455965;
                                attribute sigma_Izz : Real = 0.37017423652493897;
                                attribute Ixy : Real = -0.012060290262935716;
                                attribute sigma_Ixy : Real = 0.02351283871158888;
                                attribute Ixz : Real = -0.01515338425031792;
                                attribute sigma_Ixz : Real = 0.022566176940390956;
                                attribute Iyz : Real = -0.0058937719634679555;
                                attribute sigma_Iyz : Real = 0.02209918015384651;
                            }
                            part <'C.1.1.3.3.3.4.2'> 'Part 371' {
                                attribute POIconv : String = "+";
                                attribute Ipoint : Boolean = false;
                                attribute mass : Real = 0.7890587515793741;
                                attribute sigma_mass : Real = 0.28909372274994966;
                                attribute Cx : Real = 53.98680209182203;
                                attribute sigma_Cx : Real = 28.721044428837228;
                                attribute Cy : Real = 95.98496975377202;
                                attribute sigma_Cy : Real = 28.23690002309109;
                                attribute Cz : Real = -39.544238056987524;
                                attribute sigma_Cz : Real = 29.057750463592832;
                                attribute Ixx : Real = 1.1721711015514373;
                                attribute sigma_Ixx : Real = 0.37074144170588635;
                                attribute Iyy : Real = 1.0951211235738731;
                                attribute sigma_Iyy : Real = 0.3723953238821935;
                                attribute Izz : Real = 1.1008474308553882;
                                attribute sigma_Izz : Real = 0.37017423652493897;
                                attribute Ixy : Real = -0.07280050465536486;
                                attribute sigma_Ixy : Real = 0.02351283871158888;
                                attribute Ixz : Real = 0.05799694573055922;
                                attribute sigma_Ixz : Real = 0.022566176940390956;
                                attribute Iyz : Real = 0.011487199058910876;
                                attribute sigma_Iyz : Real = 0.02209918015384651;
                            }
                            part <'C.1.1.3.3.3.4.3'> 'Part 372' {
                                attribute POIconv : String = "+";
                                attribute Ipoint : Boolean = false;
                                attribute mass : Real = 0.38300722730276177;
                                attribute sigma_mass : Real = 0.28909372274994966;
                                attribute Cx : Real = 52.177726570516825;
                                attribute sigma_Cx : Real = 28.721044428837228;
                                attribute Cy : Real = -3.9107633754611015;
                                attribute sigma_Cy : Real = 28.23690002309109;
                                attribute Cz : Real = -59.45711024105549;
                                attribute sigma_Cz : Real = 29.057750463592832;
                                attribute Ixx : Real = 0.38422021901327974;
                                attribute sigma_Ixx : Real = 0.37074144170588635;
                                attribute Iyy : Real = 0.4476683081339953;
                                attribute sigma_Iyy : Real = 0.3723953238821935;
                                attribute Izz : Real = 0.4538802454009414;
                                attribute sigma_Izz : Real = 0.37017423652493897;
                                attribute Ixy : Real = 0.027468949864668555;
                                attribute sigma_Ixy : Real = 0.02351283871158888;
                                attribute Ixz : Real = 0.039544325396093476;
                                attribute sigma_Ixz : Real = 0.022566176940390956;
                                attribute Iyz : Real = 0.011665527210420832;
                                attribute sigma_Iyz : Real = 0.02209918015384651;
                            }
                        }
                        part <'C.1.1.3.3.3.5'> 'Subassembly 112' {
                            attribute POIconv : String = "-";
                            attribute Ipoint : Boolean = false;
                            attribute mass : Real = 1.8970107979043387;
                            attribute sigma_mass : Real = 0.5781874454998993;
                            attribute Cx : Real = -44.50199401511804;
                            attribute sigma_Cx : Real = 22.600643273700587;
                            attribute Cy : Real = 23.989263578525442;
                            attribute sigma_Cy : Real = 19.46195917999472;
                            attribute Cz : Real = -17.733726667265387;
                            attribute sigma_Cz : Real = 19.259790438320792;
                            attribute Ixx : Real = 6292.0782285975965;
                            attribute sigma_Ixx : Real = 3821.711671532245;
                            attribute Iyy : Real = 9012.314848530626;
                            attribute sigma_Iyy : Real = 4972.178603351715;
                            attribute Izz : Real = 8978.960741242227;
                            attribute sigma_Izz : Real = 5267.396043367565;
                            attribute Ixy : Real = 3289.486030806638;
                            attribute sigma_Ixy : Real = 2491.879301484781;
                            attribute Ixz : Real = 658.6136701753896;
                            attribute sigma_Ixz : Real = 2097.2355709325543;
                            attribute Iyz : Real = 92.26299024720618;
                            attribute sigma_Iyz : Real = 1804.3989692315258;
                            part <'C.1.1.3.3.3.5.1'> 'Part 373' {
                                attribute POIconv : String = "-";
                                attribute Ipoint : Boolean = false;
                                attribute mass : Real = 0.4930017203444149;
                                attribute sigma_mass : Real = 0.28909372274994966;
                                attribute Cx : Real = 48.9634505007416;
                                attribute sigma_Cx : Real = 28.721044428837228;
                                attribute Cy : Real = -30.859337421134114;
                                attribute sigma_Cy : Real = 28.23690002309109;
                                attribute Cz : Real = -24.25348130054772;
                                attribute sigma_Cz : Real = 29.057750463592832;
                                attribute Ixx : Real = 0.7428852804728492;
                                attribute sigma_Ixx : Real = 0.37074144170588635;
                                attribute Iyy : Real = 0.7512146991308191;
                                attribute sigma_Iyy : Real = 0.3723953238821935;
                                attribute Izz : Real = 0.7529417182912935;
                                attribute sigma_Izz : Real = 0.37017423652493897;
                                attribute Ixy : Real = 0.013259708736063101;
                                attribute sigma_Ixy : Real = 0.02351283871158888;
                                attribute Ixz : Real = 0.012344322066848802;
                                attribute sigma_Ixz : Real = 0.022566176940390956;
                                attribute Iyz : Real = -0.008900075135714076;
                                attribute sigma_Iyz : Real = 0.02209918015384651;
                            }
                            part <'C.1.1.3.3.3.5.2'> 'Part 374' {
                                attribute POIconv : String = "+";
                                attribute Ipoint : Boolean = false;
                                attribute mass : Real = 0.49086345958150923;
                                attribute sigma_mass : Real = 0.28909372274994966;
                                attribute Cx : Real = -71.60062612965703;
                                attribute sigma_Cx : Real = 28.721044428837228;
                                attribute Cy : Real = 56.60618063993752;
                                attribute sigma_Cy : Real = 28.23690002309109;
                                attribute Cz : Real = -78.87534759938717;
                                attribute sigma_Cz : Real = 29.057750463592832;
                                attribute Ixx : Real = 0.6061484588404196;
                                attribute sigma_Ixx : Real = 0.37074144170588635;
                                attribute Iyy : Real = 0.554689354793227;
                                attribute sigma_Iyy : Real = 0.3723953238821935;
                                attribute Izz : Real = 0.679233732908539;
                                attribute sigma_Izz : Real = 0.37017423652493897;
                                attribute Ixy : Real = 0.026031544239559713;
                                attribute sigma_Ixy : Real = 0.02351283871158888;
                                attribute Ixz : Real = -0.008043975478040356;
                                attribute sigma_Ixz : Real = 0.022566176940390956;
                                attribute Iyz : Real = -0.059851779504421804;
                                attribute sigma_Iyz : Real = 0.02209918015384651;
                            }
                            part <'C.1.1.3.3.3.5.3'> 'Part 375' {
                                attribute POIconv : String = "-";
                                attribute Ipoint : Boolean = false;
                                attribute mass : Real = 0.24642546586622485;
                                attribute sigma_mass : Real = 0.28909372274994966;
                                attribute Cx : Real = -84.09838699735701;
                                attribute sigma_Cx : Real = 28.721044428837228;
                                attribute Cy : Real = -18.07793523184955;
                                attribute sigma_Cy : Real = 28.23690002309109;
                                attribute Cz : Real = 1.7397694289684296;
                                attribute sigma_Cz : Real = 29.057750463592832;
                                attribute Ixx : Real = 0.30882200594334985;
                                attribute sigma_Ixx : Real = 0.37074144170588635;
                                attribute Iyy : Real = 0.3082591801718887;
                                attribute sigma_Iyy : Real = 0.3723953238821935;
                                attribute Izz : Real = 0.29144252165497686;
                                attribute sigma_Izz : Real = 0.37017423652493897;
                                attribute Ixy : Real = 0.014654766119721687;
                                attribute sigma_Ixy : Real = 0.02351283871158888;
                                attribute Ixz : Real = -0.021475599004901584;
                                attribute sigma_Ixz : Real = 0.022566176940390956;
                                attribute Iyz : Real = 0.02084967314682651;
                                attribute sigma_Iyz : Real = 0.02209918015384651;
                            }
                            part <'C.1.1.3.3.3.5.4'> 'Part 376' {
                                attribute POIconv : String = "-";
                                attribute Ipoint : Boolean = false;
                                attribute mass : Real = 0.6667201521121897;
                                attribute sigma_mass : Real = 0.28909372274994966;
                                attribute Cx : Real = -79.02822960168123;
                                attribute sigma_Cx : Real = 28.721044428837228;
                                attribute Cy : Real = 56.081335339695215;
                                attribute sigma_Cy : Real = 28.23690002309109;
                                attribute Cz : Real = 24.90436127409339;
                                attribute sigma_Cz : Real = 29.057750463592832;
                                attribute Ixx : Real = 0.8349685941386452;
                                attribute sigma_Ixx : Real = 0.37074144170588635;
                                attribute Iyy : Real = 0.8474066305350284;
                                attribute sigma_Iyy : Real = 0.3723953238821935;
                                attribute Izz : Real = 0.7989530974833681;
                                attribute sigma_Izz : Real = 0.37017423652493897;
                                attribute Ixy : Real = 0.009647740900007574;
                                attribute sigma_Ixy : Real = 0.02351283871158888;
                                attribute Ixz : Real = -0.03165659888702023;
                                attribute sigma_Ixz : Real = 0.022566176940390956;
                                attribute Iyz : Real = 0.01557464612257966;
                                attribute sigma_Iyz : Real = 0.02209918015384651;
                            }
                        }
                    }
                    part <'C.1.1.3.3.4'> 'Assembly 31' {
                        attribute POIconv : String = "-";
                        attribute Ipoint : Boolean = false;
                        attribute mass : Real = 9.381551188631217;
                        attribute sigma_mass : Real = 1.2928664318747298;
                        attribute Cx : Real = -3.3021412653766937;
                        attribute sigma_Cx : Real = 11.522083922607795;
                        attribute Cy : Real = -13.113368741829307;
                        attribute sigma_Cy : Real = 10.131066561504804;
                        attribute Cz : Real = 16.592507870809133;
                        attribute sigma_Cz : Real = 11.391987221742353;
                        attribute Ixx : Real = 44711.97167929083;
                        attribute sigma_Ixx : Real = 13401.820167835911;
                        attribute Iyy : Real = 60524.64188943183;
                        attribute sigma_Iyy : Real = 15950.238827113679;
                        attribute Izz : Real = 50111.95299232394;
                        attribute sigma_Izz : Real = 15309.381547275436;
                        attribute Ixy : Real = -8613.498472465479;
                        attribute sigma_Ixy : Real = 7359.169567558964;
                        attribute Ixz : Real = -8568.83225601011;
                        attribute sigma_Ixz : Real = 7485.97766919722;
                        attribute Iyz : Real = -5604.480644744064;
                        attribute sigma_Iyz : Real = 5749.0805842953;
                        part <'C.1.1.3.3.4.1'> 'Subassembly 113' {
                            attribute POIconv : String = "-";
                            attribute Ipoint : Boolean = false;
                            attribute mass : Real = 2.4163755214146807;
                            attribute sigma_mass : Real = 0.6464332159373649;
                            attribute Cx : Real = 17.15173913803412;
                            attribute sigma_Cx : Real = 21.37437504986131;
                            attribute Cy : Real = 6.979886901576667;
                            attribute sigma_Cy : Real = 18.085380288808953;
                            attribute Cz : Real = 61.73286635376213;
                            attribute sigma_Cz : Real = 16.58984762217682;
                            attribute Ixx : Real = 6586.1953852492825;
                            attribute sigma_Ixx : Real = 4306.032227017998;
                            attribute Iyy : Real = 10991.17863174943;
                            attribute sigma_Iyy : Real = 5582.067745641134;
                            attribute Izz : Real = 13721.428864357313;
                            attribute sigma_Izz : Real = 6434.8610295201;
                            attribute Ixy : Real = -4386.369759900621;
                            attribute sigma_Ixy : Real = 2951.43387337332;
                            attribute Ixz : Real = -905.9457622344152;
                            attribute sigma_Ixz : Real = 2500.7240084490422;
                            attribute Iyz : Real = -1626.877541225338;
                            attribute sigma_Iyz : Real = 2115.9797929706383;
                            part <'C.1.1.3.3.4.1.1'> 'Part 377' {
                                attribute POIconv : String = "-";
                                attribute Ipoint : Boolean = false;
                                attribute mass : Real = 0.16786196228140035;
                                attribute sigma_mass : Real = 0.28909372274994966;
                                attribute Cx : Real = 85.8563244342804;
                                attribute sigma_Cx : Real = 28.721044428837228;
                                attribute Cy : Real = 16.847784537822008;
                                attribute sigma_Cy : Real = 28.23690002309109;
                                attribute Cz : Real = 68.2447683531791;
                                attribute sigma_Cz : Real = 29.057750463592832;
                                attribute Ixx : Real = 0.18772929224369217;
                                attribute sigma_Ixx : Real = 0.37074144170588635;
                                attribute Iyy : Real = 0.16351796613933164;
                                attribute sigma_Iyy : Real = 0.3723953238821935;
                                attribute Izz : Real = 0.18264884543448073;
                                attribute sigma_Izz : Real = 0.37017423652493897;
                                attribute Ixy : Real = 0.002366922563690748;
                                attribute sigma_Ixy : Real = 0.02351283871158888;
                                attribute Ixz : Real = -7.671349051615627e-05;
                                attribute sigma_Ixz : Real = 0.022566176940390956;
                                attribute Iyz : Real = -0.013367497632409162;
                                attribute sigma_Iyz : Real = 0.02209918015384651;
                            }
                            part <'C.1.1.3.3.4.1.2'> 'Part 378' {
                                attribute POIconv : String = "+";
                                attribute Ipoint : Boolean = false;
                                attribute mass : Real = 0.7761300614897627;
                                attribute sigma_mass : Real = 0.28909372274994966;
                                attribute Cx : Real = -40.10105608031154;
                                attribute sigma_Cx : Real = 28.721044428837228;
                                attribute Cy : Real = -18.691003043204546;
                                attribute sigma_Cy : Real = 28.23690002309109;
                                attribute Cz : Real = 82.37731056287885;
                                attribute sigma_Cz : Real = 29.057750463592832;
                                attribute Ixx : Real = 0.8337004375924344;
                                attribute sigma_Ixx : Real = 0.37074144170588635;
                                attribute Iyy : Real = 0.8948591043860825;
                                attribute sigma_Iyy : Real = 0.3723953238821935;
                                attribute Izz : Real = 0.9861817588244333;
                                attribute sigma_Izz : Real = 0.37017423652493897;
                                attribute Ixy : Real = -0.0727409255035611;
                                attribute sigma_Ixy : Real = 0.02351283871158888;
                                attribute Ixz : Real = 0.05749437187098973;
                                attribute sigma_Ixz : Real = 0.022566176940390956;
                                attribute Iyz : Real = -0.010528134551486382;
                                attribute sigma_Iyz : Real = 0.02209918015384651;
                            }
                            part <'C.1.1.3.3.4.1.3'> 'Part 379' {
                                attribute POIconv : String = "+";
                                attribute Ipoint : Boolean = false;
                                attribute mass : Real = 0.3677954891961999;
                                attribute sigma_mass : Real = 0.28909372274994966;
                                attribute Cx : Real = 6.675472250208259;
                                attribute sigma_Cx : Real = 28.721044428837228;
                                attribute Cy : Real = -64.9044412188232;
                                attribute sigma_Cy : Real = 28.23690002309109;
                                attribute Cz : Real = 6.5065456088632345;
                                attribute sigma_Cz : Real = 29.057750463592832;
                                attribute Ixx : Real = 0.45608195124425166;
                                attribute sigma_Ixx : Real = 0.37074144170588635;
                                attribute Iyy : Real = 0.4488835622870266;
                                attribute sigma_Iyy : Real = 0.3723953238821935;
                                attribute Izz : Real = 0.5122677597952316;
                                attribute sigma_Izz : Real = 0.37017423652493897;
                                attribute Ixy : Real = -0.028238561556379542;
                                attribute sigma_Ixy : Real = 0.02351283871158888;
                                attribute Ixz : Real = -0.003921683895963335;
                                attribute sigma_Ixz : Real = 0.022566176940390956;
                                attribute Iyz : Real = 0.046778849140629394;
                                attribute sigma_Iyz : Real = 0.02209918015384651;
                            }
                            part <'C.1.1.3.3.4.1.4'> 'Part 380' {
                                attribute POIconv : String = "-";
                                attribute Ipoint : Boolean = false;
                                attribute mass : Real = 0.35258977467520164;
                                attribute sigma_mass : Real = 0.28909372274994966;
                                attribute Cx : Real = -42.390523571521044;
                                attribute sigma_Cx : Real = 28.721044428837228;
                                attribute Cy : Real = 19.009209191426635;
                                attribute sigma_Cy : Real = 28.23690002309109;
                                attribute Cz : Real = 34.90069201216102;
                                attribute sigma_Cz : Real = 29.057750463592832;
                                attribute Ixx : Real = 0.35212763824570303;
                                attribute sigma_Ixx : Real = 0.37074144170588635;
                                attribute Iyy : Real = 0.3520464040277288;
                                attribute sigma_Iyy : Real = 0.3723953238821935;
                                attribute Izz : Real = 0.3167711626335207;
                                attribute sigma_Izz : Real = 0.37017423652493897;
                                attribute Ixy : Real = 0.004601997288405874;
                                attribute sigma_Ixy : Real = 0.02351283871158888;
                                attribute Ixz : Real = 0.0049188604272641405;
                                attribute sigma_Ixz : Real = 0.022566176940390956;
                                attribute Iyz : Real = -0.018591595479338606;
                                attribute sigma_Iyz : Real = 0.02209918015384651;
                            }
                            part <'C.1.1.3.3.4.1.5'> 'Part 381' {
                                attribute POIconv : String = "-";
                                attribute Ipoint : Boolean = false;
                                attribute mass : Real = 0.7519982337721158;
                                attribute sigma_mass : Real = 0.28909372274994966;
                                attribute Cx : Real = 93.94692704081535;
                                attribute sigma_Cx : Real = 28.721044428837228;
                                attribute Cy : Real = 60.78961477614939;
                                attribute sigma_Cy : Real = 28.23690002309109;
                                attribute Cz : Real = 78.5638467874378;
                                attribute sigma_Cz : Real = 29.057750463592832;
                                attribute Ixx : Real = 1.0658366598083429;
                                attribute sigma_Ixx : Real = 0.37074144170588635;
                                attribute Iyy : Real = 1.0515183722742143;
                                attribute sigma_Iyy : Real = 0.3723953238821935;
                                attribute Izz : Real = 0.9352413116792168;
                                attribute sigma_Izz : Real = 0.37017423652493897;
                                attribute Ixy : Real = -0.03138950107287084;
                                attribute sigma_Ixy : Real = 0.02351283871158888;
                                attribute Ixz : Real = -0.049741399104252855;
                                attribute sigma_Ixz : Real = 0.022566176940390956;
                                attribute Iyz : Real = 0.028469702048991283;
                                attribute sigma_Iyz : Real = 0.02209918015384651;
                            }
                        }
                        part <'C.1.1.3.3.4.2'> 'Subassembly 114' {
                            attribute POIconv : String = "-";
                            attribute Ipoint : Boolean = false;
                            attribute mass : Real = 2.0659983968331943;
                            attribute sigma_mass : Real = 0.6464332159373649;
                            attribute Cx : Real = -11.100563706032066;
                            attribute sigma_Cx : Real = 21.35035675349924;
                            attribute Cy : Real = 8.314801412135612;
                            attribute sigma_Cy : Real = 18.59358543430246;
                            attribute Cz : Real = -5.220615408631324;
                            attribute sigma_Cz : Real = 27.185477492558157;
                            attribute Ixx : Real = 9384.87362108956;
                            attribute sigma_Ixx : Real = 6117.237788238491;
                            attribute Iyy : Real = 12183.584574959017;
                            attribute sigma_Iyy : Real = 7563.84782112837;
                            attribute Izz : Real = 4654.643312073181;
                            attribute sigma_Izz : Real = 3661.3486037475063;
                            attribute Ixy : Real = -744.7450227637438;
                            attribute sigma_Ixy : Real = 1594.309662863061;
                            attribute Ixz : Real = -5531.63077725781;
                            attribute sigma_Ixz : Real = 3615.8304493140413;
                            attribute Iyz : Real = -1234.6851465405114;
                            attribute sigma_Iyz : Real = 2421.338789059716;
                            part <'C.1.1.3.3.4.2.1'> 'Part 382' {
                                attribute POIconv : String = "-";
                                attribute Ipoint : Boolean = false;
                                attribute mass : Real = 0.62546605390287;
                                attribute sigma_mass : Real = 0.28909372274994966;
                                attribute Cx : Real = 2.355882665142417;
                                attribute sigma_Cx : Real = 28.721044428837228;
                                attribute Cy : Real = -3.5654504783451557;
                                attribute sigma_Cy : Real = 28.23690002309109;
                                attribute Cz : Real = 25.43421327136457;
                                attribute sigma_Cz : Real = 29.057750463592832;
                                attribute Ixx : Real = 0.6564305318742797;
                                attribute sigma_Ixx : Real = 0.37074144170588635;
                                attribute Iyy : Real = 0.7143324744289306;
                                attribute sigma_Iyy : Real = 0.3723953238821935;
                                attribute Izz : Real = 0.7175145145447938;
                                attribute sigma_Izz : Real = 0.37017423652493897;
                                attribute Ixy : Real = -0.0146954903636636;
                                attribute sigma_Ixy : Real = 0.02351283871158888;
                                attribute Ixz : Real = -0.01780526800032754;
                                attribute sigma_Ixz : Real = 0.022566176940390956;
                                attribute Iyz : Real = -0.025956038590863963;
                                attribute sigma_Iyz : Real = 0.02209918015384651;
                            }
                            part <'C.1.1.3.3.4.2.2'> 'Part 383' {
                                attribute POIconv : String = "-";
                                attribute Ipoint : Boolean = false;
                                attribute mass : Real = 0.14246590520720928;
                                attribute sigma_mass : Real = 0.28909372274994966;
                                attribute Cx : Real = -13.453342951834202;
                                attribute sigma_Cx : Real = 28.721044428837228;
                                attribute Cy : Real = -45.40736894123256;
                                attribute sigma_Cy : Real = 28.23690002309109;
                                attribute Cz : Real = -40.9826572984457;
                                attribute sigma_Cz : Real = 29.057750463592832;
                                attribute Ixx : Real = 0.16077365099943794;
                                attribute sigma_Ixx : Real = 0.37074144170588635;
                                attribute Iyy : Real = 0.15703020875757595;
                                attribute sigma_Iyy : Real = 0.3723953238821935;
                                attribute Izz : Real = 0.15542495318233188;
                                attribute sigma_Izz : Real = 0.37017423652493897;
                                attribute Ixy : Real = 5.4811923751243034e-05;
                                attribute sigma_Ixy : Real = 0.02351283871158888;
                                attribute Ixz : Real = -0.0028249315988940864;
                                attribute sigma_Ixz : Real = 0.022566176940390956;
                                attribute Iyz : Real = 0.00194954496673525;
                                attribute sigma_Iyz : Real = 0.02209918015384651;
                            }
                            part <'C.1.1.3.3.4.2.3'> 'Part 384' {
                                attribute POIconv : String = "+";
                                attribute Ipoint : Boolean = false;
                                attribute mass : Real = 0.30736152279307133;
                                attribute sigma_mass : Real = 0.28909372274994966;
                                attribute Cx : Real = 64.03149636462331;
                                attribute sigma_Cx : Real = 28.721044428837228;
                                attribute Cy : Real = 38.015674659982324;
                                attribute sigma_Cy : Real = 28.23690002309109;
                                attribute Cz : Real = 99.04580633156002;
                                attribute sigma_Cz : Real = 29.057750463592832;
                                attribute Ixx : Real = 0.36714965255547966;
                                attribute sigma_Ixx : Real = 0.37074144170588635;
                                attribute Iyy : Real = 0.4088369471696716;
                                attribute sigma_Iyy : Real = 0.3723953238821935;
                                attribute Izz : Real = 0.3272964155798288;
                                attribute sigma_Izz : Real = 0.37017423652493897;
                                attribute Ixy : Real = -0.004865696717759781;
                                attribute sigma_Ixy : Real = 0.02351283871158888;
                                attribute Ixz : Real = 0.04523094933536531;
                                attribute sigma_Ixz : Real = 0.022566176940390956;
                                attribute Iyz : Real = 0.010244793744234936;
                                attribute sigma_Iyz : Real = 0.02209918015384651;
                            }
                            part <'C.1.1.3.3.4.2.4'> 'Part 385' {
                                attribute POIconv : String = "-";
                                attribute Ipoint : Boolean = false;
                                attribute mass : Real = 0.8813279117320199;
                                attribute sigma_mass : Real = 0.28909372274994966;
                                attribute Cx : Real = -53.15743167884648;
                                attribute sigma_Cx : Real = 28.721044428837228;
                                attribute Cy : Real = 10.442890552803874;
                                attribute sigma_Cy : Real = 28.23690002309109;
                                attribute Cz : Real = -68.36772146634758;
                                attribute sigma_Cz : Real = 29.057750463592832;
                                attribute Ixx : Real = 1.1694444186108524;
                                attribute sigma_Ixx : Real = 0.37074144170588635;
                                attribute Iyy : Real = 1.2350173669635875;
                                attribute sigma_Iyy : Real = 0.3723953238821935;
                                attribute Izz : Real = 1.221708662038103;
                                attribute sigma_Izz : Real = 0.37017423652493897;
                                attribute Ixy : Real = 0.03883823840806931;
                                attribute sigma_Ixy : Real = 0.02351283871158888;
                                attribute Ixz : Real = 0.021780530814033063;
                                attribute sigma_Ixz : Real = 0.022566176940390956;
                                attribute Iyz : Real = 0.03573074102659063;
                                attribute sigma_Iyz : Real = 0.02209918015384651;
                            }
                            part <'C.1.1.3.3.4.2.5'> 'Part 386' {
                                attribute POIconv : String = "+";
                                attribute Ipoint : Boolean = false;
                                attribute mass : Real = 0.10937700319802389;
                                attribute sigma_mass : Real = 0.28909372274994966;
                                attribute Cx : Real = 42.76658818125725;
                                attribute sigma_Cx : Real = 28.721044428837228;
                                attribute Cy : Real = 45.61534714885056;
                                attribute sigma_Cy : Real = 28.23690002309109;
                                attribute Cz : Real = 81.8830500356853;
                                attribute sigma_Cz : Real = 29.057750463592832;
                                attribute Ixx : Real = 0.13144777401524757;
                                attribute sigma_Ixx : Real = 0.37074144170588635;
                                attribute Iyy : Real = 0.1344541654665131;
                                attribute sigma_Iyy : Real = 0.3723953238821935;
                                attribute Izz : Real = 0.16944041406185276;
                                attribute sigma_Izz : Real = 0.37017423652493897;
                                attribute Ixy : Real = -0.004704860740521314;
                                attribute sigma_Ixy : Real = 0.02351283871158888;
                                attribute Ixz : Real = -0.005551590956860193;
                                attribute sigma_Ixz : Real = 0.022566176940390956;
                                attribute Iyz : Real = -0.004846641111376362;
                                attribute sigma_Iyz : Real = 0.02209918015384651;
                            }
                        }
                        part <'C.1.1.3.3.4.3'> 'Subassembly 115' {
                            attribute POIconv : String = "-";
                            attribute Ipoint : Boolean = false;
                            attribute mass : Real = 0.9395518994564191;
                            attribute sigma_mass : Real = 0.40884026350990615;
                            attribute Cx : Real = -4.043768375100353;
                            attribute sigma_Cx : Real = 33.520377685102986;
                            attribute Cy : Real = -10.875771793517124;
                            attribute sigma_Cy : Real = 24.61298497742668;
                            attribute Cz : Real = 9.094300849646991;
                            attribute sigma_Cz : Real = 38.663531217927414;
                            attribute Ixx : Real = 1358.7004939698836;
                            attribute sigma_Ixx : Real = 2744.760490461251;
                            attribute Iyy : Real = 2146.3873040341336;
                            attribute sigma_Iyy : Real = 4223.923366103853;
                            attribute Izz : Real = 793.4412424532886;
                            attribute sigma_Izz : Real = 1675.3003027852678;
                            attribute Ixy : Real = -43.69194222007221;
                            attribute sigma_Ixy : Real = 387.94067138069454;
                            attribute Ixz : Real = -1034.8226057162199;
                            attribute sigma_Ixz : Real = 2043.7052054056871;
                            attribute Iyz : Real = -57.27464604161261;
                            attribute sigma_Iyz : Real = 507.76661509629076;
                            part <'C.1.1.3.3.4.3.1'> 'Part 387' {
                                attribute POIconv : String = "-";
                                attribute Ipoint : Boolean = false;
                                attribute mass : Real = 0.1324007549379021;
                                attribute sigma_mass : Real = 0.28909372274994966;
                                attribute Cx : Real = -75.64562722109258;
                                attribute sigma_Cx : Real = 28.721044428837228;
                                attribute Cy : Real = -14.837086573243141;
                                attribute sigma_Cy : Real = 28.23690002309109;
                                attribute Cz : Real = -84.6807558555156;
                                attribute sigma_Cz : Real = 29.057750463592832;
                                attribute Ixx : Real = 0.17553472010336704;
                                attribute sigma_Ixx : Real = 0.37074144170588635;
                                attribute Iyy : Real = 0.14803501730536697;
                                attribute sigma_Iyy : Real = 0.3723953238821935;
                                attribute Izz : Real = 0.16591079093823602;
                                attribute sigma_Izz : Real = 0.37017423652493897;
                                attribute Ixy : Real = 0.015232586893970855;
                                attribute sigma_Ixy : Real = 0.02351283871158888;
                                attribute Ixz : Real = -0.0009567312334899193;
                                attribute sigma_Ixz : Real = 0.022566176940390956;
                                attribute Iyz : Real = -0.01238921084133365;
                                attribute sigma_Iyz : Real = 0.02209918015384651;
                            }
                            part <'C.1.1.3.3.4.3.2'> 'Part 388' {
                                attribute POIconv : String = "+";
                                attribute Ipoint : Boolean = false;
                                attribute mass : Real = 0.807151144518517;
                                attribute sigma_mass : Real = 0.28909372274994966;
                                attribute Cx : Real = 7.701417431235313;
                                attribute sigma_Cx : Real = 28.721044428837228;
                                attribute Cy : Real = -10.22597891278565;
                                attribute sigma_Cy : Real = 28.23690002309109;
                                attribute Cz : Real = 24.476659391075373;
                                attribute sigma_Cz : Real = 29.057750463592832;
                                attribute Ixx : Real = 0.8202455337025117;
                                attribute sigma_Ixx : Real = 0.37074144170588635;
                                attribute Iyy : Real = 0.8113282285181346;
                                attribute sigma_Iyy : Real = 0.3723953238821935;
                                attribute Izz : Real = 0.7152272549742393;
                                attribute sigma_Izz : Real = 0.37017423652493897;
                                attribute Ixy : Real = -0.00677213545481405;
                                attribute sigma_Ixy : Real = 0.02351283871158888;
                                attribute Ixz : Real = -0.005947729133492619;
                                attribute sigma_Ixz : Real = 0.022566176940390956;
                                attribute Iyz : Real = 0.011259169536033297;
                                attribute sigma_Iyz : Real = 0.02209918015384651;
                            }
                        }
                        part <'C.1.1.3.3.4.4'> 'Subassembly 116' {
                            attribute POIconv : String = "-";
                            attribute Ipoint : Boolean = false;
                            attribute mass : Real = 1.826766617608024;
                            attribute sigma_mass : Real = 0.5007250159521434;
                            attribute Cx : Real = -60.965228207131254;
                            attribute sigma_Cx : Real = 18.811481108692995;
                            attribute Cy : Real = -39.32343979700054;
                            attribute sigma_Cy : Real = 18.243179220022974;
                            attribute Cz : Real = 36.86647962521003;
                            attribute sigma_Cz : Real = 18.089926203536404;
                            attribute Ixx : Real = 719.4514301428406;
                            attribute sigma_Ixx : Real = 1191.0471392107495;
                            attribute Iyy : Real = 987.7118113685935;
                            attribute sigma_Iyy : Real = 1453.5255256823812;
                            attribute Izz : Real = 1467.870867675783;
                            attribute sigma_Izz : Real = 1785.3215389577033;
                            attribute Ixy : Real = 717.7097490240482;
                            attribute sigma_Ixy : Real = 888.9113403189855;
                            attribute Ixz : Real = 10.291227284686386;
                            attribute sigma_Ixz : Real = 721.612898155165;
                            attribute Iyz : Real = 14.108911033251061;
                            attribute sigma_Iyz : Real = 599.7106902964067;
                            part <'C.1.1.3.3.4.4.1'> 'Part 389' {
                                attribute POIconv : String = "-";
                                attribute Ipoint : Boolean = false;
                                attribute mass : Real = 0.7139046251026447;
                                attribute sigma_mass : Real = 0.28909372274994966;
                                attribute Cx : Real = -87.40574680268764;
                                attribute sigma_Cx : Real = 28.721044428837228;
                                attribute Cy : Real = -17.880180245265365;
                                attribute sigma_Cy : Real = 28.23690002309109;
                                attribute Cz : Real = 39.53604926355183;
                                attribute sigma_Cz : Real = 29.057750463592832;
                                attribute Ixx : Real = 1.0309447711844637;
                                attribute sigma_Ixx : Real = 0.37074144170588635;
                                attribute Iyy : Real = 0.9377386227914168;
                                attribute sigma_Iyy : Real = 0.3723953238821935;
                                attribute Izz : Real = 1.030668584191264;
                                attribute sigma_Izz : Real = 0.37017423652493897;
                                attribute Ixy : Real = -0.004976498780813686;
                                attribute sigma_Ixy : Real = 0.02351283871158888;
                                attribute Ixz : Real = 0.003565080235109526;
                                attribute sigma_Ixz : Real = 0.022566176940390956;
                                attribute Iyz : Real = 0.011396028594465521;
                                attribute sigma_Iyz : Real = 0.02209918015384651;
                            }
                            part <'C.1.1.3.3.4.4.2'> 'Part 390' {
                                attribute POIconv : String = "-";
                                attribute Ipoint : Boolean = false;
                                attribute mass : Real = 0.295551092278678;
                                attribute sigma_mass : Real = 0.28909372274994966;
                                attribute Cx : Real = -33.12367140315473;
                                attribute sigma_Cx : Real = 28.721044428837228;
                                attribute Cy : Real = -65.27239489369094;
                                attribute sigma_Cy : Real = 28.23690002309109;
                                attribute Cz : Real = 51.6985178925097;
                                attribute sigma_Cz : Real = 29.057750463592832;
                                attribute Ixx : Real = 0.37477406366690624;
                                attribute sigma_Ixx : Real = 0.37074144170588635;
                                attribute Iyy : Real = 0.39944932687267626;
                                attribute sigma_Iyy : Real = 0.3723953238821935;
                                attribute Izz : Real = 0.31260582175360674;
                                attribute sigma_Izz : Real = 0.37017423652493897;
                                attribute Ixy : Real = -0.014740451163008633;
                                attribute sigma_Ixy : Real = 0.02351283871158888;
                                attribute Ixz : Real = 0.006089068610954781;
                                attribute sigma_Ixz : Real = 0.022566176940390956;
                                attribute Iyz : Real = -0.00154250272482289;
                                attribute sigma_Iyz : Real = 0.02209918015384651;
                            }
                            part <'C.1.1.3.3.4.4.3'> 'Part 391' {
                                attribute POIconv : String = "-";
                                attribute Ipoint : Boolean = false;
                                attribute mass : Real = 0.817310900226701;
                                attribute sigma_mass : Real = 0.28909372274994966;
                                attribute Cx : Real = -47.937864949926734;
                                attribute sigma_Cx : Real = 28.721044428837228;
                                attribute Cy : Real = -48.670189175754786;
                                attribute sigma_Cy : Real = 28.23690002309109;
                                attribute Cz : Real = 29.171191062778234;
                                attribute sigma_Cz : Real = 29.057750463592832;
                                attribute Ixx : Real = 0.8674163361629236;
                                attribute sigma_Ixx : Real = 0.37074144170588635;
                                attribute Iyy : Real = 0.9735490142799794;
                                attribute sigma_Iyy : Real = 0.3723953238821935;
                                attribute Izz : Real = 0.9580039967475;
                                attribute sigma_Izz : Real = 0.37017423652493897;
                                attribute Ixy : Real = -0.07595666677287743;
                                attribute sigma_Ixy : Real = 0.02351283871158888;
                                attribute Ixz : Real = 0.0028398898663351073;
                                attribute sigma_Ixz : Real = 0.022566176940390956;
                                attribute Iyz : Real = 0.0013683141854874232;
                                attribute sigma_Iyz : Real = 0.02209918015384651;
                            }
                        }
                        part <'C.1.1.3.3.4.5'> 'Subassembly 117' {
                            attribute POIconv : String = "-";
                            attribute Ipoint : Boolean = false;
                            attribute mass : Real = 2.1328587533188985;
                            attribute sigma_mass : Real = 0.6464332159373649;
                            attribute Cx : Real = 30.79344601876602;
                            attribute sigma_Cx : Real = 27.253014615384494;
                            attribute Cy : Real = -35.17112189050362;
                            attribute sigma_Cy : Real = 26.793509296571578;
                            attribute Cz : Real = -27.48028389403998;
                            attribute sigma_Cz : Real = 22.360653065107744;
                            attribute Ixx : Real = 11587.828266891858;
                            attribute sigma_Ixx : Real = 7415.555639827802;
                            attribute Iyy : Real = 13671.84039495386;
                            attribute sigma_Iyy : Real = 7790.484889733644;
                            attribute Izz : Real = 15562.378478372571;
                            attribute sigma_Izz : Real = 10790.418852802424;
                            attribute Ixy : Real = -2353.2801428915195;
                            attribute sigma_Ixy : Real = 5316.368658955246;
                            attribute Ixz : Real = -3859.648289417881;
                            attribute sigma_Ixz : Real = 3123.2131325927685;
                            attribute Iyz : Real = -386.76179209453153;
                            attribute sigma_Iyz : Real = 2410.1892784988277;
                            part <'C.1.1.3.3.4.5.1'> 'Part 392' {
                                attribute POIconv : String = "+";
                                attribute Ipoint : Boolean = false;
                                attribute mass : Real = 0.12312743554264308;
                                attribute sigma_mass : Real = 0.28909372274994966;
                                attribute Cx : Real = -13.61965243704617;
                                attribute sigma_Cx : Real = 28.721044428837228;
                                attribute Cy : Real = -58.821651339530945;
                                attribute sigma_Cy : Real = 28.23690002309109;
                                attribute Cz : Real = 66.03744337335229;
                                attribute sigma_Cz : Real = 29.057750463592832;
                                attribute Ixx : Real = 0.11273701249619117;
                                attribute sigma_Ixx : Real = 0.37074144170588635;
                                attribute Iyy : Real = 0.1339467200102361;
                                attribute sigma_Iyy : Real = 0.3723953238821935;
                                attribute Izz : Real = 0.12687587134572648;
                                attribute sigma_Izz : Real = 0.37017423652493897;
                                attribute Ixy : Real = -0.0019741660899585184;
                                attribute sigma_Ixy : Real = 0.02351283871158888;
                                attribute Ixz : Real = -0.0029936174079168154;
                                attribute sigma_Ixz : Real = 0.022566176940390956;
                                attribute Iyz : Real = -0.0028560964563378696;
                                attribute sigma_Iyz : Real = 0.02209918015384651;
                            }
                            part <'C.1.1.3.3.4.5.2'> 'Part 393' {
                                attribute POIconv : String = "-";
                                attribute Ipoint : Boolean = false;
                                attribute mass : Real = 0.6775872212552931;
                                attribute sigma_mass : Real = 0.28909372274994966;
                                attribute Cx : Real = 91.47244468331337;
                                attribute sigma_Cx : Real = 28.721044428837228;
                                attribute Cy : Real = -54.22576982527971;
                                attribute sigma_Cy : Real = 28.23690002309109;
                                attribute Cz : Real = 22.372767562046647;
                                attribute sigma_Cz : Real = 29.057750463592832;
                                attribute Ixx : Real = 0.9057019679536699;
                                attribute sigma_Ixx : Real = 0.37074144170588635;
                                attribute Iyy : Real = 0.9133459686867721;
                                attribute sigma_Iyy : Real = 0.3723953238821935;
                                attribute Izz : Real = 0.8425530044257208;
                                attribute sigma_Izz : Real = 0.37017423652493897;
                                attribute Ixy : Real = 0.036452692810385504;
                                attribute sigma_Ixy : Real = 0.02351283871158888;
                                attribute Ixz : Real = 0.008803544887606823;
                                attribute sigma_Ixz : Real = 0.022566176940390956;
                                attribute Iyz : Real = 0.007259635117751276;
                                attribute sigma_Iyz : Real = 0.02209918015384651;
                            }
                            part <'C.1.1.3.3.4.5.3'> 'Part 394' {
                                attribute POIconv : String = "-";
                                attribute Ipoint : Boolean = false;
                                attribute mass : Real = 0.0985529834907502;
                                attribute sigma_mass : Real = 0.28909372274994966;
                                attribute Cx : Real = -87.99872137606144;
                                attribute sigma_Cx : Real = 28.721044428837228;
                                attribute Cy : Real = 89.85906043089926;
                                attribute sigma_Cy : Real = 28.23690002309109;
                                attribute Cz : Real = -32.657551718875766;
                                attribute sigma_Cz : Real = 29.057750463592832;
                                attribute Ixx : Real = 0.13685297609509237;
                                attribute sigma_Ixx : Real = 0.37074144170588635;
                                attribute Iyy : Real = 0.11839772132804591;
                                attribute sigma_Iyy : Real = 0.3723953238821935;
                                attribute Izz : Real = 0.12420754512393485;
                                attribute sigma_Izz : Real = 0.37017423652493897;
                                attribute Ixy : Real = -0.007056821975560023;
                                attribute sigma_Ixy : Real = 0.02351283871158888;
                                attribute Ixz : Real = 0.0011114850167873698;
                                attribute sigma_Ixz : Real = 0.022566176940390956;
                                attribute Iyz : Real = 0.0001008320147939265;
                                attribute sigma_Iyz : Real = 0.02209918015384651;
                            }
                            part <'C.1.1.3.3.4.5.4'> 'Part 395' {
                                attribute POIconv : String = "+";
                                attribute Ipoint : Boolean = false;
                                attribute mass : Real = 0.8121832358497195;
                                attribute sigma_mass : Real = 0.28909372274994966;
                                attribute Cx : Real = -30.786744970828295;
                                attribute sigma_Cx : Real = 28.721044428837228;
                                attribute Cy : Real = -77.6023690123111;
                                attribute sigma_Cy : Real = 28.23690002309109;
                                attribute Cz : Real = -77.66235861927271;
                                attribute sigma_Cz : Real = 29.057750463592832;
                                attribute Ixx : Real = 1.0780461154567795;
                                attribute sigma_Ixx : Real = 0.37074144170588635;
                                attribute Iyy : Real = 1.078477733319452;
                                attribute sigma_Iyy : Real = 0.3723953238821935;
                                attribute Izz : Real = 1.1877220575344243;
                                attribute sigma_Izz : Real = 0.37017423652493897;
                                attribute Ixy : Real = 0.014635663293714646;
                                attribute sigma_Ixy : Real = 0.02351283871158888;
                                attribute Ixz : Real = 0.08743197372177619;
                                attribute sigma_Ixz : Real = 0.022566176940390956;
                                attribute Iyz : Real = -0.03052663406862784;
                                attribute sigma_Iyz : Real = 0.02209918015384651;
                            }
                            part <'C.1.1.3.3.4.5.5'> 'Part 396' {
                                attribute POIconv : String = "+";
                                attribute Ipoint : Boolean = false;
                                attribute mass : Real = 0.4214078771804925;
                                attribute sigma_mass : Real = 0.28909372274994966;
                                attribute Cx : Real = 92.66907656565309;
                                attribute sigma_Cx : Real = 28.721044428837228;
                                attribute Cy : Real = 54.915151139721274;
                                attribute sigma_Cy : Real = 28.23690002309109;
                                attribute Cz : Real = -37.03661574982107;
                                attribute sigma_Cz : Real = 29.057750463592832;
                                attribute Ixx : Real = 0.6136963861147711;
                                attribute sigma_Ixx : Real = 0.37074144170588635;
                                attribute Iyy : Real = 0.6108861521766994;
                                attribute sigma_Iyy : Real = 0.3723953238821935;
                                attribute Izz : Real = 0.617636003029593;
                                attribute sigma_Izz : Real = 0.37017423652493897;
                                attribute Ixy : Real = 0.009244017657946283;
                                attribute sigma_Ixy : Real = 0.02351283871158888;
                                attribute Ixz : Real = -0.009184020189321615;
                                attribute sigma_Ixz : Real = 0.022566176940390956;
                                attribute Iyz : Real = 0.0013082082895758164;
                                attribute sigma_Iyz : Real = 0.02209918015384651;
                            }
                        }
                    }
                }
                part <'C.1.1.3.4'> 'Subsystem 9' {
                    attribute POIconv : String = "-";
                    attribute Ipoint : Boolean = false;
                    attribute mass : Real = 26.398134766193575;
                    attribute sigma_mass : Real = 2.2578941544144424;
                    attribute Cx : Real = 19.02563671968412;
                    attribute sigma_Cx : Real = 6.953561643286083;
                    attribute Cy : Real = 4.3948100620363295;
                    attribute sigma_Cy : Real = 6.397538494221726;
                    attribute Cz : Real = 4.026449809467887;
                    attribute sigma_Cz : Real = 6.800136934210632;
                    attribute Ixx : Real = 154675.84042991034;
                    attribute sigma_Ixx : Real = 25289.83279447582;
                    attribute Iyy : Real = 139341.51626712887;
                    attribute sigma_Iyy : Real = 27687.91722386467;
                    attribute Izz : Real = 143446.70257157166;
                    attribute sigma_Izz : Real = 26031.285911843945;
                    attribute Ixy : Real = 17788.30716934082;
                    attribute sigma_Ixy : Real = 11235.680134346483;
                    attribute Ixz : Real = 5018.182656841629;
                    attribute sigma_Ixz : Real = 12470.61096683762;
                    attribute Iyz : Real = 6853.650907745424;
                    attribute sigma_Iyz : Real = 11746.200468563009;
                    part <'C.1.1.3.4.1'> 'Assembly 32' {
                        attribute POIconv : String = "-";
                        attribute Ipoint : Boolean = false;
                        attribute mass : Real = 6.813372346870368;
                        attribute sigma_mass : Real = 0.958815407608614;
                        attribute Cx : Real = 36.89906873326529;
                        attribute sigma_Cx : Real = 13.025432540773258;
                        attribute Cy : Real = -5.086034163932607;
                        attribute sigma_Cy : Real = 11.513838482448643;
                        attribute Cz : Real = 18.541415155574764;
                        attribute sigma_Cz : Real = 12.505285320225463;
                        attribute Ixx : Real = 33478.937626943676;
                        attribute sigma_Ixx : Real = 10509.991514978872;
                        attribute Iyy : Real = 30161.532058760036;
                        attribute sigma_Iyy : Real = 13297.801208025254;
                        attribute Izz : Real = 29028.777510262204;
                        attribute sigma_Izz : Real = 12448.959813096639;
                        attribute Ixy : Real = -3162.522338562925;
                        attribute sigma_Ixy : Real = 4887.68205512199;
                        attribute Ixz : Real = 522.1102635281422;
                        attribute sigma_Ixz : Real = 5955.855708031771;
                        attribute Iyz : Real = 10806.121982450466;
                        attribute sigma_Iyz : Real = 4996.107954288549;
                        part <'C.1.1.3.4.1.1'> 'Subassembly 118' {
                            attribute POIconv : String = "-";
                            attribute Ipoint : Boolean = false;
                            attribute mass : Real = 0.6156473704546225;
                            attribute sigma_mass : Real = 0.40884026350990615;
                            attribute Cx : Real = 69.56138541866616;
                            attribute sigma_Cx : Real = 79.63659284605107;
                            attribute Cy : Real = 10.596774839583333;
                            attribute sigma_Cy : Real = 29.573191162281805;
                            attribute Cz : Real = -28.960459662449125;
                            attribute sigma_Cz : Real = 39.93770659797043;
                            attribute Ixx : Real = 106.89245932913391;
                            attribute sigma_Ixx : Real = 1249.4582140337093;
                            attribute Iyy : Real = 714.8283168253002;
                            attribute sigma_Iyy : Real = 8372.638410362213;
                            attribute Izz : Real = 639.2117930558007;
                            attribute sigma_Izz : Real = 7486.571787760993;
                            attribute Ixy : Real = 97.39775773283766;
                            attribute sigma_Ixy : Real = 1151.6371706958384;
                            attribute Ixz : Real = -237.98743900937367;
                            attribute sigma_Ixz : Real = 2792.8595073155243;
                            attribute Iyz : Real = 37.1396321221986;
                            attribute sigma_Iyz : Real = 440.291436777839;
                            part <'C.1.1.3.4.1.1.1'> 'Part 397' {
                                attribute POIconv : String = "-";
                                attribute Ipoint : Boolean = false;
                                attribute mass : Real = 0.02372396921156906;
                                attribute sigma_mass : Real = 0.28909372274994966;
                                attribute Cx : Real = -89.363680081442;
                                attribute sigma_Cx : Real = 28.721044428837228;
                                attribute Cy : Real = 35.44211769476533;
                                attribute sigma_Cy : Real = 28.23690002309109;
                                attribute Cz : Real = -89.64144736528397;
                                attribute sigma_Cz : Real = 29.057750463592832;
                                attribute Ixx : Real = 0.033405870504254906;
                                attribute sigma_Ixx : Real = 0.37074144170588635;
                                attribute Iyy : Real = 0.02913846666516851;
                                attribute sigma_Iyy : Real = 0.3723953238821935;
                                attribute Izz : Real = 0.03283746375896864;
                                attribute sigma_Izz : Real = 0.37017423652493897;
                                attribute Ixy : Real = 0.0005528425961646448;
                                attribute sigma_Ixy : Real = 0.02351283871158888;
                                attribute Ixz : Real = 3.479115362449733e-05;
                                attribute sigma_Ixz : Real = 0.022566176940390956;
                                attribute Iyz : Real = 0.0013328242043395139;
                                attribute sigma_Iyz : Real = 0.02209918015384651;
                            }
                            part <'C.1.1.3.4.1.1.2'> 'Part 398' {
                                attribute POIconv : String = "+";
                                attribute Ipoint : Boolean = false;
                                attribute mass : Real = 0.5919234012430534;
                                attribute sigma_mass : Real = 0.28909372274994966;
                                attribute Cx : Real = 75.93101593665779;
                                attribute sigma_Cx : Real = 28.721044428837228;
                                attribute Cy : Real = 9.600986959412694;
                                attribute sigma_Cy : Real = 28.23690002309109;
                                attribute Cz : Real = -26.528398552909493;
                                attribute sigma_Cz : Real = 29.057750463592832;
                                attribute Ixx : Real = 0.770352850091484;
                                attribute sigma_Ixx : Real = 0.37074144170588635;
                                attribute Iyy : Real = 0.7259125163010768;
                                attribute sigma_Iyy : Real = 0.3723953238821935;
                                attribute Izz : Real = 0.7313072816393326;
                                attribute sigma_Izz : Real = 0.37017423652493897;
                                attribute Ixy : Real = 0.032472403891672996;
                                attribute sigma_Ixy : Real = 0.02351283871158888;
                                attribute Ixz : Real = 0.0302403569417911;
                                attribute sigma_Ixz : Real = 0.022566176940390956;
                                attribute Iyz : Real = 0.06243446399647014;
                                attribute sigma_Iyz : Real = 0.02209918015384651;
                            }
                        }
                        part <'C.1.1.3.4.1.2'> 'Subassembly 119' {
                            attribute POIconv : String = "-";
                            attribute Ipoint : Boolean = false;
                            attribute mass : Real = 3.3447851882535033;
                            attribute sigma_mass : Real = 0.6464332159373649;
                            attribute Cx : Real = 37.78810971883872;
                            attribute sigma_Cx : Real = 14.976044772869844;
                            attribute Cy : Real = 31.397939128856756;
                            attribute sigma_Cy : Real = 13.843347446028957;
                            attribute Cz : Real = -10.81543364311996;
                            attribute sigma_Cz : Real = 17.3111872135405;
                            attribute Ixx : Real = 6787.448211073657;
                            attribute sigma_Ixx : Real = 4475.6400903167;
                            attribute Iyy : Real = 8103.972607407806;
                            attribute sigma_Iyy : Real = 5102.675202846645;
                            attribute Izz : Real = 2582.7343318147687;
                            attribute sigma_Izz : Real = 2545.5440649171287;
                            attribute Ixy : Real = -252.41909767454518;
                            attribute sigma_Ixy : Real = 1198.5509578248145;
                            attribute Ixz : Real = 1805.4323330267075;
                            attribute sigma_Ixz : Real = 2376.3837128668924;
                            attribute Iyz : Real = 809.2370862763755;
                            attribute sigma_Iyz : Real = 1869.5411697655481;
                            part <'C.1.1.3.4.1.2.1'> 'Part 399' {
                                attribute POIconv : String = "+";
                                attribute Ipoint : Boolean = false;
                                attribute mass : Real = 0.523581439486472;
                                attribute sigma_mass : Real = 0.28909372274994966;
                                attribute Cx : Real = 50.42078816331923;
                                attribute sigma_Cx : Real = 28.721044428837228;
                                attribute Cy : Real = 17.9677443113178;
                                attribute sigma_Cy : Real = 28.23690002309109;
                                attribute Cz : Real = -72.7757129818201;
                                attribute sigma_Cz : Real = 29.057750463592832;
                                attribute Ixx : Real = 0.6823414106800034;
                                attribute sigma_Ixx : Real = 0.37074144170588635;
                                attribute Iyy : Real = 0.6193806633975562;
                                attribute sigma_Iyy : Real = 0.3723953238821935;
                                attribute Izz : Real = 0.7157345643301456;
                                attribute sigma_Izz : Real = 0.37017423652493897;
                                attribute Ixy : Real = 0.009529132218344998;
                                attribute sigma_Ixy : Real = 0.02351283871158888;
                                attribute Ixz : Real = 0.00633316435621075;
                                attribute sigma_Ixz : Real = 0.022566176940390956;
                                attribute Iyz : Real = 0.03633333192775019;
                                attribute sigma_Iyz : Real = 0.02209918015384651;
                            }
                            part <'C.1.1.3.4.1.2.2'> 'Part 400' {
                                attribute POIconv : String = "-";
                                attribute Ipoint : Boolean = false;
                                attribute mass : Real = 0.8158563330559991;
                                attribute sigma_mass : Real = 0.28909372274994966;
                                attribute Cx : Real = 24.250193033367395;
                                attribute sigma_Cx : Real = 28.721044428837228;
                                attribute Cy : Real = 15.537180751562119;
                                attribute sigma_Cy : Real = 28.23690002309109;
                                attribute Cz : Real = 39.37647631391883;
                                attribute sigma_Cz : Real = 29.057750463592832;
                                attribute Ixx : Real = 1.0297092509290482;
                                attribute sigma_Ixx : Real = 0.37074144170588635;
                                attribute Iyy : Real = 0.9790000251639716;
                                attribute sigma_Iyy : Real = 0.3723953238821935;
                                attribute Izz : Real = 1.1612455427057145;
                                attribute sigma_Izz : Real = 0.37017423652493897;
                                attribute Ixy : Real = -0.008917556040880119;
                                attribute sigma_Ixy : Real = 0.02351283871158888;
                                attribute Ixz : Real = 0.0040147945059103;
                                attribute sigma_Ixz : Real = 0.022566176940390956;
                                attribute Iyz : Real = 0.04399860010379668;
                                attribute sigma_Iyz : Real = 0.02209918015384651;
                            }
                            part <'C.1.1.3.4.1.2.3'> 'Part 401' {
                                attribute POIconv : String = "-";
                                attribute Ipoint : Boolean = false;
                                attribute mass : Real = 0.2222717572071124;
                                attribute sigma_mass : Real = 0.28909372274994966;
                                attribute Cx : Real = -13.808929780498147;
                                attribute sigma_Cx : Real = 28.721044428837228;
                                attribute Cy : Real = 20.651404466480017;
                                attribute sigma_Cy : Real = 28.23690002309109;
                                attribute Cz : Real = 72.60958417318761;
                                attribute sigma_Cz : Real = 29.057750463592832;
                                attribute Ixx : Real = 0.2632585799068577;
                                attribute sigma_Ixx : Real = 0.37074144170588635;
                                attribute Iyy : Real = 0.2820702391516388;
                                attribute sigma_Iyy : Real = 0.3723953238821935;
                                attribute Izz : Real = 0.28973382773890394;
                                attribute sigma_Izz : Real = 0.37017423652493897;
                                attribute Ixy : Real = 0.02805320581064509;
                                attribute sigma_Ixy : Real = 0.02351283871158888;
                                attribute Ixz : Real = -0.006327180711395032;
                                attribute sigma_Ixz : Real = 0.022566176940390956;
                                attribute Iyz : Real = -0.02744353798096605;
                                attribute sigma_Iyz : Real = 0.02209918015384651;
                            }
                            part <'C.1.1.3.4.1.2.4'> 'Part 402' {
                                attribute POIconv : String = "-";
                                attribute Ipoint : Boolean = false;
                                attribute mass : Real = 0.9888013822126668;
                                attribute sigma_mass : Real = 0.28909372274994966;
                                attribute Cx : Real = 25.683790165930986;
                                attribute sigma_Cx : Real = 28.721044428837228;
                                attribute Cy : Real = 47.29431327432394;
                                attribute sigma_Cy : Real = 28.23690002309109;
                                attribute Cz : Real = -33.63154106773436;
                                attribute sigma_Cz : Real = 29.057750463592832;
                                attribute Ixx : Real = 1.0904188596546653;
                                attribute sigma_Ixx : Real = 0.37074144170588635;
                                attribute Iyy : Real = 1.0730393353960321;
                                attribute sigma_Iyy : Real = 0.3723953238821935;
                                attribute Izz : Real = 1.2771831703843701;
                                attribute sigma_Izz : Real = 0.37017423652493897;
                                attribute Ixy : Real = -0.031710692012962435;
                                attribute sigma_Ixy : Real = 0.02351283871158888;
                                attribute Ixz : Real = -0.015609301703289464;
                                attribute sigma_Ixz : Real = 0.022566176940390956;
                                attribute Iyz : Real = -0.018873175179580544;
                                attribute sigma_Iyz : Real = 0.02209918015384651;
                            }
                            part <'C.1.1.3.4.1.2.5'> 'Part 403' {
                                attribute POIconv : String = "+";
                                attribute Ipoint : Boolean = false;
                                attribute mass : Real = 0.794274276291253;
                                attribute sigma_mass : Real = 0.28909372274994966;
                                attribute Cx : Real = 72.8743418585509;
                                attribute sigma_Cx : Real = 28.721044428837228;
                                attribute Cy : Real = 39.760535676032305;
                                attribute sigma_Cy : Real = 28.23690002309109;
                                attribute Cz : Real = -16.46910044364631;
                                attribute sigma_Cz : Real = 29.057750463592832;
                                attribute Ixx : Real = 1.141200087811568;
                                attribute sigma_Ixx : Real = 0.37074144170588635;
                                attribute Iyy : Real = 1.0508460947210099;
                                attribute sigma_Iyy : Real = 0.3723953238821935;
                                attribute Izz : Real = 1.045731743840879;
                                attribute sigma_Izz : Real = 0.37017423652493897;
                                attribute Ixy : Real = 0.008551433170079208;
                                attribute sigma_Ixy : Real = 0.02351283871158888;
                                attribute Ixz : Real = -0.025862813057664028;
                                attribute sigma_Ixz : Real = 0.022566176940390956;
                                attribute Iyz : Real = -0.02199402020909095;
                                attribute sigma_Iyz : Real = 0.02209918015384651;
                            }
                        }
                        part <'C.1.1.3.4.1.3'> 'Subassembly 120' {
                            attribute POIconv : String = "-";
                            attribute Ipoint : Boolean = false;
                            attribute mass : Real = 2.8529397881622423;
                            attribute sigma_mass : Real = 0.5781874454998993;
                            attribute Cx : Real = 28.8084246206925;
                            attribute sigma_Cx : Real = 18.42323571399097;
                            attribute Cy : Real = -51.24408283678674;
                            attribute sigma_Cy : Real = 17.060645783245878;
                            attribute Cz : Real = 63.20999101820902;
                            attribute sigma_Cz : Real = 15.270757301984586;
                            attribute Ixx : Real = 5938.424960333336;
                            attribute sigma_Ixx : Real = 4003.3591966858385;
                            attribute Iyy : Real = 10532.348461177196;
                            attribute sigma_Iyy : Real = 5827.956559041592;
                            attribute Izz : Real = 14278.677832502668;
                            attribute sigma_Izz : Real = 6847.385011939453;
                            attribute Ixy : Real = -1518.2274643813173;
                            attribute sigma_Ixy : Real = 3272.3564222419886;
                            attribute Ixz : Real = -3118.8671027463656;
                            attribute sigma_Ixz : Real = 2776.3803593993075;
                            attribute Iyz : Real = 36.43162202725455;
                            attribute sigma_Iyz : Real = 1816.833646965791;
                            part <'C.1.1.3.4.1.3.1'> 'Part 404' {
                                attribute POIconv : String = "-";
                                attribute Ipoint : Boolean = false;
                                attribute mass : Real = 0.9421622136284131;
                                attribute sigma_mass : Real = 0.28909372274994966;
                                attribute Cx : Real = -47.65594904311001;
                                attribute sigma_Cx : Real = 28.721044428837228;
                                attribute Cy : Real = -53.82715044543147;
                                attribute sigma_Cy : Real = 28.23690002309109;
                                attribute Cz : Real = 36.67666702531278;
                                attribute sigma_Cz : Real = 29.057750463592832;
                                attribute Ixx : Real = 1.0437591953727015;
                                attribute sigma_Ixx : Real = 0.37074144170588635;
                                attribute Iyy : Real = 0.9793043709895538;
                                attribute sigma_Iyy : Real = 0.3723953238821935;
                                attribute Izz : Real = 0.9745845104575208;
                                attribute sigma_Izz : Real = 0.37017423652493897;
                                attribute Ixy : Real = 0.035738875647215035;
                                attribute sigma_Ixy : Real = 0.02351283871158888;
                                attribute Ixz : Real = 0.021095684951311106;
                                attribute sigma_Ixz : Real = 0.022566176940390956;
                                attribute Iyz : Real = -0.045095875833028244;
                                attribute sigma_Iyz : Real = 0.02209918015384651;
                            }
                            part <'C.1.1.3.4.1.3.2'> 'Part 405' {
                                attribute POIconv : String = "-";
                                attribute Ipoint : Boolean = false;
                                attribute mass : Real = 0.648505211758893;
                                attribute sigma_mass : Real = 0.28909372274994966;
                                attribute Cx : Real = 31.843072921037674;
                                attribute sigma_Cx : Real = 28.721044428837228;
                                attribute Cy : Real = -76.02740949951112;
                                attribute sigma_Cy : Real = 28.23690002309109;
                                attribute Cz : Real = 67.62630278244615;
                                attribute sigma_Cz : Real = 29.057750463592832;
                                attribute Ixx : Real = 0.9037261117087232;
                                attribute sigma_Ixx : Real = 0.37074144170588635;
                                attribute Iyy : Real = 0.8829578768385948;
                                attribute sigma_Iyy : Real = 0.3723953238821935;
                                attribute Izz : Real = 0.8634103312708705;
                                attribute sigma_Izz : Real = 0.37017423652493897;
                                attribute Ixy : Real = -0.034788890906275086;
                                attribute sigma_Ixy : Real = 0.02351283871158888;
                                attribute Ixz : Real = 0.007737350664627605;
                                attribute sigma_Ixz : Real = 0.022566176940390956;
                                attribute Iyz : Real = -0.006804706602077034;
                                attribute sigma_Iyz : Real = 0.02209918015384651;
                            }
                            part <'C.1.1.3.4.1.3.3'> 'Part 406' {
                                attribute POIconv : String = "+";
                                attribute Ipoint : Boolean = false;
                                attribute mass : Real = 0.6997341790245846;
                                attribute sigma_mass : Real = 0.28909372274994966;
                                attribute Cx : Real = 79.95043797418475;
                                attribute sigma_Cx : Real = 28.721044428837228;
                                attribute Cy : Real = -88.08560236357152;
                                attribute sigma_Cy : Real = 28.23690002309109;
                                attribute Cz : Real = 85.12953044846654;
                                attribute sigma_Cz : Real = 29.057750463592832;
                                attribute Ixx : Real = 0.9176902665123767;
                                attribute sigma_Ixx : Real = 0.37074144170588635;
                                attribute Iyy : Real = 0.8563765098178954;
                                attribute sigma_Iyy : Real = 0.3723953238821935;
                                attribute Izz : Real = 0.9557048970472372;
                                attribute sigma_Izz : Real = 0.37017423652493897;
                                attribute Ixy : Real = 0.04706473445192353;
                                attribute sigma_Ixy : Real = 0.02351283871158888;
                                attribute Ixz : Real = -0.03542613242964024;
                                attribute sigma_Ixz : Real = 0.022566176940390956;
                                attribute Iyz : Real = -0.042300210842502545;
                                attribute sigma_Iyz : Real = 0.02209918015384651;
                            }
                            part <'C.1.1.3.4.1.3.4'> 'Part 407' {
                                attribute POIconv : String = "-";
                                attribute Ipoint : Boolean = false;
                                attribute mass : Real = 0.5625381837503519;
                                attribute sigma_mass : Real = 0.28909372274994966;
                                attribute Cx : Real = 89.76080897264183;
                                attribute sigma_Cx : Real = 28.721044428837228;
                                attribute Cy : Real = 27.479560999199748;
                                attribute sigma_Cy : Real = 28.23690002309109;
                                attribute Cz : Real = 75.29244753532112;
                                attribute sigma_Cz : Real = 29.057750463592832;
                                attribute Ixx : Real = 0.6565068204623983;
                                attribute sigma_Ixx : Real = 0.37074144170588635;
                                attribute Iyy : Real = 0.6586151501643953;
                                attribute sigma_Iyy : Real = 0.3723953238821935;
                                attribute Izz : Real = 0.5456336650326229;
                                attribute sigma_Izz : Real = 0.37017423652493897;
                                attribute Ixy : Real = 0.010321119441103366;
                                attribute sigma_Ixy : Real = 0.02351283871158888;
                                attribute Ixz : Real = -0.03817678724386985;
                                attribute sigma_Ixz : Real = 0.022566176940390956;
                                attribute Iyz : Real = 0.03758965539000718;
                                attribute sigma_Iyz : Real = 0.02209918015384651;
                            }
                        }
                    }
                    part <'C.1.1.3.4.2'> 'Assembly 33' {
                        attribute POIconv : String = "-";
                        attribute Ipoint : Boolean = false;
                        attribute mass : Real = 3.4001490504173564;
                        attribute sigma_mass : Real = 0.958815407608614;
                        attribute Cx : Real = -17.824276138959252;
                        attribute sigma_Cx : Real = 21.71880624863584;
                        attribute Cy : Real = 5.37651894045035;
                        attribute sigma_Cy : Real = 18.448412777827773;
                        attribute Cz : Real = -12.188308985490071;
                        attribute sigma_Cz : Real = 17.41610442735712;
                        attribute Ixx : Real = 15873.74444631826;
                        attribute sigma_Ixx : Real = 7225.264910552807;
                        attribute Iyy : Real = 14725.82998821234;
                        attribute sigma_Iyy : Real = 9289.192514990948;
                        attribute Izz : Real = 18968.874098263266;
                        attribute sigma_Izz : Real = 10816.274954753544;
                        attribute Ixy : Real = 1897.7628870701028;
                        attribute sigma_Ixy : Real = 4795.73718939001;
                        attribute Ixz : Real = 3607.216036685362;
                        attribute sigma_Ixz : Real = 3664.666923741506;
                        attribute Iyz : Real = -1484.7689885899185;
                        attribute sigma_Iyz : Real = 3313.874424695649;
                        part <'C.1.1.3.4.2.1'> 'Subassembly 121' {
                            attribute POIconv : String = "-";
                            attribute Ipoint : Boolean = false;
                            attribute mass : Real = 2.2305032982409467;
                            attribute sigma_mass : Real = 0.6464332159373649;
                            attribute Cx : Real = 2.374100580508956;
                            attribute sigma_Cx : Real = 19.54214192046842;
                            attribute Cy : Real = 8.079367108098323;
                            attribute sigma_Cy : Real = 20.684341029399114;
                            attribute Cz : Real = -16.666141844311653;
                            attribute sigma_Cz : Real = 21.584899293566714;
                            attribute Ixx : Real = 11521.1186064581;
                            attribute sigma_Ixx : Real = 6001.585965587111;
                            attribute Iyy : Real = 8961.86763063373;
                            attribute sigma_Iyy : Real = 5182.236746279183;
                            attribute Izz : Real = 10849.901535766652;
                            attribute sigma_Izz : Real = 5466.525433076525;
                            attribute Ixy : Real = 3039.1805605772447;
                            attribute sigma_Ixy : Real = 2413.995400516705;
                            attribute Ixz : Real = 3220.908156853319;
                            attribute sigma_Ixz : Real = 2409.0452265670024;
                            attribute Iyz : Real = -612.8942172778757;
                            attribute sigma_Iyz : Real = 2870.373167899775;
                            part <'C.1.1.3.4.2.1.1'> 'Part 408' {
                                attribute POIconv : String = "+";
                                attribute Ipoint : Boolean = false;
                                attribute mass : Real = 0.18278025591745972;
                                attribute sigma_mass : Real = 0.28909372274994966;
                                attribute Cx : Real = 55.44453551992774;
                                attribute sigma_Cx : Real = 28.721044428837228;
                                attribute Cy : Real = -0.27556465938687325;
                                attribute sigma_Cy : Real = 28.23690002309109;
                                attribute Cz : Real = -70.84898184984922;
                                attribute sigma_Cz : Real = 29.057750463592832;
                                attribute Ixx : Real = 0.2230402212027222;
                                attribute sigma_Ixx : Real = 0.37074144170588635;
                                attribute Iyy : Real = 0.21958040602385492;
                                attribute sigma_Iyy : Real = 0.3723953238821935;
                                attribute Izz : Real = 0.21344178653409862;
                                attribute sigma_Izz : Real = 0.37017423652493897;
                                attribute Ixy : Real = 0.021819800609497612;
                                attribute sigma_Ixy : Real = 0.02351283871158888;
                                attribute Ixz : Real = 0.0008911287761991166;
                                attribute sigma_Ixz : Real = 0.022566176940390956;
                                attribute Iyz : Real = -0.0186394999023912;
                                attribute sigma_Iyz : Real = 0.02209918015384651;
                            }
                            part <'C.1.1.3.4.2.1.2'> 'Part 409' {
                                attribute POIconv : String = "-";
                                attribute Ipoint : Boolean = false;
                                attribute mass : Real = 0.43897415247443133;
                                attribute sigma_mass : Real = 0.28909372274994966;
                                attribute Cx : Real = -18.61683363094926;
                                attribute sigma_Cx : Real = 28.721044428837228;
                                attribute Cy : Real = 72.86121970973909;
                                attribute sigma_Cy : Real = 28.23690002309109;
                                attribute Cz : Real = 23.037515114992857;
                                attribute sigma_Cz : Real = 29.057750463592832;
                                attribute Ixx : Real = 0.44605191823287443;
                                attribute sigma_Ixx : Real = 0.37074144170588635;
                                attribute Iyy : Real = 0.423119749996979;
                                attribute sigma_Iyy : Real = 0.3723953238821935;
                                attribute Izz : Real = 0.4591348811002982;
                                attribute sigma_Izz : Real = 0.37017423652493897;
                                attribute Ixy : Real = -0.009507339906636107;
                                attribute sigma_Ixy : Real = 0.02351283871158888;
                                attribute Ixz : Real = 0.016389828073156927;
                                attribute sigma_Ixz : Real = 0.022566176940390956;
                                attribute Iyz : Real = -0.005493112804234082;
                                attribute sigma_Iyz : Real = 0.02209918015384651;
                            }
                            part <'C.1.1.3.4.2.1.3'> 'Part 410' {
                                attribute POIconv : String = "+";
                                attribute Ipoint : Boolean = false;
                                attribute mass : Real = 0.4230969448143151;
                                attribute sigma_mass : Real = 0.28909372274994966;
                                attribute Cx : Real = -72.17906429432333;
                                attribute sigma_Cx : Real = 28.721044428837228;
                                attribute Cy : Real = 23.088056361302733;
                                attribute sigma_Cy : Real = 28.23690002309109;
                                attribute Cz : Real = 45.48424556851387;
                                attribute sigma_Cz : Real = 29.057750463592832;
                                attribute Ixx : Real = 0.47713580324547084;
                                attribute sigma_Ixx : Real = 0.37074144170588635;
                                attribute Iyy : Real = 0.5160729656899032;
                                attribute sigma_Iyy : Real = 0.3723953238821935;
                                attribute Izz : Real = 0.5112368028958486;
                                attribute sigma_Izz : Real = 0.37017423652493897;
                                attribute Ixy : Real = 0.005362689733715618;
                                attribute sigma_Ixy : Real = 0.02351283871158888;
                                attribute Ixz : Real = -0.013146447500463534;
                                attribute sigma_Ixz : Real = 0.022566176940390956;
                                attribute Iyz : Real = 0.024373738886708192;
                                attribute sigma_Iyz : Real = 0.02209918015384651;
                            }
                            part <'C.1.1.3.4.2.1.4'> 'Part 411' {
                                attribute POIconv : String = "-";
                                attribute Ipoint : Boolean = false;
                                attribute mass : Real = 0.8920250170012005;
                                attribute sigma_mass : Real = 0.28909372274994966;
                                attribute Cx : Real = 37.23470354452729;
                                attribute sigma_Cx : Real = 28.721044428837228;
                                attribute Cy : Real = -52.53887167200446;
                                attribute sigma_Cy : Real = 28.23690002309109;
                                attribute Cz : Real = -28.632713202387094;
                                attribute sigma_Cz : Real = 29.057750463592832;
                                attribute Ixx : Real = 1.0363791732454524;
                                attribute sigma_Ixx : Real = 0.37074144170588635;
                                attribute Iyy : Real = 1.1797234902122078;
                                attribute sigma_Iyy : Real = 0.3723953238821935;
                                attribute Izz : Real = 1.1593994525113964;
                                attribute sigma_Izz : Real = 0.37017423652493897;
                                attribute Ixy : Real = 0.016031035594379205;
                                attribute sigma_Ixy : Real = 0.02351283871158888;
                                attribute Ixz : Real = -0.04507704927717492;
                                attribute sigma_Ixz : Real = 0.022566176940390956;
                                attribute Iyz : Real = 0.02967864631956357;
                                attribute sigma_Iyz : Real = 0.02209918015384651;
                            }
                            part <'C.1.1.3.4.2.1.5'> 'Part 412' {
                                attribute POIconv : String = "+";
                                attribute Ipoint : Boolean = false;
                                attribute mass : Real = 0.29362692803354;
                                attribute sigma_mass : Real = 0.28909372274994966;
                                attribute Cx : Real = 2.241061720997095;
                                attribute sigma_Cx : Real = 28.721044428837228;
                                attribute Cy : Real = 78.95983019843698;
                                attribute sigma_Cy : Real = 28.23690002309109;
                                attribute Cz : Real = -95.49570959061384;
                                attribute sigma_Cz : Real = 29.057750463592832;
                                attribute Ixx : Real = 0.38827923413755033;
                                attribute sigma_Ixx : Real = 0.37074144170588635;
                                attribute Iyy : Real = 0.37646143764130113;
                                attribute sigma_Iyy : Real = 0.3723953238821935;
                                attribute Izz : Real = 0.3405159154270556;
                                attribute sigma_Izz : Real = 0.37017423652493897;
                                attribute Ixy : Real = -0.017483453178526016;
                                attribute sigma_Ixy : Real = 0.02351283871158888;
                                attribute Ixz : Real = -0.027673259923126595;
                                attribute sigma_Ixz : Real = 0.022566176940390956;
                                attribute Iyz : Real = -0.0037475097195479373;
                                attribute sigma_Iyz : Real = 0.02209918015384651;
                            }
                        }
                        part <'C.1.1.3.4.2.2'> 'Subassembly 122' {
                            attribute POIconv : String = "-";
                            attribute Ipoint : Boolean = false;
                            attribute mass : Real = 0.16892274450929837;
                            attribute sigma_mass : Real = 0.40884026350990615;
                            attribute Cx : Real = -61.23507682630823;
                            attribute sigma_Cx : Real = 171.07373562053482;
                            attribute Cy : Real = 13.266199239687454;
                            attribute sigma_Cy : Real = 96.7420196073456;
                            attribute Cz : Real = 53.83752778438514;
                            attribute sigma_Cz : Real = 29.226510210563752;
                            attribute Ixx : Real = 84.21955243417405;
                            attribute sigma_Ixx : Real = 868.5320624270385;
                            attribute Iyy : Real = 270.2796281477772;
                            attribute sigma_Iyy : Real = 2779.2878876751756;
                            attribute Izz : Real = 350.17984946060756;
                            attribute sigma_Izz : Real = 3599.724487936083;
                            attribute Ixy : Real = 148.176334209273;
                            attribute sigma_Ixy : Real = 1525.373574132704;
                            attribute Ixz : Real = -23.308530565531136;
                            attribute sigma_Ixz : Real = 258.29322919866416;
                            attribute Iyz : Real = 12.887176025138501;
                            attribute sigma_Iyz : Real = 142.97662791950816;
                            part <'C.1.1.3.4.2.2.1'> 'Part 413' {
                                attribute POIconv : String = "+";
                                attribute Ipoint : Boolean = false;
                                attribute mass : Real = 0.024139781995909288;
                                attribute sigma_mass : Real = 0.28909372274994966;
                                attribute Cx : Real = 36.310502188280225;
                                attribute sigma_Cx : Real = 28.721044428837228;
                                attribute Cy : Real = -40.669127414003015;
                                attribute sigma_Cy : Real = 28.23690002309109;
                                attribute Cz : Real = 62.32147407718003;
                                attribute sigma_Cz : Real = 29.057750463592832;
                                attribute Ixx : Real = 0.02725767100247586;
                                attribute sigma_Ixx : Real = 0.37074144170588635;
                                attribute Iyy : Real = 0.028449406874629875;
                                attribute sigma_Iyy : Real = 0.3723953238821935;
                                attribute Izz : Real = 0.029119918900478353;
                                attribute sigma_Izz : Real = 0.37017423652493897;
                                attribute Ixy : Real = -0.0011269054922727296;
                                attribute sigma_Ixy : Real = 0.02351283871158888;
                                attribute Ixz : Real = 0.0009569078179064694;
                                attribute sigma_Ixz : Real = 0.022566176940390956;
                                attribute Iyz : Real = -0.0005473443458944047;
                                attribute sigma_Iyz : Real = 0.02209918015384651;
                            }
                            part <'C.1.1.3.4.2.2.2'> 'Part 414' {
                                attribute POIconv : String = "-";
                                attribute Ipoint : Boolean = false;
                                attribute mass : Real = 0.14478296251338907;
                                attribute sigma_mass : Real = 0.28909372274994966;
                                attribute Cx : Real = -77.49893115833402;
                                attribute sigma_Cx : Real = 28.721044428837228;
                                attribute Cy : Real = 22.258880455046892;
                                attribute sigma_Cy : Real = 28.23690002309109;
                                attribute Cz : Real = 52.422992466017604;
                                attribute sigma_Cz : Real = 29.057750463592832;
                                attribute Ixx : Real = 0.23362975257959445;
                                attribute sigma_Ixx : Real = 0.37074144170588635;
                                attribute Iyy : Real = 0.23358908022952157;
                                attribute sigma_Iyy : Real = 0.3723953238821935;
                                attribute Izz : Real = 0.22890509317639687;
                                attribute sigma_Izz : Real = 0.37017423652493897;
                                attribute Ixy : Real = -0.003198497675131393;
                                attribute sigma_Ixy : Real = 0.02351283871158888;
                                attribute Ixz : Real = 0.0006681676007187626;
                                attribute sigma_Ixz : Real = 0.022566176940390956;
                                attribute Iyz : Real = -0.0010659668910849155;
                                attribute sigma_Iyz : Real = 0.02209918015384651;
                            }
                        }
                        part <'C.1.1.3.4.2.3'> 'Subassembly 123' {
                            attribute POIconv : String = "-";
                            attribute Ipoint : Boolean = false;
                            attribute mass : Real = 1.0007230076671112;
                            attribute sigma_mass : Real = 0.5781874454998993;
                            attribute Cx : Real = -55.51649867151163;
                            attribute sigma_Cx : Real = 41.896946133290655;
                            attribute Cy : Real = -1.9796207162089177;
                            attribute sigma_Cy : Real = 38.79898944690101;
                            attribute Cz : Real = -13.3529115640137;
                            attribute sigma_Cz : Real = 20.645466499754615;
                            attribute Ixx : Real = 3404.95997319839;
                            attribute sigma_Ixx : Real = 3330.691480925952;
                            attribute Iyy : Real = 2061.144343201497;
                            attribute sigma_Iyy : Real = 4943.807657362849;
                            attribute Izz : Real = 5037.777539972991;
                            attribute sigma_Izz : Real = 7271.7133427699555;
                            attribute Ixy : Real = -948.209686373365;
                            attribute sigma_Ixy : Real = 3335.262162142835;
                            attribute Ixz : Real = -232.36535099331758;
                            attribute sigma_Ixz : Real = 950.3804596307252;
                            attribute Iyz : Real = -815.1886381885938;
                            attribute sigma_Iyz : Real = 1194.2962914951227;
                            part <'C.1.1.3.4.2.3.1'> 'Part 415' {
                                attribute POIconv : String = "+";
                                attribute Ipoint : Boolean = false;
                                attribute mass : Real = 0.06433200815482996;
                                attribute sigma_mass : Real = 0.28909372274994966;
                                attribute Cx : Real = -62.4487120192498;
                                attribute sigma_Cx : Real = 28.721044428837228;
                                attribute Cy : Real = 13.181356946006417;
                                attribute sigma_Cy : Real = 28.23690002309109;
                                attribute Cz : Real = -18.05400256998837;
                                attribute sigma_Cz : Real = 29.057750463592832;
                                attribute Ixx : Real = 0.08566464022186969;
                                attribute sigma_Ixx : Real = 0.37074144170588635;
                                attribute Iyy : Real = 0.07957924592555442;
                                attribute sigma_Iyy : Real = 0.3723953238821935;
                                attribute Izz : Real = 0.07906301086929615;
                                attribute sigma_Izz : Real = 0.37017423652493897;
                                attribute Ixy : Real = -0.00036168274917020086;
                                attribute sigma_Ixy : Real = 0.02351283871158888;
                                attribute Ixz : Real = 0.002018733544854123;
                                attribute sigma_Ixz : Real = 0.022566176940390956;
                                attribute Iyz : Real = 0.0005957072987563077;
                                attribute sigma_Iyz : Real = 0.02209918015384651;
                            }
                            part <'C.1.1.3.4.2.3.2'> 'Part 416' {
                                attribute POIconv : String = "-";
                                attribute Ipoint : Boolean = false;
                                attribute mass : Real = 0.10031190048041753;
                                attribute sigma_mass : Real = 0.28909372274994966;
                                attribute Cx : Real = 71.95553602650762;
                                attribute sigma_Cx : Real = 28.721044428837228;
                                attribute Cy : Real = 82.88714457303286;
                                attribute sigma_Cy : Real = 28.23690002309109;
                                attribute Cz : Real = 8.078076411038637;
                                attribute sigma_Cz : Real = 29.057750463592832;
                                attribute Ixx : Real = 0.10514094988994091;
                                attribute sigma_Ixx : Real = 0.37074144170588635;
                                attribute Iyy : Real = 0.11587802145332216;
                                attribute sigma_Iyy : Real = 0.3723953238821935;
                                attribute Izz : Real = 0.11635948471954839;
                                attribute sigma_Izz : Real = 0.37017423652493897;
                                attribute Ixy : Real = 0.00845071023177046;
                                attribute sigma_Ixy : Real = 0.02351283871158888;
                                attribute Ixz : Real = 0.003539751587460147;
                                attribute sigma_Ixz : Real = 0.022566176940390956;
                                attribute Iyz : Real = -0.001929995543931993;
                                attribute sigma_Iyz : Real = 0.02209918015384651;
                            }
                            part <'C.1.1.3.4.2.3.3'> 'Part 417' {
                                attribute POIconv : String = "-";
                                attribute Ipoint : Boolean = false;
                                attribute mass : Real = 0.5723079992267304;
                                attribute sigma_mass : Real = 0.28909372274994966;
                                attribute Cx : Real = -66.13396527245641;
                                attribute sigma_Cx : Real = 28.721044428837228;
                                attribute Cy : Real = -49.28406924009323;
                                attribute sigma_Cy : Real = 28.23690002309109;
                                attribute Cz : Real = -25.011775083839893;
                                attribute sigma_Cz : Real = 29.057750463592832;
                                attribute Ixx : Real = 0.6609021357116578;
                                attribute sigma_Ixx : Real = 0.37074144170588635;
                                attribute Iyy : Real = 0.6154983600102096;
                                attribute sigma_Iyy : Real = 0.3723953238821935;
                                attribute Izz : Real = 0.6562060659766807;
                                attribute sigma_Izz : Real = 0.37017423652493897;
                                attribute Ixy : Real = 0.020567430151987084;
                                attribute sigma_Ixy : Real = 0.02351283871158888;
                                attribute Ixz : Real = 0.01615066952888317;
                                attribute sigma_Ixz : Real = 0.022566176940390956;
                                attribute Iyz : Real = -0.01762408074186115;
                                attribute sigma_Iyz : Real = 0.02209918015384651;
                            }
                            part <'C.1.1.3.4.2.3.4'> 'Part 418' {
                                attribute POIconv : String = "-";
                                attribute Ipoint : Boolean = false;
                                attribute mass : Real = 0.2637710998051334;
                                attribute sigma_mass : Real = 0.28909372274994966;
                                attribute Cx : Real = -79.26640072837472;
                                attribute sigma_Cx : Real = 28.721044428837228;
                                attribute Cy : Real = 64.68511871062219;
                                attribute sigma_Cy : Real = 28.23690002309109;
                                attribute Cz : Real = 4.939874680712819;
                                attribute sigma_Cz : Real = 29.057750463592832;
                                attribute Ixx : Real = 0.3782530263720684;
                                attribute sigma_Ixx : Real = 0.37074144170588635;
                                attribute Iyy : Real = 0.41130659593939833;
                                attribute sigma_Iyy : Real = 0.3723953238821935;
                                attribute Izz : Real = 0.3772507662053588;
                                attribute sigma_Izz : Real = 0.37017423652493897;
                                attribute Ixy : Real = 0.007664042749313265;
                                attribute sigma_Ixy : Real = 0.02351283871158888;
                                attribute Ixz : Real = -0.0004993204632608903;
                                attribute sigma_Ixz : Real = 0.022566176940390956;
                                attribute Iyz : Real = -0.006820167317350705;
                                attribute sigma_Iyz : Real = 0.02209918015384651;
                            }
                        }
                    }
                    part <'C.1.1.3.4.3'> 'Assembly 34' {
                        attribute POIconv : String = "-";
                        attribute Ipoint : Boolean = false;
                        attribute mass : Real = 6.770554654841778;
                        attribute sigma_mass : Real = 1.1919639546010696;
                        attribute Cx : Real = 33.00269732809781;
                        attribute sigma_Cx : Real = 13.277372206249167;
                        attribute Cy : Real = 5.0573956430638844;
                        attribute sigma_Cy : Real = 12.644179127817619;
                        attribute Cz : Real = 1.6457804529611602;
                        attribute sigma_Cz : Real = 13.664887389403724;
                        attribute Ixx : Real = 37303.26363231941;
                        attribute sigma_Ixx : Real = 11733.076055486516;
                        attribute Iyy : Real = 31615.660967461696;
                        attribute sigma_Iyy : Real = 11935.837829279157;
                        attribute Izz : Real = 29208.506952986478;
                        attribute sigma_Izz : Real = 11532.112568196444;
                        attribute Ixy : Real = 5822.254765518897;
                        attribute sigma_Ixy : Real = 4971.470286116372;
                        attribute Ixz : Real = 1555.437086006335;
                        attribute sigma_Ixz : Real = 5107.82393664394;
                        attribute Iyz : Real = -2281.5619982480525;
                        attribute sigma_Iyz : Real = 5661.863971175445;
                        part <'C.1.1.3.4.3.1'> 'Subassembly 124' {
                            attribute POIconv : String = "-";
                            attribute Ipoint : Boolean = false;
                            attribute mass : Real = 1.951630712288665;
                            attribute sigma_mass : Real = 0.6464332159373649;
                            attribute Cx : Real = 29.173886256889894;
                            attribute sigma_Cx : Real = 28.824376821657424;
                            attribute Cy : Real = 13.847058947100713;
                            attribute sigma_Cy : Real = 20.72806237729388;
                            attribute Cz : Real = 4.702336915976589;
                            attribute sigma_Cz : Real = 24.445972109900637;
                            attribute Ixx : Real = 9598.806681782906;
                            attribute sigma_Ixx : Real = 5713.079957227359;
                            attribute Iyy : Real = 10318.529194653349;
                            attribute sigma_Iyy : Real = 7401.84291797683;
                            attribute Izz : Real = 2467.8157857450387;
                            attribute sigma_Izz : Real = 5404.5309117622355;
                            attribute Ixy : Real = -666.2731908256434;
                            attribute sigma_Ixy : Real = 1987.7036018946978;
                            attribute Ixz : Real = 1358.3766993932381;
                            attribute sigma_Ixz : Real = 2942.955394706203;
                            attribute Iyz : Real = 1976.8100916321644;
                            attribute sigma_Iyz : Real = 2579.2185250996235;
                            part <'C.1.1.3.4.3.1.1'> 'Part 419' {
                                attribute POIconv : String = "-";
                                attribute Ipoint : Boolean = false;
                                attribute mass : Real = 0.9094892434936482;
                                attribute sigma_mass : Real = 0.28909372274994966;
                                attribute Cx : Real = 31.119699776172638;
                                attribute sigma_Cx : Real = 28.721044428837228;
                                attribute Cy : Real = 2.8392952401190996;
                                attribute sigma_Cy : Real = 28.23690002309109;
                                attribute Cz : Real = 69.49903233908117;
                                attribute sigma_Cz : Real = 29.057750463592832;
                                attribute Ixx : Real = 1.1504223119759562;
                                attribute sigma_Ixx : Real = 0.37074144170588635;
                                attribute Iyy : Real = 1.1416502130204527;
                                attribute sigma_Iyy : Real = 0.3723953238821935;
                                attribute Izz : Real = 1.1305561568253273;
                                attribute sigma_Izz : Real = 0.37017423652493897;
                                attribute Ixy : Real = 0.012050616902505026;
                                attribute sigma_Ixy : Real = 0.02351283871158888;
                                attribute Ixz : Real = -0.05505218775244497;
                                attribute sigma_Ixz : Real = 0.022566176940390956;
                                attribute Iyz : Real = 0.14646742835867904;
                                attribute sigma_Iyz : Real = 0.02209918015384651;
                            }
                            part <'C.1.1.3.4.3.1.2'> 'Part 420' {
                                attribute POIconv : String = "+";
                                attribute Ipoint : Boolean = false;
                                attribute mass : Real = 0.056092325994046406;
                                attribute sigma_mass : Real = 0.28909372274994966;
                                attribute Cx : Real = -42.156867450103164;
                                attribute sigma_Cx : Real = 28.721044428837228;
                                attribute Cy : Real = 56.02856012992561;
                                attribute sigma_Cy : Real = 28.23690002309109;
                                attribute Cz : Real = 5.715644173324108;
                                attribute sigma_Cz : Real = 29.057750463592832;
                                attribute Ixx : Real = 0.06504277006679979;
                                attribute sigma_Ixx : Real = 0.37074144170588635;
                                attribute Iyy : Real = 0.06544339871914866;
                                attribute sigma_Iyy : Real = 0.3723953238821935;
                                attribute Izz : Real = 0.06000423625942878;
                                attribute sigma_Izz : Real = 0.37017423652493897;
                                attribute Ixy : Real = -0.005251276244350761;
                                attribute sigma_Ixy : Real = 0.02351283871158888;
                                attribute Ixz : Real = 0.00023519043571815527;
                                attribute sigma_Ixz : Real = 0.022566176940390956;
                                attribute Iyz : Real = 0.00031209772740813774;
                                attribute sigma_Iyz : Real = 0.02209918015384651;
                            }
                            part <'C.1.1.3.4.3.1.3'> 'Part 421' {
                                attribute POIconv : String = "+";
                                attribute Ipoint : Boolean = false;
                                attribute mass : Real = 0.7712667896512431;
                                attribute sigma_mass : Real = 0.28909372274994966;
                                attribute Cx : Real = 50.49127829261124;
                                attribute sigma_Cx : Real = 28.721044428837228;
                                attribute Cy : Real = 34.31079708971083;
                                attribute sigma_Cy : Real = 28.23690002309109;
                                attribute Cz : Real = -74.79756544344127;
                                attribute sigma_Cz : Real = 29.057750463592832;
                                attribute Ixx : Real = 0.9871082772418219;
                                attribute sigma_Ixx : Real = 0.37074144170588635;
                                attribute Iyy : Real = 1.135314894551172;
                                attribute sigma_Iyy : Real = 0.3723953238821935;
                                attribute Izz : Real = 0.958963437482463;
                                attribute sigma_Izz : Real = 0.37017423652493897;
                                attribute Ixy : Real = -0.015573484141639272;
                                attribute sigma_Ixy : Real = 0.02351283871158888;
                                attribute Ixz : Real = 0.03863617195036039;
                                attribute sigma_Ixz : Real = 0.022566176940390956;
                                attribute Iyz : Real = 0.006372216276006405;
                                attribute sigma_Iyz : Real = 0.02209918015384651;
                            }
                            part <'C.1.1.3.4.3.1.4'> 'Part 422' {
                                attribute POIconv : String = "+";
                                attribute Ipoint : Boolean = false;
                                attribute mass : Real = 0.004991268917685375;
                                attribute sigma_mass : Real = 0.28909372274994966;
                                attribute Cx : Real = -87.43514423258603;
                                attribute sigma_Cx : Real = 28.721044428837228;
                                attribute Cy : Real = 54.64492975734174;
                                attribute sigma_Cy : Real = 28.23690002309109;
                                attribute Cz : Real = 46.778071066364646;
                                attribute sigma_Cz : Real = 29.057750463592832;
                                attribute Ixx : Real = 0.006088800972864968;
                                attribute sigma_Ixx : Real = 0.37074144170588635;
                                attribute Iyy : Real = 0.007678660092115591;
                                attribute sigma_Iyy : Real = 0.3723953238821935;
                                attribute Izz : Real = 0.0059435410288471505;
                                attribute sigma_Izz : Real = 0.37017423652493897;
                                attribute Ixy : Real = 0.000131165732127468;
                                attribute sigma_Ixy : Real = 0.02351283871158888;
                                attribute Ixz : Real = 8.949518996066784e-06;
                                attribute sigma_Ixz : Real = 0.022566176940390956;
                                attribute Iyz : Real = -8.833961850856149e-05;
                                attribute sigma_Iyz : Real = 0.02209918015384651;
                            }
                            part <'C.1.1.3.4.3.1.5'> 'Part 423' {
                                attribute POIconv : String = "+";
                                attribute Ipoint : Boolean = false;
                                attribute mass : Real = 0.20979108423204162;
                                attribute sigma_mass : Real = 0.28909372274994966;
                                attribute Cx : Real = -35.78577642329037;
                                attribute sigma_Cx : Real = 28.721044428837228;
                                attribute Cy : Real = -25.91273649595678;
                                attribute sigma_Cy : Real = 28.23690002309109;
                                attribute Cz : Real = 14.792789099738002;
                                attribute sigma_Cz : Real = 29.057750463592832;
                                attribute Ixx : Real = 0.22360810381027588;
                                attribute sigma_Ixx : Real = 0.37074144170588635;
                                attribute Iyy : Real = 0.27521734285092225;
                                attribute sigma_Iyy : Real = 0.3723953238821935;
                                attribute Izz : Real = 0.24899191416365518;
                                attribute sigma_Izz : Real = 0.37017423652493897;
                                attribute Ixy : Real = 0.0072782882331234805;
                                attribute sigma_Ixy : Real = 0.02351283871158888;
                                attribute Ixz : Real = 0.0041285929694535465;
                                attribute sigma_Ixz : Real = 0.022566176940390956;
                                attribute Iyz : Real = -0.013297867711905137;
                                attribute sigma_Iyz : Real = 0.02209918015384651;
                            }
                        }
                        part <'C.1.1.3.4.3.2'> 'Subassembly 125' {
                            attribute POIconv : String = "-";
                            attribute Ipoint : Boolean = false;
                            attribute mass : Real = 1.657802368374076;
                            attribute sigma_mass : Real = 0.5007250159521434;
                            attribute Cx : Real = 51.74941005665938;
                            attribute sigma_Cx : Real = 17.22927756862461;
                            attribute Cy : Real = 16.583806362816418;
                            attribute sigma_Cy : Real = 23.6395397206895;
                            attribute Cz : Real = 7.4259151467049005;
                            attribute sigma_Cz : Real = 24.237050869825097;
                            attribute Ixx : Real = 10726.732206954846;
                            attribute sigma_Ixx : Real = 5658.899226577285;
                            attribute Iyy : Real = 5187.237609719264;
                            attribute sigma_Iyy : Real = 3642.3482975952898;
                            attribute Izz : Real = 5551.083424186009;
                            attribute sigma_Izz : Real = 3746.55827176437;
                            attribute Ixy : Real = 68.84842137343598;
                            attribute sigma_Ixy : Real = 1716.2152266396524;
                            attribute Ixz : Real = 99.0197915868479;
                            attribute sigma_Ixz : Real = 1608.8964060085757;
                            attribute Iyz : Real = -5201.312318924223;
                            attribute sigma_Iyz : Real = 2807.164017775008;
                            part <'C.1.1.3.4.3.2.1'> 'Part 424' {
                                attribute POIconv : String = "-";
                                attribute Ipoint : Boolean = false;
                                attribute mass : Real = 0.7085896115608048;
                                attribute sigma_mass : Real = 0.28909372274994966;
                                attribute Cx : Real = 50.68416763097048;
                                attribute sigma_Cx : Real = 28.721044428837228;
                                attribute Cy : Real = 82.89898103103042;
                                attribute sigma_Cy : Real = 28.23690002309109;
                                attribute Cz : Real = 71.7518663033843;
                                attribute sigma_Cz : Real = 29.057750463592832;
                                attribute Ixx : Real = 0.9043909380336036;
                                attribute sigma_Ixx : Real = 0.37074144170588635;
                                attribute Iyy : Real = 1.0121323017280928;
                                attribute sigma_Iyy : Real = 0.3723953238821935;
                                attribute Izz : Real = 0.8309264105436839;
                                attribute sigma_Izz : Real = 0.37017423652493897;
                                attribute Ixy : Real = 0.021018447601426845;
                                attribute sigma_Ixy : Real = 0.02351283871158888;
                                attribute Ixz : Real = 0.01599300158227033;
                                attribute sigma_Ixz : Real = 0.022566176940390956;
                                attribute Iyz : Real = 0.020155343136182443;
                                attribute sigma_Iyz : Real = 0.02209918015384651;
                            }
                            part <'C.1.1.3.4.3.2.2'> 'Part 425' {
                                attribute POIconv : String = "-";
                                attribute Ipoint : Boolean = false;
                                attribute mass : Real = 0.6071510485748295;
                                attribute sigma_mass : Real = 0.28909372274994966;
                                attribute Cx : Real = 51.124310214072466;
                                attribute sigma_Cx : Real = 28.721044428837228;
                                attribute Cy : Real = -40.69296699017286;
                                attribute sigma_Cy : Real = 28.23690002309109;
                                attribute Cz : Real = -34.6518465783447;
                                attribute sigma_Cz : Real = 29.057750463592832;
                                attribute Ixx : Real = 0.9696378865536255;
                                attribute sigma_Ixx : Real = 0.37074144170588635;
                                attribute Iyy : Real = 0.7297743049644179;
                                attribute sigma_Iyy : Real = 0.3723953238821935;
                                attribute Izz : Real = 0.7529669742050189;
                                attribute sigma_Izz : Real = 0.37017423652493897;
                                attribute Ixy : Real = -0.00981735626742393;
                                attribute sigma_Ixy : Real = 0.02351283871158888;
                                attribute Ixz : Real = -0.010655605892752287;
                                attribute sigma_Ixz : Real = 0.022566176940390956;
                                attribute Iyz : Real = 0.0001062941215031453;
                                attribute sigma_Iyz : Real = 0.02209918015384651;
                            }
                            part <'C.1.1.3.4.3.2.3'> 'Part 426' {
                                attribute POIconv : String = "-";
                                attribute Ipoint : Boolean = false;
                                attribute mass : Real = 0.3420617082384415;
                                attribute sigma_mass : Real = 0.28909372274994966;
                                attribute Cx : Real = 55.06562381051481;
                                attribute sigma_Cx : Real = 28.721044428837228;
                                attribute Cy : Real = -19.12492853589356;
                                attribute sigma_Cy : Real = 28.23690002309109;
                                attribute Cz : Real = -51.139960857108235;
                                attribute sigma_Cz : Real = 29.057750463592832;
                                attribute Ixx : Real = 0.4226112484799215;
                                attribute sigma_Ixx : Real = 0.37074144170588635;
                                attribute Iyy : Real = 0.4280910250588482;
                                attribute sigma_Iyy : Real = 0.3723953238821935;
                                attribute Izz : Real = 0.5254632884728919;
                                attribute sigma_Izz : Real = 0.37017423652493897;
                                attribute Ixy : Real = 0.013279943992562025;
                                attribute sigma_Ixy : Real = 0.02351283871158888;
                                attribute Ixz : Real = -0.00445438574511089;
                                attribute sigma_Ixz : Real = 0.022566176940390956;
                                attribute Iyz : Real = -0.0005948309692246035;
                                attribute sigma_Iyz : Real = 0.02209918015384651;
                            }
                        }
                        part <'C.1.1.3.4.3.3'> 'Subassembly 126' {
                            attribute POIconv : String = "-";
                            attribute Ipoint : Boolean = false;
                            attribute mass : Real = 0.27954920673929157;
                            attribute sigma_mass : Real = 0.40884026350990615;
                            attribute Cx : Real = 39.1562056517129;
                            attribute sigma_Cx : Real = 20.567746774984535;
                            attribute Cy : Real = 85.16256415450343;
                            attribute sigma_Cy : Real = 24.022994078401926;
                            attribute Cz : Real = -16.79968178746062;
                            attribute sigma_Cz : Real = 103.12512262991534;
                            attribute Ixx : Real = 1289.4720730319837;
                            attribute sigma_Ixx : Real = 2212.9789802699406;
                            attribute Iyy : Real = 1268.5491798734397;
                            attribute sigma_Iyy : Real = 2179.3773299230525;
                            attribute Izz : Real = 21.355378773420274;
                            attribute sigma_Izz : Real = 101.25219996975025;
                            attribute Ixy : Real = 0.7744311204412079;
                            attribute sigma_Ixy : Real = 48.563303332331785;
                            attribute Ixz : Real = -6.123439021416647;
                            attribute sigma_Ixz : Real = 377.68791640017474;
                            attribute Iyz : Real = 162.94544557053558;
                            attribute sigma_Iyz : Real = 457.13543587411425;
                            part <'C.1.1.3.4.3.3.1'> 'Part 427' {
                                attribute POIconv : String = "+";
                                attribute Ipoint : Boolean = false;
                                attribute mass : Real = 0.1619111926262267;
                                attribute sigma_mass : Real = 0.28909372274994966;
                                attribute Cx : Real = 39.433434093371034;
                                attribute sigma_Cx : Real = 28.721044428837228;
                                attribute Cy : Real = 77.78569520451128;
                                attribute sigma_Cy : Real = 28.23690002309109;
                                attribute Cz : Real = 40.61036272905767;
                                attribute sigma_Cz : Real = 29.057750463592832;
                                attribute Ixx : Real = 0.24154281886653436;
                                attribute sigma_Ixx : Real = 0.37074144170588635;
                                attribute Iyy : Real = 0.22907819321482933;
                                attribute sigma_Iyy : Real = 0.3723953238821935;
                                attribute Izz : Real = 0.21653905545625635;
                                attribute sigma_Izz : Real = 0.37017423652493897;
                                attribute Ixy : Real = 0.0021217997868077194;
                                attribute sigma_Ixy : Real = 0.02351283871158888;
                                attribute Ixz : Real = 0.0022567388079550985;
                                attribute sigma_Ixz : Real = 0.022566176940390956;
                                attribute Iyz : Real = 0.006999220167089734;
                                attribute sigma_Iyz : Real = 0.02209918015384651;
                            }
                            part <'C.1.1.3.4.3.3.2'> 'Part 428' {
                                attribute POIconv : String = "+";
                                attribute Ipoint : Boolean = false;
                                attribute mass : Real = 0.11763801411306486;
                                attribute sigma_mass : Real = 0.28909372274994966;
                                attribute Cx : Real = 38.77464202232659;
                                attribute sigma_Cx : Real = 28.721044428837228;
                                attribute Cy : Real = 95.31572475098073;
                                attribute sigma_Cy : Real = 28.23690002309109;
                                attribute Cz : Real = -95.81605116836727;
                                attribute sigma_Cz : Real = 29.057750463592832;
                                attribute Ixx : Real = 0.1643331654313929;
                                attribute sigma_Ixx : Real = 0.37074144170588635;
                                attribute Iyy : Real = 0.16215992295845438;
                                attribute sigma_Iyy : Real = 0.3723953238821935;
                                attribute Izz : Real = 0.1714428350223776;
                                attribute sigma_Izz : Real = 0.37017423652493897;
                                attribute Ixy : Real = 0.010306780963460351;
                                attribute sigma_Ixy : Real = 0.02351283871158888;
                                attribute Ixz : Real = -0.0025066130310973473;
                                attribute sigma_Ixz : Real = 0.022566176940390956;
                                attribute Iyz : Real = -0.005056696363882812;
                                attribute sigma_Iyz : Real = 0.02209918015384651;
                            }
                        }
                        part <'C.1.1.3.4.3.4'> 'Subassembly 127' {
                            attribute POIconv : String = "-";
                            attribute Ipoint : Boolean = false;
                            attribute mass : Real = 2.371201636014972;
                            attribute sigma_mass : Real = 0.6464332159373649;
                            attribute Cx : Real = 19.083087313308273;
                            attribute sigma_Cx : Real = 21.875951093763835;
                            attribute Cy : Real = -19.338972628175245;
                            attribute sigma_Cy : Real = 21.21323717650528;
                            attribute Cz : Real = 11.441134044285736;
                            attribute sigma_Cz : Real = 22.31305090266338;
                            attribute Ixx : Real = 9496.702700166967;
                            attribute sigma_Ixx : Real = 6523.575005234381;
                            attribute Iyy : Real = 10737.759626364668;
                            attribute sigma_Iyy : Real = 6662.750499800318;
                            attribute Izz : Real = 16097.60841677081;
                            attribute sigma_Izz : Real = 7633.927998256519;
                            attribute Ixy : Real = 7663.69338139528;
                            attribute sigma_Ixy : Real = 3791.794428702702;
                            attribute Ixz : Real = -619.5385082684229;
                            attribute sigma_Ixz : Real = 2808.9895505558134;
                            attribute Iyz : Real = 14.922325002559177;
                            attribute sigma_Iyz : Real = 2892.5940596420173;
                            part <'C.1.1.3.4.3.4.1'> 'Part 429' {
                                attribute POIconv : String = "-";
                                attribute Ipoint : Boolean = false;
                                attribute mass : Real = 0.029794306237716228;
                                attribute sigma_mass : Real = 0.28909372274994966;
                                attribute Cx : Real = 45.429380843415856;
                                attribute sigma_Cx : Real = 28.721044428837228;
                                attribute Cy : Real = 26.719054905697703;
                                attribute sigma_Cy : Real = 28.23690002309109;
                                attribute Cz : Real = -94.2824135068804;
                                attribute sigma_Cz : Real = 29.057750463592832;
                                attribute Ixx : Real = 0.0351440098797554;
                                attribute sigma_Ixx : Real = 0.37074144170588635;
                                attribute Iyy : Real = 0.03770904454056056;
                                attribute sigma_Iyy : Real = 0.3723953238821935;
                                attribute Izz : Real = 0.034440097297161784;
                                attribute sigma_Izz : Real = 0.37017423652493897;
                                attribute Ixy : Real = 0.00016006458800752843;
                                attribute sigma_Ixy : Real = 0.02351283871158888;
                                attribute Ixz : Real = 0.002924436136549487;
                                attribute sigma_Ixz : Real = 0.022566176940390956;
                                attribute Iyz : Real = -0.00017606686273497803;
                                attribute sigma_Iyz : Real = 0.02209918015384651;
                            }
                            part <'C.1.1.3.4.3.4.2'> 'Part 430' {
                                attribute POIconv : String = "+";
                                attribute Ipoint : Boolean = false;
                                attribute mass : Real = 0.5003303071025293;
                                attribute sigma_mass : Real = 0.28909372274994966;
                                attribute Cx : Real = 59.56250415183604;
                                attribute sigma_Cx : Real = 28.721044428837228;
                                attribute Cy : Real = -30.107643827795982;
                                attribute sigma_Cy : Real = 28.23690002309109;
                                attribute Cz : Real = 59.00630345568061;
                                attribute sigma_Cz : Real = 29.057750463592832;
                                attribute Ixx : Real = 0.6510155006328452;
                                attribute sigma_Ixx : Real = 0.37074144170588635;
                                attribute Iyy : Real = 0.7674421556152697;
                                attribute sigma_Iyy : Real = 0.3723953238821935;
                                attribute Izz : Real = 0.6215946714821855;
                                attribute sigma_Izz : Real = 0.37017423652493897;
                                attribute Ixy : Real = 0.03319655461440689;
                                attribute sigma_Ixy : Real = 0.02351283871158888;
                                attribute Ixz : Real = 0.01838404888949848;
                                attribute sigma_Ixz : Real = 0.022566176940390956;
                                attribute Iyz : Real = -0.03798131030457702;
                                attribute sigma_Iyz : Real = 0.02209918015384651;
                            }
                            part <'C.1.1.3.4.3.4.3'> 'Part 431' {
                                attribute POIconv : String = "+";
                                attribute Ipoint : Boolean = false;
                                attribute mass : Real = 0.9400139372036792;
                                attribute sigma_mass : Real = 0.28909372274994966;
                                attribute Cx : Real = 70.35587434656918;
                                attribute sigma_Cx : Real = 28.721044428837228;
                                attribute Cy : Real = -78.75907151028514;
                                attribute sigma_Cy : Real = 28.23690002309109;
                                attribute Cz : Real = -2.960251597687602;
                                attribute sigma_Cz : Real = 29.057750463592832;
                                attribute Ixx : Real = 1.1048786939949125;
                                attribute sigma_Ixx : Real = 0.37074144170588635;
                                attribute Iyy : Real = 1.1028865908242194;
                                attribute sigma_Iyy : Real = 0.3723953238821935;
                                attribute Izz : Real = 0.9030065288808734;
                                attribute sigma_Izz : Real = 0.37017423652493897;
                                attribute Ixy : Real = 0.056158234996003656;
                                attribute sigma_Ixy : Real = 0.02351283871158888;
                                attribute Ixz : Real = -0.10483425118501807;
                                attribute sigma_Ixz : Real = 0.022566176940390956;
                                attribute Iyz : Real = -0.08826017583415448;
                                attribute sigma_Iyz : Real = 0.02209918015384651;
                            }
                            part <'C.1.1.3.4.3.4.4'> 'Part 432' {
                                attribute POIconv : String = "-";
                                attribute Ipoint : Boolean = false;
                                attribute mass : Real = 0.158609783468768;
                                attribute sigma_mass : Real = 0.28909372274994966;
                                attribute Cx : Real = -44.00008297525346;
                                attribute sigma_Cx : Real = 28.721044428837228;
                                attribute Cy : Real = 40.450009098276496;
                                attribute sigma_Cy : Real = 28.23690002309109;
                                attribute Cz : Real = -39.13062531501055;
                                attribute sigma_Cz : Real = 29.057750463592832;
                                attribute Ixx : Real = 0.21768747069022196;
                                attribute sigma_Ixx : Real = 0.37074144170588635;
                                attribute Iyy : Real = 0.21859048473007575;
                                attribute sigma_Iyy : Real = 0.3723953238821935;
                                attribute Izz : Real = 0.21110189911333235;
                                attribute sigma_Izz : Real = 0.37017423652493897;
                                attribute Ixy : Real = -0.016849790326129516;
                                attribute sigma_Ixy : Real = 0.02351283871158888;
                                attribute Ixz : Real = 0.0037306280567339623;
                                attribute sigma_Ixz : Real = 0.022566176940390956;
                                attribute Iyz : Real = 0.007845058481487095;
                                attribute sigma_Iyz : Real = 0.02209918015384651;
                            }
                            part <'C.1.1.3.4.3.4.5'> 'Part 433' {
                                attribute POIconv : String = "+";
                                attribute Ipoint : Boolean = false;
                                attribute mass : Real = 0.7424533020022791;
                                attribute sigma_mass : Real = 0.28909372274994966;
                                attribute Cx : Real = -60.69240141659975;
                                attribute sigma_Cx : Real = 28.721044428837228;
                                attribute Cy : Real = 48.528230749070644;
                                attribute sigma_Cy : Real = 28.23690002309109;
                                attribute Cz : Real = 12.667262274771929;
                                attribute sigma_Cz : Real = 29.057750463592832;
                                attribute Ixx : Real = 1.1081461745810353;
                                attribute sigma_Ixx : Real = 0.37074144170588635;
                                attribute Iyy : Real = 0.949089420021869;
                                attribute sigma_Iyy : Real = 0.3723953238821935;
                                attribute Izz : Real = 0.9982687442612806;
                                attribute sigma_Izz : Real = 0.37017423652493897;
                                attribute Ixy : Real = -0.0056058837701114155;
                                attribute sigma_Ixy : Real = 0.02351283871158888;
                                attribute Ixz : Real = 0.007615769199301767;
                                attribute sigma_Ixz : Real = 0.022566176940390956;
                                attribute Iyz : Real = -0.03573553233987374;
                                attribute sigma_Iyz : Real = 0.02209918015384651;
                            }
                        }
                        part <'C.1.1.3.4.3.5'> 'Subassembly 128' {
                            attribute POIconv : String = "-";
                            attribute Ipoint : Boolean = false;
                            attribute mass : Real = 0.5103707314247732;
                            attribute sigma_mass : Real = 0.40884026350990615;
                            attribute Cx : Real = 48.050727541882885;
                            attribute sigma_Cx : Real = 66.6631683192647;
                            attribute Cy : Real = 3.4755733505834736;
                            attribute sigma_Cy : Real = 27.280161743065136;
                            attribute Cz : Real = -64.22385607942789;
                            attribute sigma_Cz : Real = 27.99843346788333;
                            attribute Ixx : Real = 3.4724052789932256;
                            attribute sigma_Ixx : Real = 38.41326591798387;
                            attribute Iyy : Real = 296.12110726875306;
                            attribute sigma_Iyy : Real = 3341.6993623393846;
                            attribute Izz : Real = 296.3984893187645;
                            attribute sigma_Izz : Real = 3344.433342074633;
                            attribute Ixy : Real = -21.366084566125167;
                            attribute sigma_Ixy : Real = 262.7644059424068;
                            attribute Ixz : Real = 19.578517862052774;
                            attribute sigma_Ixz : Real = 246.161039564125;
                            attribute Iyz : Real = 1.4285416985674746;
                            attribute sigma_Iyz : Real = 19.169912318539758;
                            part <'C.1.1.3.4.3.5.1'> 'Part 434' {
                                attribute POIconv : String = "-";
                                attribute Ipoint : Boolean = false;
                                attribute mass : Real = 0.48597481388016606;
                                attribute sigma_mass : Real = 0.28909372274994966;
                                attribute Cx : Real = 53.43048204667866;
                                attribute sigma_Cx : Real = 28.721044428837228;
                                attribute Cy : Real = 3.8660902995616198;
                                attribute sigma_Cy : Real = 28.23690002309109;
                                attribute Cz : Real = -64.58254107274115;
                                attribute sigma_Cz : Real = 29.057750463592832;
                                attribute Ixx : Real = 0.5813709162591114;
                                attribute sigma_Ixx : Real = 0.37074144170588635;
                                attribute Iyy : Real = 0.5370018953907398;
                                attribute sigma_Iyy : Real = 0.3723953238821935;
                                attribute Izz : Real = 0.573491080162924;
                                attribute sigma_Izz : Real = 0.37017423652493897;
                                attribute Ixy : Real = -0.006438100087433812;
                                attribute sigma_Ixy : Real = 0.02351283871158888;
                                attribute Ixz : Real = -0.04174474211502744;
                                attribute sigma_Ixz : Real = 0.022566176940390956;
                                attribute Iyz : Real = 0.004643443325828774;
                                attribute sigma_Iyz : Real = 0.02209918015384651;
                            }
                            part <'C.1.1.3.4.3.5.2'> 'Part 435' {
                                attribute POIconv : String = "+";
                                attribute Ipoint : Boolean = false;
                                attribute mass : Real = 0.024395917544607074;
                                attribute sigma_mass : Real = 0.28909372274994966;
                                attribute Cx : Real = -59.11577641963959;
                                attribute sigma_Cx : Real = 28.721044428837228;
                                attribute Cy : Real = -4.303654516115785;
                                attribute sigma_Cy : Real = 28.23690002309109;
                                attribute Cz : Real = -57.07873138599098;
                                attribute sigma_Cz : Real = 29.057750463592832;
                                attribute Ixx : Real = 0.032565620792309596;
                                attribute sigma_Ixx : Real = 0.37074144170588635;
                                attribute Iyy : Real = 0.03232860716542206;
                                attribute sigma_Iyy : Real = 0.3723953238821935;
                                attribute Izz : Real = 0.030758970733119513;
                                attribute sigma_Izz : Real = 0.37017423652493897;
                                attribute Ixy : Real = 0.00045978983486391015;
                                attribute sigma_Ixy : Real = 0.02351283871158888;
                                attribute Ixz : Real = -0.0021135067278569243;
                                attribute sigma_Ixz : Real = 0.022566176940390956;
                                attribute Iyz : Real = 0.00018526442473190197;
                                attribute sigma_Iyz : Real = 0.02209918015384651;
                            }
                        }
                    }
                    part <'C.1.1.3.4.4'> 'Assembly 35' {
                        attribute POIconv : String = "-";
                        attribute Ipoint : Boolean = false;
                        attribute mass : Real = 3.208625982074067;
                        attribute sigma_mass : Real = 0.8176805270198123;
                        attribute Cx : Real = -14.75206127718891;
                        attribute sigma_Cx : Real = 17.865444098463595;
                        attribute Cy : Real = 21.42474310847793;
                        attribute sigma_Cy : Real = 17.905434188891704;
                        attribute Cz : Real = -22.35813123035988;
                        attribute sigma_Cz : Real = 22.743960971678444;
                        attribute Ixx : Real = 19392.530734661148;
                        attribute sigma_Ixx : Real = 11696.481325377445;
                        attribute Iyy : Real = 15442.134884464078;
                        attribute sigma_Iyy : Real = 12263.915567071997;
                        attribute Izz : Real = 12638.366863695966;
                        attribute sigma_Izz : Real = 7203.199477748254;
                        attribute Ixy : Real = -285.078332371422;
                        attribute sigma_Ixy : Real = 3277.556496008648;
                        attribute Ixz : Real = 4502.345879352373;
                        attribute sigma_Ixz : Real = 5622.565259439396;
                        attribute Iyz : Real = 2904.796153807259;
                        attribute sigma_Iyz : Real = 4865.451063596329;
                        part <'C.1.1.3.4.4.1'> 'Subassembly 129' {
                            attribute POIconv : String = "-";
                            attribute Ipoint : Boolean = false;
                            attribute mass : Real = 1.4015354088898748;
                            attribute sigma_mass : Real = 0.5007250159521434;
                            attribute Cx : Real = 7.917278310813669;
                            attribute sigma_Cx : Real = 31.624105461321204;
                            attribute Cy : Real = 9.376398748403085;
                            attribute sigma_Cy : Real = 25.093580798518772;
                            attribute Cz : Real = -60.78605617939767;
                            attribute sigma_Cz : Real = 39.18809307579244;
                            attribute Ixx : Real = 3541.0110300675856;
                            attribute sigma_Ixx : Real = 8434.827587675078;
                            attribute Iyy : Real = 4921.8914186647935;
                            attribute sigma_Iyy : Real = 10209.955322889991;
                            attribute Izz : Real = 2350.1359345943606;
                            attribute sigma_Izz : Real = 4630.864790352324;
                            attribute Ixy : Real = 467.1744789538885;
                            attribute sigma_Ixy : Real = 2120.526160185589;
                            attribute Ixz : Real = 689.8205318871666;
                            attribute sigma_Ixz : Real = 4720.081983209289;
                            attribute Iyz : Real = -1186.3566155327346;
                            attribute sigma_Iyz : Real = 3159.6693189300477;
                            part <'C.1.1.3.4.4.1.1'> 'Part 436' {
                                attribute POIconv : String = "+";
                                attribute Ipoint : Boolean = false;
                                attribute mass : Real = 0.3480424385853112;
                                attribute sigma_mass : Real = 0.28909372274994966;
                                attribute Cx : Real = 57.54070375114679;
                                attribute sigma_Cx : Real = 28.721044428837228;
                                attribute Cy : Real = 14.480746164917946;
                                attribute sigma_Cy : Real = 28.23690002309109;
                                attribute Cz : Real = -30.676222499459982;
                                attribute sigma_Cz : Real = 29.057750463592832;
                                attribute Ixx : Real = 0.37923024432900126;
                                attribute sigma_Ixx : Real = 0.37074144170588635;
                                attribute Iyy : Real = 0.42781526515126506;
                                attribute sigma_Iyy : Real = 0.3723953238821935;
                                attribute Izz : Real = 0.4651090471883633;
                                attribute sigma_Izz : Real = 0.37017423652493897;
                                attribute Ixy : Real = -0.023435525630714237;
                                attribute sigma_Ixy : Real = 0.02351283871158888;
                                attribute Ixz : Real = 0.024135619321135737;
                                attribute sigma_Ixz : Real = 0.022566176940390956;
                                attribute Iyz : Real = 0.005961486876783505;
                                attribute sigma_Iyz : Real = 0.02209918015384651;
                            }
                            part <'C.1.1.3.4.4.1.2'> 'Part 437' {
                                attribute POIconv : String = "-";
                                attribute Ipoint : Boolean = false;
                                attribute mass : Real = 0.08925935830641538;
                                attribute sigma_mass : Real = 0.28909372274994966;
                                attribute Cx : Real = -94.65510570444167;
                                attribute sigma_Cx : Real = 28.721044428837228;
                                attribute Cy : Real = 77.24496074952185;
                                attribute sigma_Cy : Real = 28.23690002309109;
                                attribute Cz : Real = 93.67089378647506;
                                attribute sigma_Cz : Real = 29.057750463592832;
                                attribute Ixx : Real = 0.11339744422302175;
                                attribute sigma_Ixx : Real = 0.37074144170588635;
                                attribute Iyy : Real = 0.11186144820662926;
                                attribute sigma_Iyy : Real = 0.3723953238821935;
                                attribute Izz : Real = 0.10909778118314283;
                                attribute sigma_Izz : Real = 0.37017423652493897;
                                attribute Ixy : Real = -0.008898110007961358;
                                attribute sigma_Ixy : Real = 0.02351283871158888;
                                attribute Ixz : Real = -0.00022610005020483852;
                                attribute sigma_Ixz : Real = 0.022566176940390956;
                                attribute Iyz : Real = -0.0006522884395466499;
                                attribute sigma_Iyz : Real = 0.02209918015384651;
                            }
                            part <'C.1.1.3.4.4.1.3'> 'Part 438' {
                                attribute POIconv : String = "-";
                                attribute Ipoint : Boolean = false;
                                attribute mass : Real = 0.9642336119981483;
                                attribute sigma_mass : Real = 0.28909372274994966;
                                attribute Cx : Real = -0.4992638248950243;
                                attribute sigma_Cx : Real = 28.721044428837228;
                                attribute Cy : Real = 1.2513617053627968;
                                attribute sigma_Cy : Real = 28.23690002309109;
                                attribute Cz : Real = -85.95239333808422;
                                attribute sigma_Cz : Real = 29.057750463592832;
                                attribute Ixx : Real = 0.9699863062211797;
                                attribute sigma_Ixx : Real = 0.37074144170588635;
                                attribute Iyy : Real = 1.2079574364458971;
                                attribute sigma_Iyy : Real = 0.3723953238821935;
                                attribute Izz : Real = 1.2376753762277009;
                                attribute sigma_Izz : Real = 0.37017423652493897;
                                attribute Ixy : Real = -0.1174213643025402;
                                attribute sigma_Ixy : Real = 0.02351283871158888;
                                attribute Ixz : Real = -0.026273893843116708;
                                attribute sigma_Ixz : Real = 0.022566176940390956;
                                attribute Iyz : Real = -0.009570120433749545;
                                attribute sigma_Iyz : Real = 0.02209918015384651;
                            }
                        }
                        part <'C.1.1.3.4.4.2'> 'Subassembly 130' {
                            attribute POIconv : String = "-";
                            attribute Ipoint : Boolean = false;
                            attribute mass : Real = 1.8070905731841922;
                            attribute sigma_mass : Real = 0.6464332159373649;
                            attribute Cx : Real = -32.33384859886744;
                            attribute sigma_Cx : Real = 18.046320412698453;
                            attribute Cy : Real = 30.769145370169298;
                            attribute sigma_Cy : Real = 24.69155519448172;
                            attribute Cz : Real = 7.445630852986167;
                            attribute sigma_Cz : Real = 21.909763348813897;
                            attribute Ixx : Real = 11815.449054730025;
                            attribute sigma_Ixx : Real = 6308.906585041946;
                            attribute Iyy : Real = 5566.56055287084;
                            attribute sigma_Iyy : Real = 3978.245656254261;
                            attribute Izz : Real = 8648.13507272026;
                            attribute sigma_Izz : Real = 4847.666619019595;
                            attribute Ixy : Real = -1431.9406354019522;
                            attribute sigma_Ixy : Real = 2141.648218212583;
                            attribute Ixz : Real = 1644.6762296275972;
                            attribute sigma_Ixz : Real = 1774.4438839198422;
                            attribute Iyz : Real = 5243.325402821345;
                            attribute sigma_Iyz : Real = 3071.3456526215296;
                            part <'C.1.1.3.4.4.2.1'> 'Part 439' {
                                attribute POIconv : String = "-";
                                attribute Ipoint : Boolean = false;
                                attribute mass : Real = 0.3171077902994584;
                                attribute sigma_mass : Real = 0.28909372274994966;
                                attribute Cx : Real = 11.465211166068912;
                                attribute sigma_Cx : Real = 28.721044428837228;
                                attribute Cy : Real = 96.86811096034944;
                                attribute sigma_Cy : Real = 28.23690002309109;
                                attribute Cz : Real = -73.75914030708373;
                                attribute sigma_Cz : Real = 29.057750463592832;
                                attribute Ixx : Real = 0.45994550420763664;
                                attribute sigma_Ixx : Real = 0.37074144170588635;
                                attribute Iyy : Real = 0.44076294215537776;
                                attribute sigma_Iyy : Real = 0.3723953238821935;
                                attribute Izz : Real = 0.4131652531219322;
                                attribute sigma_Izz : Real = 0.37017423652493897;
                                attribute Ixy : Real = 0.0005199851554080533;
                                attribute sigma_Ixy : Real = 0.02351283871158888;
                                attribute Ixz : Real = 0.02852347871642939;
                                attribute sigma_Ixz : Real = 0.022566176940390956;
                                attribute Iyz : Real = 0.002980288698795897;
                                attribute sigma_Iyz : Real = 0.02209918015384651;
                            }
                            part <'C.1.1.3.4.4.2.2'> 'Part 440' {
                                attribute POIconv : String = "+";
                                attribute Ipoint : Boolean = false;
                                attribute mass : Real = 0.5156767961001024;
                                attribute sigma_mass : Real = 0.28909372274994966;
                                attribute Cx : Real = -40.47277043573558;
                                attribute sigma_Cx : Real = 28.721044428837228;
                                attribute Cy : Real = 89.64092768728733;
                                attribute sigma_Cy : Real = 28.23690002309109;
                                attribute Cz : Real = -10.617992747575045;
                                attribute sigma_Cz : Real = 29.057750463592832;
                                attribute Ixx : Real = 0.7028248822518219;
                                attribute sigma_Ixx : Real = 0.37074144170588635;
                                attribute Iyy : Real = 0.7517963562676144;
                                attribute sigma_Iyy : Real = 0.3723953238821935;
                                attribute Izz : Real = 0.6639416659528959;
                                attribute sigma_Izz : Real = 0.37017423652493897;
                                attribute Ixy : Real = 0.01839627751161948;
                                attribute sigma_Ixy : Real = 0.02351283871158888;
                                attribute Ixz : Real = 0.0070630304703299274;
                                attribute sigma_Ixz : Real = 0.022566176940390956;
                                attribute Iyz : Real = -0.046866808845210245;
                                attribute sigma_Iyz : Real = 0.02209918015384651;
                            }
                            part <'C.1.1.3.4.4.2.3'> 'Part 441' {
                                attribute POIconv : String = "-";
                                attribute Ipoint : Boolean = false;
                                attribute mass : Real = 0.5690418751575053;
                                attribute sigma_mass : Real = 0.28909372274994966;
                                attribute Cx : Real = -52.35967915505171;
                                attribute sigma_Cx : Real = 28.721044428837228;
                                attribute Cy : Real = -54.447084898129106;
                                attribute sigma_Cy : Real = 28.23690002309109;
                                attribute Cz : Real = 67.87704508751631;
                                attribute sigma_Cz : Real = 29.057750463592832;
                                attribute Ixx : Real = 0.7701473592136892;
                                attribute sigma_Ixx : Real = 0.37074144170588635;
                                attribute Iyy : Real = 0.8540617134153161;
                                attribute sigma_Iyy : Real = 0.3723953238821935;
                                attribute Izz : Real = 0.8592896575430501;
                                attribute sigma_Izz : Real = 0.37017423652493897;
                                attribute Ixy : Real = -0.001201587182770149;
                                attribute sigma_Ixy : Real = 0.02351283871158888;
                                attribute Ixz : Real = 0.006131234676026237;
                                attribute sigma_Ixz : Real = 0.022566176940390956;
                                attribute Iyz : Real = 0.0017456708924400858;
                                attribute sigma_Iyz : Real = 0.02209918015384651;
                            }
                            part <'C.1.1.3.4.4.2.4'> 'Part 442' {
                                attribute POIconv : String = "+";
                                attribute Ipoint : Boolean = false;
                                attribute mass : Real = 0.1152762261540629;
                                attribute sigma_mass : Real = 0.28909372274994966;
                                attribute Cx : Real = 16.47229455411434;
                                attribute sigma_Cx : Real = 28.721044428837228;
                                attribute Cy : Real = -3.7976374849677086;
                                attribute sigma_Cy : Real = 28.23690002309109;
                                attribute Cz : Real = 22.08794029429555;
                                attribute sigma_Cz : Real = 29.057750463592832;
                                attribute Ixx : Real = 0.11423274068471265;
                                attribute sigma_Ixx : Real = 0.37074144170588635;
                                attribute Iyy : Real = 0.13817641051214025;
                                attribute sigma_Iyy : Real = 0.3723953238821935;
                                attribute Izz : Real = 0.1327594593317718;
                                attribute sigma_Izz : Real = 0.37017423652493897;
                                attribute Ixy : Real = -0.00011505759661113631;
                                attribute sigma_Ixy : Real = 0.02351283871158888;
                                attribute Ixz : Real = 0.013558168601432892;
                                attribute sigma_Ixz : Real = 0.022566176940390956;
                                attribute Iyz : Real = 0.0020041304356723266;
                                attribute sigma_Iyz : Real = 0.02209918015384651;
                            }
                            part <'C.1.1.3.4.4.2.5'> 'Part 443' {
                                attribute POIconv : String = "+";
                                attribute Ipoint : Boolean = false;
                                attribute mass : Real = 0.2899878854730632;
                                attribute sigma_mass : Real = 0.28909372274994966;
                                attribute Cx : Real = -45.86069555953145;
                                attribute sigma_Cx : Real = 28.721044428837228;
                                attribute Cy : Real = 34.7590456251055;
                                attribute sigma_Cy : Real = 28.23690002309109;
                                attribute Cz : Real = 3.96183580160141;
                                attribute sigma_Cz : Real = 29.057750463592832;
                                attribute Ixx : Real = 0.34044218780609325;
                                attribute sigma_Ixx : Real = 0.37074144170588635;
                                attribute Iyy : Real = 0.34216827779801307;
                                attribute sigma_Iyy : Real = 0.3723953238821935;
                                attribute Izz : Real = 0.35013035150955424;
                                attribute sigma_Izz : Real = 0.37017423652493897;
                                attribute Ixy : Real = 0.005067793697219284;
                                attribute sigma_Ixy : Real = 0.02351283871158888;
                                attribute Ixz : Real = -0.018874089907912697;
                                attribute sigma_Ixz : Real = 0.022566176940390956;
                                attribute Iyz : Real = -0.0006734550510073482;
                                attribute sigma_Iyz : Real = 0.02209918015384651;
                            }
                        }
                    }
                    part <'C.1.1.3.4.5'> 'Assembly 36' {
                        attribute POIconv : String = "-";
                        attribute Ipoint : Boolean = false;
                        attribute mass : Real = 6.205432731990004;
                        attribute sigma_mass : Real = 1.081689663197327;
                        attribute Cx : Real = 21.80777878439356;
                        attribute sigma_Cx : Real = 12.898546620512901;
                        attribute Cy : Real = 4.73802671102935;
                        attribute sigma_Cy : Real = 13.979185837349068;
                        attribute Cz : Real = 13.214114863740255;
                        attribute sigma_Cz : Real = 13.056934242668042;
                        attribute Ixx : Real = 41952.09547853398;
                        attribute sigma_Ixx : Real = 12981.26755831626;
                        attribute Iyy : Real = 30445.804497181485;
                        attribute sigma_Iyy : Real = 10834.842993883482;
                        attribute Izz : Real = 40226.94952034435;
                        attribute sigma_Izz : Real = 12257.2511953779;
                        attribute Ixy : Real = 10461.248632271687;
                        attribute sigma_Ixy : Real = 5423.074927918709;
                        attribute Ixz : Real = 1423.2050484743136;
                        attribute sigma_Ixz : Real = 5209.618439246629;
                        attribute Iyz : Real = -5515.512938429425;
                        attribute sigma_Iyz : Real = 6215.932492104661;
                        part <'C.1.1.3.4.5.1'> 'Subassembly 131' {
                            attribute POIconv : String = "-";
                            attribute Ipoint : Boolean = false;
                            attribute mass : Real = 0.8933736283231992;
                            attribute sigma_mass : Real = 0.40884026350990615;
                            attribute Cx : Real = 3.8369888452199405;
                            attribute sigma_Cx : Real = 34.6251318679649;
                            attribute Cy : Real = 19.850542360869188;
                            attribute sigma_Cy : Real = 21.802271678721887;
                            attribute Cz : Real = -29.105853513972328;
                            attribute sigma_Cz : Real = 26.414692258316094;
                            attribute Ixx : Real = 987.180425474482;
                            attribute sigma_Ixx : Real = 1313.1260827333012;
                            attribute Iyy : Real = 3504.9068188207166;
                            attribute sigma_Iyy : Real = 3091.7742369300063;
                            attribute Izz : Real = 2805.737290005019;
                            attribute sigma_Izz : Real = 2617.465564277495;
                            attribute Ixy : Real = 617.8338072745888;
                            attribute sigma_Ixy : Real = 1029.5460101148024;
                            attribute Ixz : Real = 1497.4356084074398;
                            attribute sigma_Ixz : Real = 1441.6076486606273;
                            attribute Iyz : Real = -347.6788914978621;
                            attribute sigma_Iyz : Real = 607.9173185334098;
                            part <'C.1.1.3.4.5.1.1'> 'Part 444' {
                                attribute POIconv : String = "+";
                                attribute Ipoint : Boolean = false;
                                attribute mass : Real = 0.31187800780683755;
                                attribute sigma_mass : Real = 0.28909372274994966;
                                attribute Cx : Real = 78.36190196685493;
                                attribute sigma_Cx : Real = 28.721044428837228;
                                attribute Cy : Real = 2.548074722290039;
                                attribute sigma_Cy : Real = 28.23690002309109;
                                attribute Cz : Real = -71.03986721485853;
                                attribute sigma_Cz : Real = 29.057750463592832;
                                attribute Ixx : Real = 0.358766294052545;
                                attribute sigma_Ixx : Real = 0.37074144170588635;
                                attribute Iyy : Real = 0.45850768320580665;
                                attribute sigma_Iyy : Real = 0.3723953238821935;
                                attribute Izz : Real = 0.40571701567283897;
                                attribute sigma_Izz : Real = 0.37017423652493897;
                                attribute Ixy : Real = -0.002981333229521103;
                                attribute sigma_Ixy : Real = 0.02351283871158888;
                                attribute Ixz : Real = 0.018479235800641595;
                                attribute sigma_Ixz : Real = 0.022566176940390956;
                                attribute Iyz : Real = 0.009529533846192696;
                                attribute sigma_Iyz : Real = 0.02209918015384651;
                            }
                            part <'C.1.1.3.4.5.1.2'> 'Part 445' {
                                attribute POIconv : String = "-";
                                attribute Ipoint : Boolean = false;
                                attribute mass : Real = 0.5814956205163617;
                                attribute sigma_mass : Real = 0.28909372274994966;
                                attribute Cx : Real = -36.133529618382454;
                                attribute sigma_Cx : Real = 28.721044428837228;
                                attribute Cy : Real = 29.13050758652389;
                                attribute sigma_Cy : Real = 28.23690002309109;
                                attribute Cz : Real = -6.6150621976703405;
                                attribute sigma_Cz : Real = 29.057750463592832;
                                attribute Ixx : Real = 0.8092511598099693;
                                attribute sigma_Ixx : Real = 0.37074144170588635;
                                attribute Iyy : Real = 0.7007570977343255;
                                attribute sigma_Iyy : Real = 0.3723953238821935;
                                attribute Izz : Real = 0.7050345016199404;
                                attribute sigma_Izz : Real = 0.37017423652493897;
                                attribute Ixy : Real = -0.016192925273277113;
                                attribute sigma_Ixy : Real = 0.02351283871158888;
                                attribute Ixz : Real = 0.04886802956799248;
                                attribute sigma_Ixz : Real = 0.022566176940390956;
                                attribute Iyz : Real = -0.01641922366939069;
                                attribute sigma_Iyz : Real = 0.02209918015384651;
                            }
                        }
                        part <'C.1.1.3.4.5.2'> 'Subassembly 132' {
                            attribute POIconv : String = "-";
                            attribute Ipoint : Boolean = false;
                            attribute mass : Real = 2.4588028360148892;
                            attribute sigma_mass : Real = 0.6464332159373649;
                            attribute Cx : Real = 22.1259780290922;
                            attribute sigma_Cx : Real = 20.325352233653806;
                            attribute Cy : Real = -27.378347552352103;
                            attribute sigma_Cy : Real = 22.97345795141268;
                            attribute Cz : Real = 34.703241621060855;
                            attribute sigma_Cz : Real = 18.468063746962777;
                            attribute Ixx : Real = 11464.77399359534;
                            attribute sigma_Ixx : Real = 6810.859606012976;
                            attribute Iyy : Real = 10158.553793686597;
                            attribute sigma_Iyy : Real = 5753.8716196108935;
                            attribute Izz : Real = 17047.87119786616;
                            attribute sigma_Izz : Real = 7918.7683811821635;
                            attribute Ixy : Real = 5893.810147239261;
                            attribute sigma_Ixy : Real = 3410.4740273994803;
                            attribute Ixz : Real = -2680.162027062944;
                            attribute sigma_Ixz : Real = 2682.6847638772347;
                            attribute Iyz : Real = 1430.1653958820073;
                            attribute sigma_Iyz : Real = 2977.861311784377;
                            part <'C.1.1.3.4.5.2.1'> 'Part 446' {
                                attribute POIconv : String = "-";
                                attribute Ipoint : Boolean = false;
                                attribute mass : Real = 0.5228137397051323;
                                attribute sigma_mass : Real = 0.28909372274994966;
                                attribute Cx : Real = -60.0142742972821;
                                attribute sigma_Cx : Real = 28.721044428837228;
                                attribute Cy : Real = -16.18464714847505;
                                attribute sigma_Cy : Real = 28.23690002309109;
                                attribute Cz : Real = 9.75523549132049;
                                attribute sigma_Cz : Real = 29.057750463592832;
                                attribute Ixx : Real = 0.6790532206009162;
                                attribute sigma_Ixx : Real = 0.37074144170588635;
                                attribute Iyy : Real = 0.607793780746232;
                                attribute sigma_Iyy : Real = 0.3723953238821935;
                                attribute Izz : Real = 0.676490130055023;
                                attribute sigma_Izz : Real = 0.37017423652493897;
                                attribute Ixy : Real = -0.023595526019412574;
                                attribute sigma_Ixy : Real = 0.02351283871158888;
                                attribute Ixz : Real = 0.0196178674439043;
                                attribute sigma_Ixz : Real = 0.022566176940390956;
                                attribute Iyz : Real = 0.030465135507161373;
                                attribute sigma_Iyz : Real = 0.02209918015384651;
                            }
                            part <'C.1.1.3.4.5.2.2'> 'Part 447' {
                                attribute POIconv : String = "+";
                                attribute Ipoint : Boolean = false;
                                attribute mass : Real = 0.22894971508253364;
                                attribute sigma_mass : Real = 0.28909372274994966;
                                attribute Cx : Real = 5.651916330680251;
                                attribute sigma_Cx : Real = 28.721044428837228;
                                attribute Cy : Real = 83.51241177879274;
                                attribute sigma_Cy : Real = 28.23690002309109;
                                attribute Cz : Real = 71.98789604008198;
                                attribute sigma_Cz : Real = 29.057750463592832;
                                attribute Ixx : Real = 0.29055284631210637;
                                attribute sigma_Ixx : Real = 0.37074144170588635;
                                attribute Iyy : Real = 0.27634499498260595;
                                attribute sigma_Iyy : Real = 0.3723953238821935;
                                attribute Izz : Real = 0.294995404497698;
                                attribute sigma_Izz : Real = 0.37017423652493897;
                                attribute Ixy : Real = 0.01634544882887808;
                                attribute sigma_Ixy : Real = 0.02351283871158888;
                                attribute Ixz : Real = 0.007249188140548639;
                                attribute sigma_Ixz : Real = 0.022566176940390956;
                                attribute Iyz : Real = 0.014629235826602624;
                                attribute sigma_Iyz : Real = 0.02209918015384651;
                            }
                            part <'C.1.1.3.4.5.2.3'> 'Part 448' {
                                attribute POIconv : String = "+";
                                attribute Ipoint : Boolean = false;
                                attribute mass : Real = 0.6893118706266396;
                                attribute sigma_mass : Real = 0.28909372274994966;
                                attribute Cx : Real = -1.1883747298270464;
                                attribute sigma_Cx : Real = 28.721044428837228;
                                attribute Cy : Real = 24.5611316524446;
                                attribute sigma_Cy : Real = 28.23690002309109;
                                attribute Cz : Real = 12.492801202461123;
                                attribute sigma_Cz : Real = 29.057750463592832;
                                attribute Ixx : Real = 0.831046085691071;
                                attribute sigma_Ixx : Real = 0.37074144170588635;
                                attribute Iyy : Real = 0.8274859558897861;
                                attribute sigma_Iyy : Real = 0.3723953238821935;
                                attribute Izz : Real = 1.0029565028532625;
                                attribute sigma_Izz : Real = 0.37017423652493897;
                                attribute Ixy : Real = 0.009048756782681747;
                                attribute sigma_Ixy : Real = 0.02351283871158888;
                                attribute Ixz : Real = 0.053072462305126036;
                                attribute sigma_Ixz : Real = 0.022566176940390956;
                                attribute Iyz : Real = -0.006702095873235189;
                                attribute sigma_Iyz : Real = 0.02209918015384651;
                            }
                            part <'C.1.1.3.4.5.2.4'> 'Part 449' {
                                attribute POIconv : String = "+";
                                attribute Ipoint : Boolean = false;
                                attribute mass : Real = 0.9115084869794082;
                                attribute sigma_mass : Real = 0.28909372274994966;
                                attribute Cx : Real = 85.71678870357573;
                                attribute sigma_Cx : Real = 28.721044428837228;
                                attribute Cy : Real = -94.70810191705823;
                                attribute sigma_Cy : Real = 28.23690002309109;
                                attribute Cz : Real = 64.41936157643795;
                                attribute sigma_Cz : Real = 29.057750463592832;
                                attribute Ixx : Real = 1.2669812039375097;
                                attribute sigma_Ixx : Real = 0.37074144170588635;
                                attribute Iyy : Real = 1.3069677950158685;
                                attribute sigma_Iyy : Real = 0.3723953238821935;
                                attribute Izz : Real = 1.148769429126702;
                                attribute sigma_Izz : Real = 0.37017423652493897;
                                attribute Ixy : Real = 0.004238102117325041;
                                attribute sigma_Ixy : Real = 0.02351283871158888;
                                attribute Ixz : Real = 0.08339448320902551;
                                attribute sigma_Ixz : Real = 0.022566176940390956;
                                attribute Iyz : Real = 0.014340104925734794;
                                attribute sigma_Iyz : Real = 0.02209918015384651;
                            }
                            part <'C.1.1.3.4.5.2.5'> 'Part 450' {
                                attribute POIconv : String = "-";
                                attribute Ipoint : Boolean = false;
                                attribute mass : Real = 0.10621902362117544;
                                attribute sigma_mass : Real = 0.28909372274994966;
                                attribute Cx : Real = 67.53291697241366;
                                attribute sigma_Cx : Real = 28.721044428837228;
                                attribute Cy : Real = -80.77259813435376;
                                attribute sigma_Cy : Real = 28.23690002309109;
                                attribute Cz : Real = -33.73766173608601;
                                attribute sigma_Cz : Real = 29.057750463592832;
                                attribute Ixx : Real = 0.16656362489037033;
                                attribute sigma_Ixx : Real = 0.37074144170588635;
                                attribute Iyy : Real = 0.16463505561182337;
                                attribute sigma_Iyy : Real = 0.3723953238821935;
                                attribute Izz : Real = 0.17058897977468665;
                                attribute sigma_Izz : Real = 0.37017423652493897;
                                attribute Ixy : Real = 0.0009354398285409536;
                                attribute sigma_Ixy : Real = 0.02351283871158888;
                                attribute Ixz : Real = -6.876906624152896e-05;
                                attribute sigma_Ixz : Real = 0.022566176940390956;
                                attribute Iyz : Real = -0.0008291113670801317;
                                attribute sigma_Iyz : Real = 0.02209918015384651;
                            }
                        }
                        part <'C.1.1.3.4.5.3'> 'Subassembly 133' {
                            attribute POIconv : String = "-";
                            attribute Ipoint : Boolean = false;
                            attribute mass : Real = 2.0728487458424643;
                            attribute sigma_mass : Real = 0.5781874454998993;
                            attribute Cx : Real = 23.342681645168845;
                            attribute sigma_Cx : Real = 19.520717019791956;
                            attribute Cy : Real = 17.379060808774437;
                            attribute sigma_Cy : Real = 24.17906175448765;
                            attribute Cz : Real = 11.388978969253795;
                            attribute sigma_Cz : Real = 22.176574628547034;
                            attribute Ixx : Real = 19344.215357468725;
                            attribute sigma_Ixx : Real = 9018.335445055975;
                            attribute Iyy : Real = 10192.172041914328;
                            attribute sigma_Iyy : Real = 5728.613992136611;
                            attribute Izz : Real = 13704.528700599525;
                            attribute sigma_Izz : Real = 6929.232439849777;
                            attribute Ixy : Real = 4058.1121511218366;
                            attribute sigma_Ixy : Real = 3108.4707106977776;
                            attribute Ixz : Real = 2988.5771968740883;
                            attribute sigma_Ixz : Real = 2640.6568771106527;
                            attribute Iyz : Real = -9409.190743889338;
                            attribute sigma_Iyz : Real = 4477.635709172186;
                            part <'C.1.1.3.4.5.3.1'> 'Part 451' {
                                attribute POIconv : String = "-";
                                attribute Ipoint : Boolean = false;
                                attribute mass : Real = 0.24806270349677653;
                                attribute sigma_mass : Real = 0.28909372274994966;
                                attribute Cx : Real = 38.488904014229774;
                                attribute sigma_Cx : Real = 28.721044428837228;
                                attribute Cy : Real = 1.7818327993154526;
                                attribute sigma_Cy : Real = 28.23690002309109;
                                attribute Cz : Real = -5.157064041122794;
                                attribute sigma_Cz : Real = 29.057750463592832;
                                attribute Ixx : Real = 0.3199103766104747;
                                attribute sigma_Ixx : Real = 0.37074144170588635;
                                attribute Iyy : Real = 0.3451475932042683;
                                attribute sigma_Iyy : Real = 0.3723953238821935;
                                attribute Izz : Real = 0.3430850202777122;
                                attribute sigma_Izz : Real = 0.37017423652493897;
                                attribute Ixy : Real = 0.008357385415948465;
                                attribute sigma_Ixy : Real = 0.02351283871158888;
                                attribute Ixz : Real = 0.021948817821131273;
                                attribute sigma_Ixz : Real = 0.022566176940390956;
                                attribute Iyz : Real = 0.009556949759083316;
                                attribute sigma_Iyz : Real = 0.02209918015384651;
                            }
                            part <'C.1.1.3.4.5.3.2'> 'Part 452' {
                                attribute POIconv : String = "+";
                                attribute Ipoint : Boolean = false;
                                attribute mass : Real = 0.6117523147936444;
                                attribute sigma_mass : Real = 0.28909372274994966;
                                attribute Cx : Real = 65.18396865576506;
                                attribute sigma_Cx : Real = 28.721044428837228;
                                attribute Cy : Real = -89.62902100756764;
                                attribute sigma_Cy : Real = 28.23690002309109;
                                attribute Cz : Real = -73.56894188560545;
                                attribute sigma_Cz : Real = 29.057750463592832;
                                attribute Ixx : Real = 0.7836475243013408;
                                attribute sigma_Ixx : Real = 0.37074144170588635;
                                attribute Iyy : Real = 0.7817376337627282;
                                attribute sigma_Iyy : Real = 0.3723953238821935;
                                attribute Izz : Real = 0.936314847512146;
                                attribute sigma_Izz : Real = 0.37017423652493897;
                                attribute Ixy : Real = -0.002231534834657638;
                                attribute sigma_Ixy : Real = 0.02351283871158888;
                                attribute Ixz : Real = -0.010654113709594425;
                                attribute sigma_Ixz : Real = 0.022566176940390956;
                                attribute Iyz : Real = -0.018593174876273544;
                                attribute sigma_Iyz : Real = 0.02209918015384651;
                            }
                            part <'C.1.1.3.4.5.3.3'> 'Part 453' {
                                attribute POIconv : String = "-";
                                attribute Ipoint : Boolean = false;
                                attribute mass : Real = 0.9453501234266442;
                                attribute sigma_mass : Real = 0.28909372274994966;
                                attribute Cx : Real = 9.240136854350567;
                                attribute sigma_Cx : Real = 28.721044428837228;
                                attribute Cy : Real = 84.18410453014076;
                                attribute sigma_Cy : Real = 28.23690002309109;
                                attribute Cz : Real = 71.61254864186049;
                                attribute sigma_Cz : Real = 29.057750463592832;
                                attribute Ixx : Real = 1.0073219362129149;
                                attribute sigma_Ixx : Real = 0.37074144170588635;
                                attribute Iyy : Real = 1.012171959304027;
                                attribute sigma_Iyy : Real = 0.3723953238821935;
                                attribute Izz : Real = 1.1000265940111011;
                                attribute sigma_Izz : Real = 0.37017423652493897;
                                attribute Ixy : Real = 0.08542130311730473;
                                attribute sigma_Ixy : Real = 0.02351283871158888;
                                attribute Ixz : Real = 0.012987189307802322;
                                attribute sigma_Ixz : Real = 0.022566176940390956;
                                attribute Iyz : Real = 0.004717362666225057;
                                attribute sigma_Iyz : Real = 0.02209918015384651;
                            }
                            part <'C.1.1.3.4.5.3.4'> 'Part 454' {
                                attribute POIconv : String = "+";
                                attribute Ipoint : Boolean = false;
                                attribute mass : Real = 0.26768360412539915;
                                attribute sigma_mass : Real = 0.28909372274994966;
                                attribute Cx : Real = -36.51109477505088;
                                attribute sigma_Cx : Real = 28.721044428837228;
                                attribute Cy : Real = 40.45621561817825;
                                attribute sigma_Cy : Real = 28.23690002309109;
                                attribute Cz : Real = 8.196037355810404;
                                attribute sigma_Cz : Real = 29.057750463592832;
                                attribute Ixx : Real = 0.32781616604180586;
                                attribute sigma_Ixx : Real = 0.37074144170588635;
                                attribute Iyy : Real = 0.3053052767812128;
                                attribute sigma_Iyy : Real = 0.3723953238821935;
                                attribute Izz : Real = 0.33856274027143235;
                                attribute sigma_Izz : Real = 0.37017423652493897;
                                attribute Ixy : Real = -0.007622666768213576;
                                attribute sigma_Ixy : Real = 0.02351283871158888;
                                attribute Ixz : Real = -0.0045914575573862745;
                                attribute sigma_Ixz : Real = 0.022566176940390956;
                                attribute Iyz : Real = 0.007794474606989081;
                                attribute sigma_Iyz : Real = 0.02209918015384651;
                            }
                        }
                        part <'C.1.1.3.4.5.4'> 'Subassembly 134' {
                            attribute POIconv : String = "-";
                            attribute Ipoint : Boolean = false;
                            attribute mass : Real = 0.7804075218094513;
                            attribute sigma_mass : Real = 0.5007250159521434;
                            attribute Cx : Real = 37.30047817371956;
                            attribute sigma_Cx : Real = 44.3850548411799;
                            attribute Cy : Real = 55.04989122949243;
                            attribute sigma_Cy : Real = 21.65499914119633;
                            attribute Cz : Real = -1.197267843474264;
                            attribute sigma_Cz : Real = 45.97569026510458;
                            attribute Ixx : Real = 2204.631572146711;
                            attribute sigma_Ixx : Real = 2943.3111012188106;
                            attribute Iyy : Real = 3204.7762063780574;
                            attribute sigma_Iyy : Real = 5451.976958662878;
                            attribute Izz : Real = 1140.9875520810265;
                            attribute sigma_Izz : Real = 3134.4688101564125;
                            attribute Ixy : Real = 272.25975524720366;
                            attribute sigma_Ixy : Real = 774.7731231362125;
                            attribute Ixz : Real = 133.54912592095002;
                            attribute sigma_Ixz : Real = 2677.1416731937484;
                            attribute Iyz : Real = -70.79453257381967;
                            attribute sigma_Iyz : Real = 938.6046205703442;
                            part <'C.1.1.3.4.5.4.1'> 'Part 455' {
                                attribute POIconv : String = "+";
                                attribute Ipoint : Boolean = false;
                                attribute mass : Real = 0.06650748666119762;
                                attribute sigma_mass : Real = 0.28909372274994966;
                                attribute Cx : Real = -61.92862228490412;
                                attribute sigma_Cx : Real = 28.721044428837228;
                                attribute Cy : Real = 78.5804741550237;
                                attribute sigma_Cy : Real = 28.23690002309109;
                                attribute Cz : Real = -86.9897248223424;
                                attribute sigma_Cz : Real = 29.057750463592832;
                                attribute Ixx : Real = 0.06838749864555303;
                                attribute sigma_Ixx : Real = 0.37074144170588635;
                                attribute Iyy : Real = 0.06293185525826493;
                                attribute sigma_Iyy : Real = 0.3723953238821935;
                                attribute Izz : Real = 0.06802642825942584;
                                attribute sigma_Izz : Real = 0.37017423652493897;
                                attribute Ixy : Real = 0.002605432892014207;
                                attribute sigma_Ixy : Real = 0.02351283871158888;
                                attribute Ixz : Real = 0.001118479906078592;
                                attribute sigma_Ixz : Real = 0.022566176940390956;
                                attribute Iyz : Real = 0.0012674500604080187;
                                attribute sigma_Iyz : Real = 0.02209918015384651;
                            }
                            part <'C.1.1.3.4.5.4.2'> 'Part 456' {
                                attribute POIconv : String = "+";
                                attribute Ipoint : Boolean = false;
                                attribute mass : Real = 0.4733419907672796;
                                attribute sigma_mass : Real = 0.28909372274994966;
                                attribute Cx : Real = 30.664983857423067;
                                attribute sigma_Cx : Real = 28.721044428837228;
                                attribute Cy : Real = 57.449891325086355;
                                attribute sigma_Cy : Real = 28.23690002309109;
                                attribute Cz : Real = 40.5304794665426;
                                attribute sigma_Cz : Real = 29.057750463592832;
                                attribute Ixx : Real = 0.556845090183731;
                                attribute sigma_Ixx : Real = 0.37074144170588635;
                                attribute Iyy : Real = 0.5164760257118595;
                                attribute sigma_Iyy : Real = 0.3723953238821935;
                                attribute Izz : Real = 0.6222203837491571;
                                attribute sigma_Izz : Real = 0.37017423652493897;
                                attribute Ixy : Real = -0.054850706093484684;
                                attribute sigma_Ixy : Real = 0.02351283871158888;
                                attribute Ixz : Real = 0.0328379128277422;
                                attribute sigma_Ixz : Real = 0.022566176940390956;
                                attribute Iyz : Real = -0.03399197839457565;
                                attribute sigma_Iyz : Real = 0.02209918015384651;
                            }
                            part <'C.1.1.3.4.5.4.3'> 'Part 457' {
                                attribute POIconv : String = "+";
                                attribute Ipoint : Boolean = false;
                                attribute mass : Real = 0.24055804438097403;
                                attribute sigma_mass : Real = 0.28909372274994966;
                                attribute Cx : Real = 77.79106409288943;
                                attribute sigma_Cx : Real = 28.721044428837228;
                                attribute Cy : Real = 43.82191188633442;
                                attribute sigma_Cy : Real = 28.23690002309109;
                                attribute Cz : Real = -59.58506497554481;
                                attribute sigma_Cz : Real = 29.057750463592832;
                                attribute Ixx : Real = 0.3306170994872622;
                                attribute sigma_Ixx : Real = 0.37074144170588635;
                                attribute Iyy : Real = 0.30516438737166784;
                                attribute sigma_Iyy : Real = 0.3723953238821935;
                                attribute Izz : Real = 0.32654242627407176;
                                attribute sigma_Izz : Real = 0.37017423652493897;
                                attribute Ixy : Real = -0.015590895501857945;
                                attribute sigma_Ixy : Real = 0.02351283871158888;
                                attribute Ixz : Real = 0.00918350599806595;
                                attribute sigma_Ixz : Real = 0.022566176940390956;
                                attribute Iyz : Real = -0.01889154217104471;
                                attribute sigma_Iyz : Real = 0.02209918015384651;
                            }
                        }
                    }
                }
                part <'C.1.1.3.5'> 'Subsystem 10' {
                    attribute POIconv : String = "-";
                    attribute Ipoint : Boolean = false;
                    attribute mass : Real = 20.233444404111474;
                    attribute sigma_mass : Real = 1.8511030230298948;
                    attribute Cx : Real = -13.169376731375372;
                    attribute sigma_Cx : Real = 7.374205868843514;
                    attribute Cy : Real = -0.7708221472779114;
                    attribute sigma_Cy : Real = 7.374135421576577;
                    attribute Cz : Real = 10.687100195150302;
                    attribute sigma_Cz : Real = 7.445440641594884;
                    attribute Ixx : Real = 113358.01046175303;
                    attribute sigma_Ixx : Real = 21595.59717935209;
                    attribute Iyy : Real = 109629.45710082675;
                    attribute sigma_Iyy : Real = 20786.824712873553;
                    attribute Izz : Real = 115927.29943455194;
                    attribute sigma_Izz : Real = 21023.764986407245;
                    attribute Ixy : Real = -8135.412867493238;
                    attribute sigma_Ixy : Real = 9397.02885533142;
                    attribute Ixz : Real = 7569.6316673651;
                    attribute sigma_Ixz : Real = 9763.270139244802;
                    attribute Iyz : Real = -19217.99434126448;
                    attribute sigma_Iyz : Real = 10388.727155750028;
                    part <'C.1.1.3.5.1'> 'Assembly 37' {
                        attribute POIconv : String = "-";
                        attribute Ipoint : Boolean = false;
                        attribute mass : Real = 9.2505251029192;
                        attribute sigma_mass : Real = 1.2265207905297184;
                        attribute Cx : Real = -23.890544009757775;
                        attribute sigma_Cx : Real = 10.723787185786655;
                        attribute Cy : Real = -9.57217086512795;
                        attribute sigma_Cy : Real = 10.337082252134477;
                        attribute Cz : Real = 14.979791982578492;
                        attribute sigma_Cz : Real = 11.211981673125186;
                        attribute Ixx : Real = 54383.79221949015;
                        attribute sigma_Ixx : Real = 14927.25466162546;
                        attribute Iyy : Real = 64151.65987328623;
                        attribute sigma_Iyy : Real = 15512.602956328625;
                        attribute Izz : Real = 54682.40915945031;
                        attribute sigma_Izz : Real = 14090.130702773515;
                        attribute Ixy : Real = -1115.2084064320643;
                        attribute sigma_Ixy : Real = 6203.79826626381;
                        attribute Ixz : Real = 8663.664634281748;
                        attribute sigma_Ixz : Real = 7561.079693272897;
                        attribute Iyz : Real = -13741.8156654224;
                        attribute sigma_Iyz : Real = 7205.262573867297;
                        part <'C.1.1.3.5.1.1'> 'Subassembly 135' {
                            attribute POIconv : String = "-";
                            attribute Ipoint : Boolean = false;
                            attribute mass : Real = 3.2661567861572838;
                            attribute sigma_mass : Real = 0.6464332159373649;
                            attribute Cx : Real = -29.082375376604798;
                            attribute sigma_Cx : Real = 19.62746662469492;
                            attribute Cy : Real = 12.993499230485554;
                            attribute sigma_Cy : Real = 15.787391455493363;
                            attribute Cz : Real = 64.84364092663151;
                            attribute sigma_Cz : Real = 16.989478597037284;
                            attribute Ixx : Real = 12626.28905009073;
                            attribute sigma_Ixx : Real = 6335.513969799091;
                            attribute Iyy : Real = 22228.002414267827;
                            attribute sigma_Iyy : Real = 9838.721050135588;
                            attribute Izz : Real = 22468.080071907167;
                            attribute sigma_Izz : Real = 9057.373356349486;
                            attribute Ixy : Real = -2773.52028525448;
                            attribute sigma_Ixy : Real = 3960.614844039717;
                            attribute Ixz : Real = 8276.00663740346;
                            attribute sigma_Ixz : Real = 4777.867272146302;
                            attribute Iyz : Real = -590.7457236728386;
                            attribute sigma_Iyz : Real = 2934.3461990145292;
                            part <'C.1.1.3.5.1.1.1'> 'Part 458' {
                                attribute POIconv : String = "+";
                                attribute Ipoint : Boolean = false;
                                attribute mass : Real = 0.852228607890429;
                                attribute sigma_mass : Real = 0.28909372274994966;
                                attribute Cx : Real = 11.89677082002163;
                                attribute sigma_Cx : Real = 28.721044428837228;
                                attribute Cy : Real = 78.33172748796642;
                                attribute sigma_Cy : Real = 28.23690002309109;
                                attribute Cz : Real = 78.24640246108174;
                                attribute sigma_Cz : Real = 29.057750463592832;
                                attribute Ixx : Real = 1.0191807238627326;
                                attribute sigma_Ixx : Real = 0.37074144170588635;
                                attribute Iyy : Real = 0.9027187720533281;
                                attribute sigma_Iyy : Real = 0.3723953238821935;
                                attribute Izz : Real = 1.0860216896509165;
                                attribute sigma_Izz : Real = 0.37017423652493897;
                                attribute Ixy : Real = 0.0816520581507543;
                                attribute sigma_Ixy : Real = 0.02351283871158888;
                                attribute Ixz : Real = 0.013254648772264083;
                                attribute sigma_Ixz : Real = 0.022566176940390956;
                                attribute Iyz : Real = 0.01379489756306939;
                                attribute sigma_Iyz : Real = 0.02209918015384651;
                            }
                            part <'C.1.1.3.5.1.1.2'> 'Part 459' {
                                attribute POIconv : String = "+";
                                attribute Ipoint : Boolean = false;
                                attribute mass : Real = 0.9781517378294374;
                                attribute sigma_mass : Real = 0.28909372274994966;
                                attribute Cx : Real = -85.21695537492633;
                                attribute sigma_Cx : Real = 28.721044428837228;
                                attribute Cy : Real = -35.638842917978764;
                                attribute sigma_Cy : Real = 28.23690002309109;
                                attribute Cz : Real = 96.02976464666426;
                                attribute sigma_Cz : Real = 29.057750463592832;
                                attribute Ixx : Real = 1.1894279637885954;
                                attribute sigma_Ixx : Real = 0.37074144170588635;
                                attribute Iyy : Real = 1.133324540379323;
                                attribute sigma_Iyy : Real = 0.3723953238821935;
                                attribute Izz : Real = 1.2133297388067426;
                                attribute sigma_Izz : Real = 0.37017423652493897;
                                attribute Ixy : Real = 0.023528587805677785;
                                attribute sigma_Ixy : Real = 0.02351283871158888;
                                attribute Ixz : Real = -0.0757935796150287;
                                attribute sigma_Ixz : Real = 0.022566176940390956;
                                attribute Iyz : Real = 0.020193049044117204;
                                attribute sigma_Iyz : Real = 0.02209918015384651;
                            }
                            part <'C.1.1.3.5.1.1.3'> 'Part 460' {
                                attribute POIconv : String = "+";
                                attribute Ipoint : Boolean = false;
                                attribute mass : Real = 0.7059542618249544;
                                attribute sigma_mass : Real = 0.28909372274994966;
                                attribute Cx : Real = -95.21634955890477;
                                attribute sigma_Cx : Real = 28.721044428837228;
                                attribute Cy : Real = 19.21276869252324;
                                attribute sigma_Cy : Real = 28.23690002309109;
                                attribute Cz : Real = 86.51930494233966;
                                attribute sigma_Cz : Real = 29.057750463592832;
                                attribute Ixx : Real = 0.7967217870028317;
                                attribute sigma_Ixx : Real = 0.37074144170588635;
                                attribute Iyy : Real = 0.7171490701438248;
                                attribute sigma_Iyy : Real = 0.3723953238821935;
                                attribute Izz : Real = 0.7711234643088769;
                                attribute sigma_Izz : Real = 0.37017423652493897;
                                attribute Ixy : Real = 0.016859116287476;
                                attribute sigma_Ixy : Real = 0.02351283871158888;
                                attribute Ixz : Real = 0.00723925450695739;
                                attribute sigma_Ixz : Real = 0.022566176940390956;
                                attribute Iyz : Real = -0.017748259546424717;
                                attribute sigma_Iyz : Real = 0.02209918015384651;
                            }
                            part <'C.1.1.3.5.1.1.4'> 'Part 461' {
                                attribute POIconv : String = "-";
                                attribute Ipoint : Boolean = false;
                                attribute mass : Real = 0.1611299698406365;
                                attribute sigma_mass : Real = 0.28909372274994966;
                                attribute Cx : Real = -44.13274098187685;
                                attribute sigma_Cx : Real = 28.721044428837228;
                                attribute Cy : Real = 29.771981993690133;
                                attribute sigma_Cy : Real = 28.23690002309109;
                                attribute Cz : Real = 22.40537218749523;
                                attribute sigma_Cz : Real = 29.057750463592832;
                                attribute Ixx : Real = 0.16725321386047218;
                                attribute sigma_Ixx : Real = 0.37074144170588635;
                                attribute Iyy : Real = 0.1686967579328828;
                                attribute sigma_Iyy : Real = 0.3723953238821935;
                                attribute Izz : Real = 0.17814873261443437;
                                attribute sigma_Izz : Real = 0.37017423652493897;
                                attribute Ixy : Real = -0.010627065479733437;
                                attribute sigma_Ixy : Real = 0.02351283871158888;
                                attribute Ixz : Real = -0.008583138368446852;
                                attribute sigma_Ixz : Real = 0.022566176940390956;
                                attribute Iyz : Real = -0.0069019785610489335;
                                attribute sigma_Iyz : Real = 0.02209918015384651;
                            }
                            part <'C.1.1.3.5.1.1.5'> 'Part 462' {
                                attribute POIconv : String = "+";
                                attribute Ipoint : Boolean = false;
                                attribute mass : Real = 0.5686922087718267;
                                attribute sigma_mass : Real = 0.28909372274994966;
                                attribute Cx : Real = 92.41948639973998;
                                attribute sigma_Cx : Real = 28.721044428837228;
                                attribute Cy : Real = -13.74738677404821;
                                attribute sigma_Cy : Real = 28.23690002309109;
                                attribute Cz : Real = -23.76479711383581;
                                attribute sigma_Cz : Real = 29.057750463592832;
                                attribute Ixx : Real = 0.7716076793871112;
                                attribute sigma_Ixx : Real = 0.37074144170588635;
                                attribute Iyy : Real = 0.7763645387377982;
                                attribute sigma_Iyy : Real = 0.3723953238821935;
                                attribute Izz : Real = 0.8898418486430881;
                                attribute sigma_Izz : Real = 0.37017423652493897;
                                attribute Ixy : Real = 0.0008876595156627811;
                                attribute sigma_Ixy : Real = 0.02351283871158888;
                                attribute Ixz : Real = -0.0007235803758987441;
                                attribute sigma_Ixz : Real = 0.022566176940390956;
                                attribute Iyz : Real = 0.00020708640397413224;
                                attribute sigma_Iyz : Real = 0.02209918015384651;
                            }
                        }
                        part <'C.1.1.3.5.1.2'> 'Subassembly 136' {
                            attribute POIconv : String = "-";
                            attribute Ipoint : Boolean = false;
                            attribute mass : Real = 1.1519550417771098;
                            attribute sigma_mass : Real = 0.5007250159521434;
                            attribute Cx : Real = -56.565916012043765;
                            attribute sigma_Cx : Real = 19.787842330770612;
                            attribute Cy : Real = -33.44450008835592;
                            attribute sigma_Cy : Real = 31.964311157068817;
                            attribute Cz : Real = -23.396138036652722;
                            attribute sigma_Cz : Real = 32.35606164643526;
                            attribute Ixx : Real = 5899.12981257622;
                            attribute sigma_Ixx : Real = 6017.523363657984;
                            attribute Iyy : Real = 3056.5172594608284;
                            attribute sigma_Iyy : Real = 3332.3046240924173;
                            attribute Izz : Real = 3241.09739138675;
                            attribute sigma_Izz : Real = 3508.442060326211;
                            attribute Ixy : Real = -736.4544121218422;
                            attribute sigma_Ixy : Real = 1151.18303169823;
                            attribute Ixz : Real = -636.5758695667799;
                            attribute sigma_Ixz : Real = 1075.2775955265788;
                            attribute Iyz : Real = -2863.4575078536704;
                            attribute sigma_Iyz : Real = 3004.5637781255296;
                            part <'C.1.1.3.5.1.2.1'> 'Part 463' {
                                attribute POIconv : String = "+";
                                attribute Ipoint : Boolean = false;
                                attribute mass : Real = 0.24279296651482582;
                                attribute sigma_mass : Real = 0.28909372274994966;
                                attribute Cx : Real = -33.822951605543494;
                                attribute sigma_Cx : Real = 28.721044428837228;
                                attribute Cy : Real = 65.04495250992477;
                                attribute sigma_Cy : Real = 28.23690002309109;
                                attribute Cz : Real = 72.46500812470913;
                                attribute sigma_Cz : Real = 29.057750463592832;
                                attribute Ixx : Real = 0.31572226114769975;
                                attribute sigma_Ixx : Real = 0.37074144170588635;
                                attribute Iyy : Real = 0.29345039114185656;
                                attribute sigma_Iyy : Real = 0.3723953238821935;
                                attribute Izz : Real = 0.311584443280575;
                                attribute sigma_Izz : Real = 0.37017423652493897;
                                attribute Ixy : Real = 0.02740623490253343;
                                attribute sigma_Ixy : Real = 0.02351283871158888;
                                attribute Ixz : Real = 0.01565162285770408;
                                attribute sigma_Ixz : Real = 0.022566176940390956;
                                attribute Iyz : Real = 0.02542376696352857;
                                attribute sigma_Iyz : Real = 0.02209918015384651;
                            }
                            part <'C.1.1.3.5.1.2.2'> 'Part 464' {
                                attribute POIconv : String = "-";
                                attribute Ipoint : Boolean = false;
                                attribute mass : Real = 0.6697904606887605;
                                attribute sigma_mass : Real = 0.28909372274994966;
                                attribute Cx : Real = -66.57535820268095;
                                attribute sigma_Cx : Real = 28.721044428837228;
                                attribute Cy : Real = -64.48161150328815;
                                attribute sigma_Cy : Real = 28.23690002309109;
                                attribute Cz : Real = -45.590148493647575;
                                attribute sigma_Cz : Real = 29.057750463592832;
                                attribute Ixx : Real = 0.9672626224717293;
                                attribute sigma_Ixx : Real = 0.37074144170588635;
                                attribute Iyy : Real = 0.9701426491373292;
                                attribute sigma_Iyy : Real = 0.3723953238821935;
                                attribute Izz : Real = 0.893705853556378;
                                attribute sigma_Izz : Real = 0.37017423652493897;
                                attribute Ixy : Real = 0.0456289932356362;
                                attribute sigma_Ixy : Real = 0.02351283871158888;
                                attribute Ixz : Real = 0.02610961099341013;
                                attribute sigma_Ixz : Real = 0.022566176940390956;
                                attribute Iyz : Real = -0.01801196703694679;
                                attribute sigma_Iyz : Real = 0.02209918015384651;
                            }
                            part <'C.1.1.3.5.1.2.3'> 'Part 465' {
                                attribute POIconv : String = "-";
                                attribute Ipoint : Boolean = false;
                                attribute mass : Real = 0.2393716145735234;
                                attribute sigma_mass : Real = 0.28909372274994966;
                                attribute Cx : Real = -51.6263282392174;
                                attribute sigma_Cx : Real = 28.721044428837228;
                                attribute Cy : Real = -46.496111154556274;
                                attribute sigma_Cy : Real = 28.23690002309109;
                                attribute Cz : Real = -58.52593225426972;
                                attribute sigma_Cz : Real = 29.057750463592832;
                                attribute Ixx : Real = 0.2845513937057712;
                                attribute sigma_Ixx : Real = 0.37074144170588635;
                                attribute Iyy : Real = 0.28235374934067803;
                                attribute sigma_Iyy : Real = 0.3723953238821935;
                                attribute Izz : Real = 0.2431978331049264;
                                attribute sigma_Izz : Real = 0.37017423652493897;
                                attribute Ixy : Real = 0.017268125739333035;
                                attribute sigma_Ixy : Real = 0.02351283871158888;
                                attribute Ixz : Real = -0.0008433170627217269;
                                attribute sigma_Ixz : Real = 0.022566176940390956;
                                attribute Iyz : Real = -0.0008812957676617741;
                                attribute sigma_Iyz : Real = 0.02209918015384651;
                            }
                        }
                        part <'C.1.1.3.5.1.3'> 'Subassembly 137' {
                            attribute POIconv : String = "-";
                            attribute Ipoint : Boolean = false;
                            attribute mass : Real = 2.1511481392625718;
                            attribute sigma_mass : Real = 0.5781874454998993;
                            attribute Cx : Real = -1.9431994267345665;
                            attribute sigma_Cx : Real = 22.16545868331777;
                            attribute Cy : Real = -38.66263611859805;
                            attribute sigma_Cy : Real = 22.24601444600116;
                            attribute Cz : Real = -42.23405356191207;
                            attribute sigma_Cz : Real = 17.665877373631183;
                            attribute Ixx : Real = 5703.996830264714;
                            attribute sigma_Ixx : Real = 5564.375476018459;
                            attribute Iyy : Real = 10184.186603776963;
                            attribute sigma_Iyy : Real = 5466.771663181834;
                            attribute Izz : Real = 13064.319629084617;
                            attribute sigma_Izz : Real = 7099.741771788375;
                            attribute Ixy : Real = 1814.098410671545;
                            attribute sigma_Ixy : Real = 2789.665103892541;
                            attribute Ixz : Real = 1134.0622165344867;
                            attribute sigma_Ixz : Real = 2438.985512824044;
                            attribute Iyz : Real = 1886.4790046135051;
                            attribute sigma_Iyz : Real = 2319.083712381474;
                            part <'C.1.1.3.5.1.3.1'> 'Part 466' {
                                attribute POIconv : String = "+";
                                attribute Ipoint : Boolean = false;
                                attribute mass : Real = 0.7402364585334436;
                                attribute sigma_mass : Real = 0.28909372274994966;
                                attribute Cx : Real = -44.25944513641298;
                                attribute sigma_Cx : Real = 28.721044428837228;
                                attribute Cy : Real = -48.235469264909625;
                                attribute sigma_Cy : Real = 28.23690002309109;
                                attribute Cz : Real = -18.56502965092659;
                                attribute sigma_Cz : Real = 29.057750463592832;
                                attribute Ixx : Real = 0.938604890194411;
                                attribute sigma_Ixx : Real = 0.37074144170588635;
                                attribute Iyy : Real = 0.961304647707503;
                                attribute sigma_Iyy : Real = 0.3723953238821935;
                                attribute Izz : Real = 0.6908370035330155;
                                attribute sigma_Izz : Real = 0.37017423652493897;
                                attribute Ixy : Real = 0.0025464797714238735;
                                attribute sigma_Ixy : Real = 0.02351283871158888;
                                attribute Ixz : Real = -0.02604349214569731;
                                attribute sigma_Ixz : Real = 0.022566176940390956;
                                attribute Iyz : Real = 0.0040440490153330465;
                                attribute sigma_Iyz : Real = 0.02209918015384651;
                            }
                            part <'C.1.1.3.5.1.3.2'> 'Part 467' {
                                attribute POIconv : String = "+";
                                attribute Ipoint : Boolean = false;
                                attribute mass : Real = 0.43324308657250366;
                                attribute sigma_mass : Real = 0.28909372274994966;
                                attribute Cx : Real = -55.33792055211961;
                                attribute sigma_Cx : Real = 28.721044428837228;
                                attribute Cy : Real = -58.96467235870659;
                                attribute sigma_Cy : Real = 28.23690002309109;
                                attribute Cz : Real = -30.408555176109076;
                                attribute sigma_Cz : Real = 29.057750463592832;
                                attribute Ixx : Real = 0.5624938775724406;
                                attribute sigma_Ixx : Real = 0.37074144170588635;
                                attribute Iyy : Real = 0.5999818993347447;
                                attribute sigma_Iyy : Real = 0.3723953238821935;
                                attribute Izz : Real = 0.6101723224944161;
                                attribute sigma_Izz : Real = 0.37017423652493897;
                                attribute Ixy : Real = 0.003481346388634529;
                                attribute sigma_Ixy : Real = 0.02351283871158888;
                                attribute Ixz : Real = -0.005472061181803927;
                                attribute sigma_Ixz : Real = 0.022566176940390956;
                                attribute Iyz : Real = 0.05298425613091419;
                                attribute sigma_Iyz : Real = 0.02209918015384651;
                            }
                            part <'C.1.1.3.5.1.3.3'> 'Part 468' {
                                attribute POIconv : String = "-";
                                attribute Ipoint : Boolean = false;
                                attribute mass : Real = 0.7111286660346668;
                                attribute sigma_mass : Real = 0.28909372274994966;
                                attribute Cx : Real = 88.6565619148314;
                                attribute sigma_Cx : Real = 28.721044428837228;
                                attribute Cy : Real = -60.5176470708102;
                                attribute sigma_Cy : Real = 28.23690002309109;
                                attribute Cz : Real = -52.8477877844125;
                                attribute sigma_Cz : Real = 29.057750463592832;
                                attribute Ixx : Real = 0.976328887157829;
                                attribute sigma_Ixx : Real = 0.37074144170588635;
                                attribute Iyy : Real = 0.9515660805855486;
                                attribute sigma_Iyy : Real = 0.3723953238821935;
                                attribute Izz : Real = 1.0701742767975397;
                                attribute sigma_Izz : Real = 0.37017423652493897;
                                attribute Ixy : Real = 0.0013663381044850594;
                                attribute sigma_Ixy : Real = 0.02351283871158888;
                                attribute Ixz : Real = -0.012915727076441598;
                                attribute sigma_Ixz : Real = 0.022566176940390956;
                                attribute Iyz : Real = -0.011604368292494206;
                                attribute sigma_Iyz : Real = 0.02209918015384651;
                            }
                            part <'C.1.1.3.5.1.3.4'> 'Part 469' {
                                attribute POIconv : String = "-";
                                attribute Ipoint : Boolean = false;
                                attribute mass : Real = 0.2665399281219579;
                                attribute sigma_mass : Real = 0.28909372274994966;
                                attribute Cx : Real = -39.35285075567663;
                                attribute sigma_Cx : Real = 28.721044428837228;
                                attribute Cy : Real = 79.23190207220614;
                                attribute sigma_Cy : Real = 28.23690002309109;
                                attribute Cz : Real = -98.87194382026792;
                                attribute sigma_Cz : Real = 29.057750463592832;
                                attribute Ixx : Real = 0.36533245129072295;
                                attribute sigma_Ixx : Real = 0.37074144170588635;
                                attribute Iyy : Real = 0.38399999003229224;
                                attribute sigma_Iyy : Real = 0.3723953238821935;
                                attribute Izz : Real = 0.3304229946885984;
                                attribute sigma_Izz : Real = 0.37017423652493897;
                                attribute Ixy : Real = -0.014928380362488308;
                                attribute sigma_Ixy : Real = 0.02351283871158888;
                                attribute Ixz : Real = -0.00034931409991713184;
                                attribute sigma_Ixz : Real = 0.022566176940390956;
                                attribute Iyz : Real = 0.0006385616678204783;
                                attribute sigma_Iyz : Real = 0.02209918015384651;
                            }
                        }
                        part <'C.1.1.3.5.1.4'> 'Subassembly 138' {
                            attribute POIconv : String = "-";
                            attribute Ipoint : Boolean = false;
                            attribute mass : Real = 1.3187348448268603;
                            attribute sigma_mass : Real = 0.5781874454998993;
                            attribute Cx : Real = -22.873706617702524;
                            attribute sigma_Cx : Real = 28.239922685282355;
                            attribute Cy : Real = 1.908975543624859;
                            attribute sigma_Cy : Real = 20.713455645133013;
                            attribute Cz : Real = 30.59484632050752;
                            attribute sigma_Cz : Real = 19.74571362829424;
                            attribute Ixx : Real = 1165.2140764506842;
                            attribute sigma_Ixx : Real = 1526.3770672185435;
                            attribute Iyy : Real = 3622.7075169135996;
                            attribute sigma_Iyy : Real = 3221.4400319970478;
                            attribute Izz : Real = 4497.627064649266;
                            attribute sigma_Izz : Real = 3803.488695719692;
                            attribute Ixy : Real = 1878.308175756109;
                            attribute sigma_Ixy : Real = 1710.625117027363;
                            attribute Ixz : Real = 51.97202686655861;
                            attribute sigma_Ixz : Real = 1111.7945125234621;
                            attribute Iyz : Real = -3.5741680154432167;
                            attribute sigma_Iyz : Real = 645.5193717917593;
                            part <'C.1.1.3.5.1.4.1'> 'Part 470' {
                                attribute POIconv : String = "+";
                                attribute Ipoint : Boolean = false;
                                attribute mass : Real = 0.05379393326677382;
                                attribute sigma_mass : Real = 0.28909372274994966;
                                attribute Cx : Real = 3.362171445041895;
                                attribute sigma_Cx : Real = 28.721044428837228;
                                attribute Cy : Real = -19.867231836542487;
                                attribute sigma_Cy : Real = 28.23690002309109;
                                attribute Cz : Real = 78.27592073008418;
                                attribute sigma_Cz : Real = 29.057750463592832;
                                attribute Ixx : Real = 0.059512283110862194;
                                attribute sigma_Ixx : Real = 0.37074144170588635;
                                attribute Iyy : Real = 0.057284198431538993;
                                attribute sigma_Iyy : Real = 0.3723953238821935;
                                attribute Izz : Real = 0.06422225600541613;
                                attribute sigma_Izz : Real = 0.37017423652493897;
                                attribute Ixy : Real = 0.0021444276580470847;
                                attribute sigma_Ixy : Real = 0.02351283871158888;
                                attribute Ixz : Real = -0.0018989226702066705;
                                attribute sigma_Ixz : Real = 0.022566176940390956;
                                attribute Iyz : Real = -0.0025391449245142925;
                                attribute sigma_Iyz : Real = 0.02209918015384651;
                            }
                            part <'C.1.1.3.5.1.4.2'> 'Part 471' {
                                attribute POIconv : String = "-";
                                attribute Ipoint : Boolean = false;
                                attribute mass : Real = 0.2673411031479482;
                                attribute sigma_mass : Real = 0.28909372274994966;
                                attribute Cx : Real = 63.81350485607982;
                                attribute sigma_Cx : Real = 28.721044428837228;
                                attribute Cy : Real = -45.22587857209146;
                                attribute sigma_Cy : Real = 28.23690002309109;
                                attribute Cz : Real = 28.4212589263916;
                                attribute sigma_Cz : Real = 29.057750463592832;
                                attribute Ixx : Real = 0.3347281847176712;
                                attribute sigma_Ixx : Real = 0.37074144170588635;
                                attribute Iyy : Real = 0.31812458275417416;
                                attribute sigma_Iyy : Real = 0.3723953238821935;
                                attribute Izz : Real = 0.3747686086436962;
                                attribute sigma_Izz : Real = 0.37017423652493897;
                                attribute Ixy : Real = 0.01267528623893561;
                                attribute sigma_Ixy : Real = 0.02351283871158888;
                                attribute Ixz : Real = -0.024089665931105612;
                                attribute sigma_Ixz : Real = 0.022566176940390956;
                                attribute Iyz : Real = 0.006258429926214659;
                                attribute sigma_Iyz : Real = 0.02209918015384651;
                            }
                            part <'C.1.1.3.5.1.4.3'> 'Part 472' {
                                attribute POIconv : String = "+";
                                attribute Ipoint : Boolean = false;
                                attribute mass : Real = 0.4736474926432129;
                                attribute sigma_mass : Real = 0.28909372274994966;
                                attribute Cx : Real = -17.277435772120953;
                                attribute sigma_Cx : Real = 28.721044428837228;
                                attribute Cy : Real = 0.4694958683103323;
                                attribute sigma_Cy : Real = 28.23690002309109;
                                attribute Cz : Real = 24.28442914970219;
                                attribute sigma_Cz : Real = 29.057750463592832;
                                attribute Ixx : Real = 0.6336127418221724;
                                attribute sigma_Ixx : Real = 0.37074144170588635;
                                attribute Iyy : Real = 0.6260988087031966;
                                attribute sigma_Iyy : Real = 0.3723953238821935;
                                attribute Izz : Real = 0.5526634153011218;
                                attribute sigma_Izz : Real = 0.37017423652493897;
                                attribute Ixy : Real = 0.005648930516605661;
                                attribute sigma_Ixy : Real = 0.02351283871158888;
                                attribute Ixz : Real = 0.025454765069569403;
                                attribute sigma_Ixz : Real = 0.022566176940390956;
                                attribute Iyz : Real = 0.049651689126243986;
                                attribute sigma_Iyz : Real = 0.02209918015384651;
                            }
                            part <'C.1.1.3.5.1.4.4'> 'Part 473' {
                                attribute POIconv : String = "-";
                                attribute Ipoint : Boolean = false;
                                attribute mass : Real = 0.5239523157689254;
                                attribute sigma_mass : Real = 0.28909372274994966;
                                attribute Cx : Real = -74.857531581074;
                                attribute sigma_Cx : Real = 28.721044428837228;
                                attribute Cy : Real = 29.496061708778143;
                                attribute sigma_Cy : Real = 28.23690002309109;
                                attribute Cz : Real = 32.513055205345154;
                                attribute sigma_Cz : Real = 29.057750463592832;
                                attribute Ixx : Real = 0.6408368683918888;
                                attribute sigma_Ixx : Real = 0.37074144170588635;
                                attribute Iyy : Real = 0.6260877703208927;
                                attribute sigma_Iyy : Real = 0.3723953238821935;
                                attribute Izz : Real = 0.7139552121810759;
                                attribute sigma_Izz : Real = 0.37017423652493897;
                                attribute Ixy : Real = 0.010740171506611605;
                                attribute sigma_Ixy : Real = 0.02351283871158888;
                                attribute Ixz : Real = -0.0326633502036774;
                                attribute sigma_Ixz : Real = 0.022566176940390956;
                                attribute Iyz : Real = 0.030185392793024807;
                                attribute sigma_Iyz : Real = 0.02209918015384651;
                            }
                        }
                        part <'C.1.1.3.5.1.5'> 'Subassembly 139' {
                            attribute POIconv : String = "-";
                            attribute Ipoint : Boolean = false;
                            attribute mass : Real = 1.3625302908953745;
                            attribute sigma_mass : Real = 0.40884026350990615;
                            attribute Cx : Real = -19.45397004892185;
                            attribute sigma_Cx : Real = 24.424909646967215;
                            attribute Cy : Real = -8.666395873235054;
                            attribute sigma_Cy : Real = 27.560927725905966;
                            attribute Cz : Real = 3.110359406823635;
                            attribute sigma_Cz : Real = 28.977727463717635;
                            attribute Ixx : Real = 7301.543002128716;
                            attribute sigma_Ixx : Real = 5171.838646687233;
                            attribute Iyy : Real = 5305.320286781226;
                            attribute sigma_Iyy : Real = 4133.291658739733;
                            attribute Izz : Real = 4713.9530099519725;
                            attribute sigma_Izz : Real = 3759.522451386126;
                            attribute Ixy : Real = -2134.2739431962955;
                            attribute sigma_Ixy : Real = 1823.4637132379808;
                            attribute Ixz : Real = -2314.857862728042;
                            attribute sigma_Ixz : Real = 1959.088942071285;
                            attribute Iyz : Real = -3637.9740616523095;
                            attribute sigma_Iyz : Real = 2578.7156382162357;
                            part <'C.1.1.3.5.1.5.1'> 'Part 474' {
                                attribute POIconv : String = "+";
                                attribute Ipoint : Boolean = false;
                                attribute mass : Real = 0.4162971959328279;
                                attribute sigma_mass : Real = 0.28909372274994966;
                                attribute Cx : Real = -67.05261403694749;
                                attribute sigma_Cx : Real = 28.721044428837228;
                                attribute Cy : Real = -83.46742051653564;
                                attribute sigma_Cy : Real = 28.23690002309109;
                                attribute Cz : Real = -78.02020902745426;
                                attribute sigma_Cz : Real = 29.057750463592832;
                                attribute Ixx : Real = 0.5308111760083822;
                                attribute sigma_Ixx : Real = 0.37074144170588635;
                                attribute Iyy : Real = 0.43273314828348447;
                                attribute sigma_Iyy : Real = 0.3723953238821935;
                                attribute Izz : Real = 0.5073523344840073;
                                attribute sigma_Izz : Real = 0.37017423652493897;
                                attribute Ixy : Real = -0.02496227537438398;
                                attribute sigma_Ixy : Real = 0.02351283871158888;
                                attribute Ixz : Real = -0.013729279060180961;
                                attribute sigma_Ixz : Real = 0.022566176940390956;
                                attribute Iyz : Real = 0.05013582958418038;
                                attribute sigma_Iyz : Real = 0.02209918015384651;
                            }
                            part <'C.1.1.3.5.1.5.2'> 'Part 475' {
                                attribute POIconv : String = "-";
                                attribute Ipoint : Boolean = false;
                                attribute mass : Real = 0.9462330949625466;
                                attribute sigma_mass : Real = 0.28909372274994966;
                                attribute Cx : Real = 1.4871512539684772;
                                attribute sigma_Cx : Real = 28.721044428837228;
                                attribute Cy : Real = 24.242468737065792;
                                attribute sigma_Cy : Real = 28.23690002309109;
                                attribute Cz : Real = 38.80391982384026;
                                attribute sigma_Cz : Real = 29.057750463592832;
                                attribute Ixx : Real = 1.316600994963291;
                                attribute sigma_Ixx : Real = 0.37074144170588635;
                                attribute Iyy : Real = 1.0914832897109266;
                                attribute sigma_Iyy : Real = 0.3723953238821935;
                                attribute Izz : Real = 1.2902879760838417;
                                attribute sigma_Izz : Real = 0.37017423652493897;
                                attribute Ixy : Real = -0.007844296853939715;
                                attribute sigma_Ixy : Real = 0.02351283871158888;
                                attribute Ixz : Real = 0.01978579195004356;
                                attribute sigma_Ixz : Real = 0.022566176940390956;
                                attribute Iyz : Real = -0.08401086901832105;
                                attribute sigma_Iyz : Real = 0.02209918015384651;
                            }
                        }
                    }
                    part <'C.1.1.3.5.2'> 'Assembly 38' {
                        attribute POIconv : String = "-";
                        attribute Ipoint : Boolean = false;
                        attribute mass : Real = 6.183674312149407;
                        attribute sigma_mass : Real = 1.1563748909997986;
                        attribute Cx : Real = 1.908702105605684;
                        attribute sigma_Cx : Real = 14.657085846617315;
                        attribute Cy : Real = 10.271409647453892;
                        attribute sigma_Cy : Real = 14.848441150503856;
                        attribute Cz : Real = 5.369495200833816;
                        attribute sigma_Cz : Real = 14.173620205047929;
                        attribute Ixx : Real = 35436.247158826765;
                        attribute sigma_Ixx : Real = 12959.848480476137;
                        attribute Iyy : Real = 28409.177382695976;
                        attribute sigma_Iyy : Real = 11668.8163963031;
                        attribute Izz : Real = 41277.93577179713;
                        attribute sigma_Izz : Real = 13369.286223082754;
                        attribute Ixy : Real = -3019.018906075174;
                        attribute sigma_Ixy : Real = 5915.885572050362;
                        attribute Ixz : Real = -3103.049202314926;
                        attribute sigma_Ixz : Real = 5043.913479397659;
                        attribute Iyz : Real = -4027.3761949984973;
                        attribute sigma_Iyz : Real = 6178.815071400394;
                        part <'C.1.1.3.5.2.1'> 'Subassembly 140' {
                            attribute POIconv : String = "-";
                            attribute Ipoint : Boolean = false;
                            attribute mass : Real = 1.9572807194809432;
                            attribute sigma_mass : Real = 0.6464332159373649;
                            attribute Cx : Real = 40.19987047608272;
                            attribute sigma_Cx : Real = 19.53028664150906;
                            attribute Cy : Real = -19.12273692794425;
                            attribute sigma_Cy : Real = 24.37965944552952;
                            attribute Cz : Real = -1.3780732316953985;
                            attribute sigma_Cz : Real = 24.92849829638344;
                            attribute Ixx : Real = 7667.853266387087;
                            attribute sigma_Ixx : Real = 5807.938964654445;
                            attribute Iyy : Real = 4394.05509052396;
                            attribute sigma_Iyy : Real = 4572.777382157332;
                            attribute Izz : Real = 6239.275027467639;
                            attribute sigma_Izz : Real = 4777.341830121051;
                            attribute Ixy : Real = 766.3215079421753;
                            attribute sigma_Ixy : Real = 2154.7765072206107;
                            attribute Ixz : Real = -1184.5295705475191;
                            attribute sigma_Ixz : Real = 1836.4537192614403;
                            attribute Iyz : Real = 282.6462459501736;
                            attribute sigma_Iyz : Real = 2332.7972251551128;
                            part <'C.1.1.3.5.2.1.1'> 'Part 476' {
                                attribute POIconv : String = "+";
                                attribute Ipoint : Boolean = false;
                                attribute mass : Real = 0.2124007968043443;
                                attribute sigma_mass : Real = 0.28909372274994966;
                                attribute Cx : Real = -25.68104132078588;
                                attribute sigma_Cx : Real = 28.721044428837228;
                                attribute Cy : Real = 54.07387805171311;
                                attribute sigma_Cy : Real = 28.23690002309109;
                                attribute Cz : Real = -76.66985411196947;
                                attribute sigma_Cz : Real = 29.057750463592832;
                                attribute Ixx : Real = 0.2732004462099619;
                                attribute sigma_Ixx : Real = 0.37074144170588635;
                                attribute Iyy : Real = 0.24200968129454017;
                                attribute sigma_Iyy : Real = 0.3723953238821935;
                                attribute Izz : Real = 0.2720603545976912;
                                attribute sigma_Izz : Real = 0.37017423652493897;
                                attribute Ixy : Real = -0.011968646694734547;
                                attribute sigma_Ixy : Real = 0.02351283871158888;
                                attribute Ixz : Real = -0.016712456410657356;
                                attribute sigma_Ixz : Real = 0.022566176940390956;
                                attribute Iyz : Real = -0.002182925168597428;
                                attribute sigma_Iyz : Real = 0.02209918015384651;
                            }
                            part <'C.1.1.3.5.2.1.2'> 'Part 477' {
                                attribute POIconv : String = "-";
                                attribute Ipoint : Boolean = false;
                                attribute mass : Real = 0.8352115565084387;
                                attribute sigma_mass : Real = 0.28909372274994966;
                                attribute Cx : Real = 34.49557917192578;
                                attribute sigma_Cx : Real = 28.721044428837228;
                                attribute Cy : Real = -26.44871873781085;
                                attribute sigma_Cy : Real = 28.23690002309109;
                                attribute Cz : Real = 25.456016091629863;
                                attribute sigma_Cz : Real = 29.057750463592832;
                                attribute Ixx : Real = 0.7302139381672937;
                                attribute sigma_Ixx : Real = 0.37074144170588635;
                                attribute Iyy : Real = 0.9761035480191154;
                                attribute sigma_Iyy : Real = 0.3723953238821935;
                                attribute Izz : Real = 0.9920480510142249;
                                attribute sigma_Izz : Real = 0.37017423652493897;
                                attribute Ixy : Real = -0.05799103773509501;
                                attribute sigma_Ixy : Real = 0.02351283871158888;
                                attribute Ixz : Real = 0.009734387723880848;
                                attribute sigma_Ixz : Real = 0.022566176940390956;
                                attribute Iyz : Real = 0.009602784364827175;
                                attribute sigma_Iyz : Real = 0.02209918015384651;
                            }
                            part <'C.1.1.3.5.2.1.3'> 'Part 478' {
                                attribute POIconv : String = "-";
                                attribute Ipoint : Boolean = false;
                                attribute mass : Real = 0.24205635552457533;
                                attribute sigma_mass : Real = 0.28909372274994966;
                                attribute Cx : Real = 76.53168644756079;
                                attribute sigma_Cx : Real = 28.721044428837228;
                                attribute Cy : Real = 70.73780265636742;
                                attribute sigma_Cy : Real = 28.23690002309109;
                                attribute Cz : Real = 30.486800195649266;
                                attribute sigma_Cz : Real = 29.057750463592832;
                                attribute Ixx : Real = 0.32464668902420013;
                                attribute sigma_Ixx : Real = 0.37074144170588635;
                                attribute Iyy : Real = 0.27978398643442925;
                                attribute sigma_Iyy : Real = 0.3723953238821935;
                                attribute Izz : Real = 0.263055836639231;
                                attribute sigma_Izz : Real = 0.37017423652493897;
                                attribute Ixy : Real = 0.016614713241331548;
                                attribute sigma_Ixy : Real = 0.02351283871158888;
                                attribute Ixz : Real = 0.01399782298102264;
                                attribute sigma_Ixz : Real = 0.022566176940390956;
                                attribute Iyz : Real = -0.018957547240597266;
                                attribute sigma_Iyz : Real = 0.02209918015384651;
                            }
                            part <'C.1.1.3.5.2.1.4'> 'Part 479' {
                                attribute POIconv : String = "-";
                                attribute Ipoint : Boolean = false;
                                attribute mass : Real = 0.5823844344441313;
                                attribute sigma_mass : Real = 0.28909372274994966;
                                attribute Cx : Real = 58.873468451201916;
                                attribute sigma_Cx : Real = 28.721044428837228;
                                attribute Cy : Real = -71.7826466076076;
                                attribute sigma_Cy : Real = 28.23690002309109;
                                attribute Cz : Real = -11.469634529203176;
                                attribute sigma_Cz : Real = 29.057750463592832;
                                attribute Ixx : Real = 0.6441668946195129;
                                attribute sigma_Ixx : Real = 0.37074144170588635;
                                attribute Iyy : Real = 0.7186646275515615;
                                attribute sigma_Iyy : Real = 0.3723953238821935;
                                attribute Izz : Real = 0.7793213298717644;
                                attribute sigma_Izz : Real = 0.37017423652493897;
                                attribute Ixy : Real = 0.05129219420828757;
                                attribute sigma_Ixy : Real = 0.02351283871158888;
                                attribute Ixz : Real = -0.0067679140619685395;
                                attribute sigma_Ixz : Real = 0.022566176940390956;
                                attribute Iyz : Real = 0.020065684329194835;
                                attribute sigma_Iyz : Real = 0.02209918015384651;
                            }
                            part <'C.1.1.3.5.2.1.5'> 'Part 480' {
                                attribute POIconv : String = "+";
                                attribute Ipoint : Boolean = false;
                                attribute mass : Real = 0.08522757619945333;
                                attribute sigma_mass : Real = 0.28909372274994966;
                                attribute Cx : Real = 29.49779937043786;
                                attribute sigma_Cx : Real = 28.721044428837228;
                                attribute Cy : Real = -25.121706956997514;
                                attribute sigma_Cy : Real = 28.23690002309109;
                                attribute Cz : Real = -98.24852924793959;
                                attribute sigma_Cz : Real = 29.057750463592832;
                                attribute Ixx : Real = 0.09295107987150189;
                                attribute sigma_Ixx : Real = 0.37074144170588635;
                                attribute Iyy : Real = 0.09363749449332734;
                                attribute sigma_Iyy : Real = 0.3723953238821935;
                                attribute Izz : Real = 0.09665229984110107;
                                attribute sigma_Izz : Real = 0.37017423652493897;
                                attribute Ixy : Real = 0.00031482721439296025;
                                attribute sigma_Ixy : Real = 0.02351283871158888;
                                attribute Ixz : Real = -0.0007078397963966121;
                                attribute sigma_Ixz : Real = 0.022566176940390956;
                                attribute Iyz : Real = -0.0013766801883652617;
                                attribute sigma_Iyz : Real = 0.02209918015384651;
                            }
                        }
                        part <'C.1.1.3.5.2.2'> 'Subassembly 141' {
                            attribute POIconv : String = "-";
                            attribute Ipoint : Boolean = false;
                            attribute mass : Real = 1.0273223030988592;
                            attribute sigma_mass : Real = 0.5007250159521434;
                            attribute Cx : Real = -24.626445243198205;
                            attribute sigma_Cx : Real = 35.489777316648485;
                            attribute Cy : Real = -29.91012306096829;
                            attribute sigma_Cy : Real = 32.00675775527563;
                            attribute Cz : Real = -18.55358056709841;
                            attribute sigma_Cz : Real = 26.915148918167503;
                            attribute Ixx : Real = 4643.6983958695855;
                            attribute sigma_Ixx : Real = 3384.2917142124816;
                            attribute Iyy : Real = 5750.701910821414;
                            attribute sigma_Iyy : Real = 3954.4535905352463;
                            attribute Izz : Real = 8133.340841073046;
                            attribute sigma_Izz : Real = 5128.861753618825;
                            attribute Ixy : Real = -4028.181685843335;
                            attribute sigma_Ixy : Real = 2548.024047335412;
                            attribute Ixz : Real = 672.9822996906108;
                            attribute sigma_Ixz : Real = 1671.8176230632473;
                            attribute Iyz : Real = 578.3488051754924;
                            attribute sigma_Iyz : Real = 1480.0238163563401;
                            part <'C.1.1.3.5.2.2.1'> 'Part 481' {
                                attribute POIconv : String = "+";
                                attribute Ipoint : Boolean = false;
                                attribute mass : Real = 0.16374995881691576;
                                attribute sigma_mass : Real = 0.28909372274994966;
                                attribute Cx : Real = -67.04862541519105;
                                attribute sigma_Cx : Real = 28.721044428837228;
                                attribute Cy : Real = -67.478201771155;
                                attribute sigma_Cy : Real = 28.23690002309109;
                                attribute Cz : Real = -82.33389533124864;
                                attribute sigma_Cz : Real = 29.057750463592832;
                                attribute Ixx : Real = 0.1898077490849003;
                                attribute sigma_Ixx : Real = 0.37074144170588635;
                                attribute Iyy : Real = 0.20152880244461618;
                                attribute sigma_Iyy : Real = 0.3723953238821935;
                                attribute Izz : Real = 0.16429627004527667;
                                attribute sigma_Izz : Real = 0.37017423652493897;
                                attribute Ixy : Real = 0.00561605382337779;
                                attribute sigma_Ixy : Real = 0.02351283871158888;
                                attribute Ixz : Real = 0.02384162093817892;
                                attribute sigma_Ixz : Real = 0.022566176940390956;
                                attribute Iyz : Real = 0.010141324329997838;
                                attribute sigma_Iyz : Real = 0.02209918015384651;
                            }
                            part <'C.1.1.3.5.2.2.2'> 'Part 482' {
                                attribute POIconv : String = "-";
                                attribute Ipoint : Boolean = false;
                                attribute mass : Real = 0.4507169040031731;
                                attribute sigma_mass : Real = 0.28909372274994966;
                                attribute Cx : Real = -83.87389783747494;
                                attribute sigma_Cx : Real = 28.721044428837228;
                                attribute Cy : Real = -81.38862894847989;
                                attribute sigma_Cy : Real = 28.23690002309109;
                                attribute Cz : Real = 12.456491077318788;
                                attribute sigma_Cz : Real = 29.057750463592832;
                                attribute Ixx : Real = 0.6158056778280808;
                                attribute sigma_Ixx : Real = 0.37074144170588635;
                                attribute Iyy : Real = 0.5796172556689609;
                                attribute sigma_Iyy : Real = 0.3723953238821935;
                                attribute Izz : Real = 0.5051401470904547;
                                attribute sigma_Izz : Real = 0.37017423652493897;
                                attribute Ixy : Real = 0.009343448528794547;
                                attribute sigma_Ixy : Real = 0.02351283871158888;
                                attribute Ixz : Real = 0.005082597909516647;
                                attribute sigma_Ixz : Real = 0.022566176940390956;
                                attribute Iyz : Real = 0.04005551617207841;
                                attribute sigma_Iyz : Real = 0.02209918015384651;
                            }
                            part <'C.1.1.3.5.2.2.3'> 'Part 483' {
                                attribute POIconv : String = "+";
                                attribute Ipoint : Boolean = false;
                                attribute mass : Real = 0.4128554402787704;
                                attribute sigma_mass : Real = 0.28909372274994966;
                                attribute Cx : Real = 56.88019213266671;
                                attribute sigma_Cx : Real = 28.721044428837228;
                                attribute Cy : Real = 41.18983414955437;
                                attribute sigma_Cy : Real = 28.23690002309109;
                                attribute Cz : Real = -27.11042449809611;
                                attribute sigma_Cz : Real = 29.057750463592832;
                                attribute Ixx : Real = 0.5251657863510354;
                                attribute sigma_Ixx : Real = 0.37074144170588635;
                                attribute Iyy : Real = 0.5873546373931822;
                                attribute sigma_Iyy : Real = 0.3723953238821935;
                                attribute Izz : Real = 0.5157196977397867;
                                attribute sigma_Izz : Real = 0.37017423652493897;
                                attribute Ixy : Real = -0.005497476757732408;
                                attribute sigma_Ixy : Real = 0.02351283871158888;
                                attribute Ixz : Real = -0.029968072992941602;
                                attribute sigma_Ixz : Real = 0.022566176940390956;
                                attribute Iyz : Real = -0.00027002658520572744;
                                attribute sigma_Iyz : Real = 0.02209918015384651;
                            }
                        }
                        part <'C.1.1.3.5.2.3'> 'Subassembly 142' {
                            attribute POIconv : String = "-";
                            attribute Ipoint : Boolean = false;
                            attribute mass : Real = 1.2334115097650793;
                            attribute sigma_mass : Real = 0.6464332159373649;
                            attribute Cx : Real = -29.18322802191898;
                            attribute sigma_Cx : Real = 41.667072799737056;
                            attribute Cy : Real = -15.194639480873436;
                            attribute sigma_Cy : Real = 23.522777314968568;
                            attribute Cz : Real = 25.879519583477638;
                            attribute sigma_Cz : Real = 31.955829692315692;
                            attribute Ixx : Real = 4829.607617440035;
                            attribute sigma_Ixx : Real = 3979.8446635264704;
                            attribute Iyy : Real = 7978.425095522935;
                            attribute sigma_Iyy : Real = 6829.502437311594;
                            attribute Izz : Real = 6329.161952387209;
                            attribute sigma_Izz : Real = 5607.881541988633;
                            attribute Ixy : Real = 597.5398939534599;
                            attribute sigma_Ixy : Real = 1970.1009360332157;
                            attribute Ixz : Real = -1739.47350919591;
                            attribute sigma_Ixz : Real = 2960.289496604493;
                            attribute Iyz : Real = -1300.5924225891135;
                            attribute sigma_Iyz : Real = 1838.1625212168735;
                            part <'C.1.1.3.5.2.3.1'> 'Part 484' {
                                attribute POIconv : String = "+";
                                attribute Ipoint : Boolean = false;
                                attribute mass : Real = 0.16437632891070098;
                                attribute sigma_mass : Real = 0.28909372274994966;
                                attribute Cx : Real = -87.94091385789216;
                                attribute sigma_Cx : Real = 28.721044428837228;
                                attribute Cy : Real = 8.840931532904506;
                                attribute sigma_Cy : Real = 28.23690002309109;
                                attribute Cz : Real = -3.924263082444668;
                                attribute sigma_Cz : Real = 29.057750463592832;
                                attribute Ixx : Real = 0.19322989172315935;
                                attribute sigma_Ixx : Real = 0.37074144170588635;
                                attribute Iyy : Real = 0.18117497347683426;
                                attribute sigma_Iyy : Real = 0.3723953238821935;
                                attribute Izz : Real = 0.1639870371480213;
                                attribute sigma_Izz : Real = 0.37017423652493897;
                                attribute Ixy : Real = -0.005156382773976093;
                                attribute sigma_Ixy : Real = 0.02351283871158888;
                                attribute Ixz : Real = -0.010925383719903361;
                                attribute sigma_Ixz : Real = 0.022566176940390956;
                                attribute Iyz : Real = 0.02123519131864228;
                                attribute sigma_Iyz : Real = 0.02209918015384651;
                            }
                            part <'C.1.1.3.5.2.3.2'> 'Part 485' {
                                attribute POIconv : String = "+";
                                attribute Ipoint : Boolean = false;
                                attribute mass : Real = 0.24464886306924746;
                                attribute sigma_mass : Real = 0.28909372274994966;
                                attribute Cx : Real = 51.770894788205624;
                                attribute sigma_Cx : Real = 28.721044428837228;
                                attribute Cy : Real = -38.410535361617804;
                                attribute sigma_Cy : Real = 28.23690002309109;
                                attribute Cz : Real = 81.0674368403852;
                                attribute sigma_Cz : Real = 29.057750463592832;
                                attribute Ixx : Real = 0.35059562263245053;
                                attribute sigma_Ixx : Real = 0.37074144170588635;
                                attribute Iyy : Real = 0.35202187162961696;
                                attribute sigma_Iyy : Real = 0.3723953238821935;
                                attribute Izz : Real = 0.3586053470740151;
                                attribute sigma_Izz : Real = 0.37017423652493897;
                                attribute Ixy : Real = -0.008559046326059546;
                                attribute sigma_Ixy : Real = 0.02351283871158888;
                                attribute Ixz : Real = 0.0021574451421087866;
                                attribute sigma_Ixz : Real = 0.022566176940390956;
                                attribute Iyz : Real = -0.0018875008007492736;
                                attribute sigma_Iyz : Real = 0.02209918015384651;
                            }
                            part <'C.1.1.3.5.2.3.3'> 'Part 486' {
                                attribute POIconv : String = "-";
                                attribute Ipoint : Boolean = false;
                                attribute mass : Real = 0.4945702078763861;
                                attribute sigma_mass : Real = 0.28909372274994966;
                                attribute Cx : Real = -45.98975325934589;
                                attribute sigma_Cx : Real = 28.721044428837228;
                                attribute Cy : Real = 19.607096491381526;
                                attribute sigma_Cy : Real = 28.23690002309109;
                                attribute Cz : Real = 57.24931266158819;
                                attribute sigma_Cz : Real = 29.057750463592832;
                                attribute Ixx : Real = 0.6302831230563763;
                                attribute sigma_Ixx : Real = 0.37074144170588635;
                                attribute Iyy : Real = 0.5453448119334797;
                                attribute sigma_Iyy : Real = 0.3723953238821935;
                                attribute Izz : Real = 0.7254060587094954;
                                attribute sigma_Izz : Real = 0.37017423652493897;
                                attribute Ixy : Real = -0.008412597573371964;
                                attribute sigma_Ixy : Real = 0.02351283871158888;
                                attribute Ixz : Real = 0.0027969856382327298;
                                attribute sigma_Ixz : Real = 0.022566176940390956;
                                attribute Iyz : Real = 0.03360699727518125;
                                attribute sigma_Iyz : Real = 0.02209918015384651;
                            }
                            part <'C.1.1.3.5.2.3.4'> 'Part 487' {
                                attribute POIconv : String = "-";
                                attribute Ipoint : Boolean = false;
                                attribute mass : Real = 0.11192142649460585;
                                attribute sigma_mass : Real = 0.28909372274994966;
                                attribute Cx : Real = 84.71009056083858;
                                attribute sigma_Cx : Real = 28.721044428837228;
                                attribute Cy : Real = -47.43609852157533;
                                attribute sigma_Cy : Real = 28.23690002309109;
                                attribute Cz : Real = -23.268806701526046;
                                attribute sigma_Cz : Real = 29.057750463592832;
                                attribute Ixx : Real = 0.1373412624547402;
                                attribute sigma_Ixx : Real = 0.37074144170588635;
                                attribute Iyy : Real = 0.13942781677990032;
                                attribute sigma_Iyy : Real = 0.3723953238821935;
                                attribute Izz : Real = 0.11985992298820253;
                                attribute sigma_Izz : Real = 0.37017423652493897;
                                attribute Ixy : Real = 0.006348304676403214;
                                attribute sigma_Ixy : Real = 0.02351283871158888;
                                attribute Ixz : Real = -0.002555814129702577;
                                attribute sigma_Ixz : Real = 0.022566176940390956;
                                attribute Iyz : Real = 0.0007607875565043727;
                                attribute sigma_Iyz : Real = 0.02209918015384651;
                            }
                            part <'C.1.1.3.5.2.3.5'> 'Part 488' {
                                attribute POIconv : String = "+";
                                attribute Ipoint : Boolean = false;
                                attribute mass : Real = 0.21789468341413887;
                                attribute sigma_mass : Real = 0.28909372274994966;
                                attribute Cx : Real = -96.10573016107082;
                                attribute sigma_Cx : Real = 28.721044428837228;
                                attribute Cy : Real = -69.69127939082682;
                                attribute sigma_Cy : Real = 28.23690002309109;
                                attribute Cz : Real = -59.55826546996832;
                                attribute sigma_Cz : Real = 29.057750463592832;
                                attribute Ixx : Real = 0.2775584631756365;
                                attribute sigma_Ixx : Real = 0.37074144170588635;
                                attribute Iyy : Real = 0.2794096157926723;
                                attribute sigma_Iyy : Real = 0.3723953238821935;
                                attribute Izz : Real = 0.3019541112248354;
                                attribute sigma_Izz : Real = 0.37017423652493897;
                                attribute Ixy : Real = -0.0008468145558568571;
                                attribute sigma_Ixy : Real = 0.02351283871158888;
                                attribute Ixz : Real = -0.0026579386579302193;
                                attribute sigma_Ixz : Real = 0.022566176940390956;
                                attribute Iyz : Real = -0.007667960070206363;
                                attribute sigma_Iyz : Real = 0.02209918015384651;
                            }
                        }
                        part <'C.1.1.3.5.2.4'> 'Subassembly 143' {
                            attribute POIconv : String = "-";
                            attribute Ipoint : Boolean = false;
                            attribute mass : Real = 1.9656597798045259;
                            attribute sigma_mass : Real = 0.5007250159521434;
                            attribute Cx : Real = -2.841495515734685;
                            attribute sigma_Cx : Real = 20.24766302425275;
                            attribute Cy : Real = 76.51995404090623;
                            attribute sigma_Cy : Real = 23.27610682573371;
                            attribute Cz : Real = 11.721710818540918;
                            attribute sigma_Cz : Real = 26.11203154663393;
                            attribute Ixx : Real = 4243.152509726533;
                            attribute sigma_Ixx : Real = 6401.856868279927;
                            attribute Iyy : Real = 4180.920130365874;
                            attribute sigma_Iyy : Real = 4786.372046591782;
                            attribute Izz : Real = 2969.6048702785633;
                            attribute sigma_Izz : Real = 3481.358692247992;
                            attribute Ixy : Real = -1104.3139083611197;
                            attribute sigma_Ixy : Real = 1358.3483498113294;
                            attribute Ixz : Real = -1551.443155759976;
                            attribute sigma_Ixz : Real = 1618.2429504417967;
                            attribute Iyz : Real = -2029.0672800480675;
                            attribute sigma_Iyz : Real = 3120.5237986717916;
                            part <'C.1.1.3.5.2.4.1'> 'Part 489' {
                                attribute POIconv : String = "+";
                                attribute Ipoint : Boolean = false;
                                attribute mass : Real = 0.9797311544348486;
                                attribute sigma_mass : Real = 0.28909372274994966;
                                attribute Cx : Real = 24.184934701770544;
                                attribute sigma_Cx : Real = 28.721044428837228;
                                attribute Cy : Real = 99.54050313681364;
                                attribute sigma_Cy : Real = 28.23690002309109;
                                attribute Cz : Real = 43.70176154188812;
                                attribute sigma_Cz : Real = 29.057750463592832;
                                attribute Ixx : Real = 1.2733607291849118;
                                attribute sigma_Ixx : Real = 0.37074144170588635;
                                attribute Iyy : Real = 1.1688262813881496;
                                attribute sigma_Iyy : Real = 0.3723953238821935;
                                attribute Izz : Real = 1.3946195222107354;
                                attribute sigma_Izz : Real = 0.37017423652493897;
                                attribute Ixy : Real = 0.015571141618372022;
                                attribute sigma_Ixy : Real = 0.02351283871158888;
                                attribute Ixz : Real = -0.019751431039975308;
                                attribute sigma_Ixz : Real = 0.022566176940390956;
                                attribute Iyz : Real = 0.09809058418986746;
                                attribute sigma_Iyz : Real = 0.02209918015384651;
                            }
                            part <'C.1.1.3.5.2.4.2'> 'Part 490' {
                                attribute POIconv : String = "+";
                                attribute Ipoint : Boolean = false;
                                attribute mass : Real = 0.10377336461236701;
                                attribute sigma_mass : Real = 0.28909372274994966;
                                attribute Cx : Real = -14.816736988723278;
                                attribute sigma_Cx : Real = 28.721044428837228;
                                attribute Cy : Real = -10.649866750463843;
                                attribute sigma_Cy : Real = 28.23690002309109;
                                attribute Cz : Real = -99.30578176863492;
                                attribute sigma_Cz : Real = 29.057750463592832;
                                attribute Ixx : Real = 0.15507165814899845;
                                attribute sigma_Ixx : Real = 0.37074144170588635;
                                attribute Iyy : Real = 0.1568864109492887;
                                attribute sigma_Iyy : Real = 0.3723953238821935;
                                attribute Izz : Real = 0.15828423479637294;
                                attribute sigma_Izz : Real = 0.37017423652493897;
                                attribute Ixy : Real = 0.006754056841802575;
                                attribute sigma_Ixy : Real = 0.02351283871158888;
                                attribute Ixz : Real = 0.00019768165558448663;
                                attribute sigma_Ixz : Real = 0.022566176940390956;
                                attribute Iyz : Real = -0.00018422986073554073;
                                attribute sigma_Iyz : Real = 0.02209918015384651;
                            }
                            part <'C.1.1.3.5.2.4.3'> 'Part 491' {
                                attribute POIconv : String = "+";
                                attribute Ipoint : Boolean = false;
                                attribute mass : Real = 0.8821552607573103;
                                attribute sigma_mass : Real = 0.28909372274994966;
                                attribute Cx : Real = -31.448619114235044;
                                attribute sigma_Cx : Real = 28.721044428837228;
                                attribute Cy : Real = 61.20740743353963;
                                attribute sigma_Cy : Real = 28.23690002309109;
                                attribute Cz : Real = -10.734829911962152;
                                attribute sigma_Cz : Real = 29.057750463592832;
                                attribute Ixx : Real = 1.0604167900272277;
                                attribute sigma_Ixx : Real = 0.37074144170588635;
                                attribute Iyy : Real = 1.0755883193522682;
                                attribute sigma_Iyy : Real = 0.3723953238821935;
                                attribute Izz : Real = 1.0431785297335203;
                                attribute sigma_Izz : Real = 0.37017423652493897;
                                attribute Ixy : Real = -0.014324567936260912;
                                attribute sigma_Ixy : Real = 0.02351283871158888;
                                attribute Ixz : Real = -0.012068091469857777;
                                attribute sigma_Ixz : Real = 0.022566176940390956;
                                attribute Iyz : Real = 0.004789550252911379;
                                attribute sigma_Iyz : Real = 0.02209918015384651;
                            }
                        }
                    }
                    part <'C.1.1.3.5.3'> 'Assembly 39' {
                        attribute POIconv : String = "-";
                        attribute Ipoint : Boolean = false;
                        attribute mass : Real = 4.799244989042869;
                        attribute sigma_mass : Real = 0.7648700959862226;
                        attribute Cx : Real = -11.931994961112096;
                        attribute sigma_Cx : Real = 12.724114493487857;
                        attribute Cy : Real = 1.9661775654112037;
                        attribute sigma_Cy : Real = 13.827012518349655;
                        attribute Cz : Real = 9.264518987319756;
                        attribute sigma_Cz : Real = 13.485910647119683;
                        attribute Ixx : Real = 21676.429007468723;
                        attribute sigma_Ixx : Real = 8171.44491748816;
                        attribute Iyy : Real = 14237.106755634315;
                        attribute sigma_Iyy : Real = 6439.133512950906;
                        attribute Izz : Real = 15983.957327295728;
                        attribute sigma_Izz : Real = 6739.104625267102;
                        attribute Ixy : Real = -2082.490746314316;
                        attribute sigma_Ixy : Real = 3162.684798083061;
                        attribute Ixz : Real = 1079.0319297591354;
                        attribute sigma_Ixz : Real = 3047.6564412695234;
                        attribute Iyz : Real = -2180.081738366562;
                        attribute sigma_Iyz : Real = 3950.724415524445;
                        part <'C.1.1.3.5.3.1'> 'Subassembly 144' {
                            attribute POIconv : String = "-";
                            attribute Ipoint : Boolean = false;
                            attribute mass : Real = 1.8987638791166246;
                            attribute sigma_mass : Real = 0.5007250159521434;
                            attribute Cx : Real = -2.1941113168548294;
                            attribute sigma_Cx : Real = 20.152918745910224;
                            attribute Cy : Real = -3.074238871595755;
                            attribute sigma_Cy : Real = 22.83433348355383;
                            attribute Cz : Real = 36.31677117925892;
                            attribute sigma_Cz : Real = 18.311850933967733;
                            attribute Ixx : Real = 7404.24963465867;
                            attribute sigma_Ixx : Real = 4643.935535422351;
                            attribute Iyy : Real = 3166.2092948129766;
                            attribute sigma_Iyy : Real = 2740.3228668179436;
                            attribute Izz : Real = 9047.40190057097;
                            attribute sigma_Izz : Real = 5086.576722463866;
                            attribute Ixy : Real = -1068.4534574237189;
                            attribute sigma_Ixy : Real = 2281.339204345071;
                            attribute Ixz : Real = 1206.7737499554987;
                            attribute sigma_Ixz : Real = 1302.6380026541285;
                            attribute Iyz : Real = 1512.583270101191;
                            attribute sigma_Iyz : Real = 2113.3536485020036;
                            part <'C.1.1.3.5.3.1.1'> 'Part 492' {
                                attribute POIconv : String = "-";
                                attribute Ipoint : Boolean = false;
                                attribute mass : Real = 0.456779734400101;
                                attribute sigma_mass : Real = 0.28909372274994966;
                                attribute Cx : Real = -65.07756817154586;
                                attribute sigma_Cx : Real = 28.721044428837228;
                                attribute Cy : Real = -20.718311425298452;
                                attribute sigma_Cy : Real = 28.23690002309109;
                                attribute Cz : Real = 66.25896566547453;
                                attribute sigma_Cz : Real = 29.057750463592832;
                                attribute Ixx : Real = 0.5219499861603093;
                                attribute sigma_Ixx : Real = 0.37074144170588635;
                                attribute Iyy : Real = 0.5240345911279958;
                                attribute sigma_Iyy : Real = 0.3723953238821935;
                                attribute Izz : Real = 0.6072828593849432;
                                attribute sigma_Izz : Real = 0.37017423652493897;
                                attribute Ixy : Real = 0.003379810394848723;
                                attribute sigma_Ixy : Real = 0.02351283871158888;
                                attribute Ixz : Real = -0.0015570557014130606;
                                attribute sigma_Ixz : Real = 0.022566176940390956;
                                attribute Iyz : Real = -0.013852493918282666;
                                attribute sigma_Iyz : Real = 0.02209918015384651;
                            }
                            part <'C.1.1.3.5.3.1.2'> 'Part 493' {
                                attribute POIconv : String = "-";
                                attribute Ipoint : Boolean = false;
                                attribute mass : Real = 0.8545161055035424;
                                attribute sigma_mass : Real = 0.28909372274994966;
                                attribute Cx : Real = 14.27876208908856;
                                attribute sigma_Cx : Real = 28.721044428837228;
                                attribute Cy : Real = -52.957221725955606;
                                attribute sigma_Cy : Real = 28.23690002309109;
                                attribute Cz : Real = 37.10089614614844;
                                attribute sigma_Cz : Real = 29.057750463592832;
                                attribute Ixx : Real = 1.1733830730280859;
                                attribute sigma_Ixx : Real = 0.37074144170588635;
                                attribute Iyy : Real = 1.1396127012612223;
                                attribute sigma_Iyy : Real = 0.3723953238821935;
                                attribute Izz : Real = 1.1478849656533123;
                                attribute sigma_Izz : Real = 0.37017423652493897;
                                attribute Ixy : Real = -0.022730525926512812;
                                attribute sigma_Ixy : Real = 0.02351283871158888;
                                attribute Ixz : Real = 0.0068739508055629985;
                                attribute sigma_Ixz : Real = 0.022566176940390956;
                                attribute Iyz : Real = 0.02347491269355722;
                                attribute sigma_Iyz : Real = 0.02209918015384651;
                            }
                            part <'C.1.1.3.5.3.1.3'> 'Part 494' {
                                attribute POIconv : String = "-";
                                attribute Ipoint : Boolean = false;
                                attribute mass : Real = 0.5874680392129812;
                                attribute sigma_mass : Real = 0.28909372274994966;
                                attribute Cx : Real = 22.739250352606177;
                                attribute sigma_Cx : Real = 28.721044428837228;
                                attribute Cy : Real = 83.20324965752661;
                                attribute sigma_Cy : Real = 28.23690002309109;
                                attribute Cz : Real = 11.894957395270467;
                                attribute sigma_Cz : Real = 29.057750463592832;
                                attribute Ixx : Real = 0.6274487930061973;
                                attribute sigma_Ixx : Real = 0.37074144170588635;
                                attribute Iyy : Real = 0.7727533694797315;
                                attribute sigma_Iyy : Real = 0.3723953238821935;
                                attribute Izz : Real = 0.7970727530554764;
                                attribute sigma_Izz : Real = 0.37017423652493897;
                                attribute Ixy : Real = -0.0432451684166896;
                                attribute sigma_Ixy : Real = 0.02351283871158888;
                                attribute Ixz : Real = 0.029962829448293787;
                                attribute sigma_Ixz : Real = 0.022566176940390956;
                                attribute Iyz : Real = 0.005769132986700421;
                                attribute sigma_Iyz : Real = 0.02209918015384651;
                            }
                        }
                        part <'C.1.1.3.5.3.2'> 'Subassembly 145' {
                            attribute POIconv : String = "-";
                            attribute Ipoint : Boolean = false;
                            attribute mass : Real = 2.900481109926244;
                            attribute sigma_mass : Real = 0.5781874454998993;
                            attribute Cx : Real = -18.306779357907025;
                            attribute sigma_Cx : Real = 16.27175385288757;
                            attribute Cy : Real = 5.2658234874416685;
                            attribute sigma_Cy : Real = 17.28571047234253;
                            attribute Cz : Real = -8.44490140332495;
                            attribute sigma_Cz : Real = 17.88718978949191;
                            attribute Ixx : Real = 11893.139418882216;
                            attribute sigma_Ixx : Real = 6149.0855077878105;
                            attribute Iyy : Real = 8473.75428658418;
                            attribute sigma_Iyy : Real = 5089.858563259404;
                            attribute Izz : Real = 6558.8140608797385;
                            attribute sigma_Izz : Real = 4280.160168812462;
                            attribute Ixy : Real = -1168.244555873352;
                            attribute sigma_Ixy : Real = 2110.7944043119364;
                            attribute Ixz : Real = 699.8988972687093;
                            attribute sigma_Ixz : Real = 2361.2491014902143;
                            attribute Iyz : Real = -4121.0593114441845;
                            attribute sigma_Iyz : Real = 2985.309569257121;
                            part <'C.1.1.3.5.3.2.1'> 'Part 495' {
                                attribute POIconv : String = "-";
                                attribute Ipoint : Boolean = false;
                                attribute mass : Real = 0.7315342742293142;
                                attribute sigma_mass : Real = 0.28909372274994966;
                                attribute Cx : Real = -27.083597285673022;
                                attribute sigma_Cx : Real = 28.721044428837228;
                                attribute Cy : Real = 59.81912002898753;
                                attribute sigma_Cy : Real = 28.23690002309109;
                                attribute Cz : Real = 54.87254145555198;
                                attribute sigma_Cz : Real = 29.057750463592832;
                                attribute Ixx : Real = 0.9046982971158939;
                                attribute sigma_Ixx : Real = 0.37074144170588635;
                                attribute Iyy : Real = 0.9475187028309325;
                                attribute sigma_Iyy : Real = 0.3723953238821935;
                                attribute Izz : Real = 0.7458865510366658;
                                attribute sigma_Izz : Real = 0.37017423652493897;
                                attribute Ixy : Real = -0.01280273458091544;
                                attribute sigma_Ixy : Real = 0.02351283871158888;
                                attribute Ixz : Real = 0.004567230542952156;
                                attribute sigma_Ixz : Real = 0.022566176940390956;
                                attribute Iyz : Real = 0.005248098682998648;
                                attribute sigma_Iyz : Real = 0.02209918015384651;
                            }
                            part <'C.1.1.3.5.3.2.2'> 'Part 496' {
                                attribute POIconv : String = "-";
                                attribute Ipoint : Boolean = false;
                                attribute mass : Real = 0.9129071567088831;
                                attribute sigma_mass : Real = 0.28909372274994966;
                                attribute Cx : Real = -8.936004992574453;
                                attribute sigma_Cx : Real = 28.721044428837228;
                                attribute Cy : Real = -19.17416276410222;
                                attribute sigma_Cy : Real = 28.23690002309109;
                                attribute Cz : Real = -72.87885313853621;
                                attribute sigma_Cz : Real = 29.057750463592832;
                                attribute Ixx : Real = 1.1025994208789753;
                                attribute sigma_Ixx : Real = 0.37074144170588635;
                                attribute Iyy : Real = 1.12154690615921;
                                attribute sigma_Iyy : Real = 0.3723953238821935;
                                attribute Izz : Real = 0.9919616068567793;
                                attribute sigma_Izz : Real = 0.37017423652493897;
                                attribute Ixy : Real = -0.0908055245648895;
                                attribute sigma_Ixy : Real = 0.02351283871158888;
                                attribute Ixz : Real = -0.06132027589368768;
                                attribute sigma_Ixz : Real = 0.022566176940390956;
                                attribute Iyz : Real = -0.026988278481022074;
                                attribute sigma_Iyz : Real = 0.02209918015384651;
                            }
                            part <'C.1.1.3.5.3.2.3'> 'Part 497' {
                                attribute POIconv : String = "+";
                                attribute Ipoint : Boolean = false;
                                attribute mass : Real = 0.33162104671006093;
                                attribute sigma_mass : Real = 0.28909372274994966;
                                attribute Cx : Real = 36.28541943617165;
                                attribute sigma_Cx : Real = 28.721044428837228;
                                attribute Cy : Real = 58.1856410484761;
                                attribute sigma_Cy : Real = 28.23690002309109;
                                attribute Cz : Real = 12.509159417822957;
                                attribute sigma_Cz : Real = 29.057750463592832;
                                attribute Ixx : Real = 0.4775281663408432;
                                attribute sigma_Ixx : Real = 0.37074144170588635;
                                attribute Iyy : Real = 0.42359904073673266;
                                attribute sigma_Iyy : Real = 0.3723953238821935;
                                attribute Izz : Real = 0.462655986295135;
                                attribute sigma_Izz : Real = 0.37017423652493897;
                                attribute Ixy : Real = -0.028136388917012176;
                                attribute sigma_Ixy : Real = 0.02351283871158888;
                                attribute Ixz : Real = 0.02027832792366263;
                                attribute sigma_Ixz : Real = 0.022566176940390956;
                                attribute Iyz : Real = 0.001679733290880705;
                                attribute sigma_Iyz : Real = 0.02209918015384651;
                            }
                            part <'C.1.1.3.5.3.2.4'> 'Part 498' {
                                attribute POIconv : String = "+";
                                attribute Ipoint : Boolean = false;
                                attribute mass : Real = 0.924418632277986;
                                attribute sigma_mass : Real = 0.28909372274994966;
                                attribute Cx : Real = -40.1994860265404;
                                attribute sigma_Cx : Real = 28.721044428837228;
                                attribute Cy : Real = -32.75319938547909;
                                attribute sigma_Cy : Real = 28.23690002309109;
                                attribute Cz : Real = -2.436229260638356;
                                attribute sigma_Cz : Real = 29.057750463592832;
                                attribute Ixx : Real = 1.4455758152316664;
                                attribute sigma_Ixx : Real = 0.37074144170588635;
                                attribute Iyy : Real = 1.4260410003644974;
                                attribute sigma_Iyy : Real = 0.3723953238821935;
                                attribute Izz : Real = 1.4127503014989167;
                                attribute sigma_Izz : Real = 0.37017423652493897;
                                attribute Ixy : Real = 0.020105404962665264;
                                attribute sigma_Ixy : Real = 0.02351283871158888;
                                attribute Ixz : Real = 0.01913291002739733;
                                attribute sigma_Ixz : Real = 0.022566176940390956;
                                attribute Iyz : Real = 0.02229040833634502;
                                attribute sigma_Iyz : Real = 0.02209918015384651;
                            }
                        }
                    }
                }
            }
            part <'C.1.1.4'> 'Element 4' {
                attribute POIconv : String = "-";
                attribute Ipoint : Boolean = false;
                attribute mass : Real = 119.66025232612644;
                attribute sigma_mass : Real = 4.403344397586287;
                attribute Cx : Real = -6.075282627346583;
                attribute sigma_Cx : Real = 3.1510878674624485;
                attribute Cy : Real = -2.4884651609288992;
                attribute sigma_Cy : Real = 3.117721941602758;
                attribute Cz : Real = -4.992233379730092;
                attribute sigma_Cz : Real = 3.1388649993745252;
                attribute Ixx : Real = 759925.0813497938;
                attribute sigma_Ixx : Real = 56332.81731528726;
                attribute Iyy : Real = 801578.2607786297;
                attribute sigma_Iyy : Real = 57820.15815730523;
                attribute Izz : Real = 780136.643783377;
                attribute sigma_Izz : Real = 57981.39261409782;
                attribute Ixy : Real = -20200.93418018664;
                attribute sigma_Ixy : Real = 26894.788014429658;
                attribute Ixz : Real = -23498.56949799716;
                attribute sigma_Ixz : Real = 27233.86608801572;
                attribute Iyz : Real = -28439.929212214487;
                attribute sigma_Iyz : Real = 26401.64708814549;
                part <'C.1.1.4.1'> 'Subsystem 11' {
                    attribute POIconv : String = "-";
                    attribute Ipoint : Boolean = false;
                    attribute mass : Real = 18.279298806732985;
                    attribute sigma_mass : Real = 1.5834315318329186;
                    attribute Cx : Real = -16.2717001146691;
                    attribute sigma_Cx : Real = 7.725230621268175;
                    attribute Cy : Real = -10.240560359479536;
                    attribute sigma_Cy : Real = 7.624937510131202;
                    attribute Cz : Real = -13.34736096840824;
                    attribute sigma_Cz : Real = 7.482671486933478;
                    attribute Ixx : Real = 117835.73923769585;
                    attribute sigma_Ixx : Real = 19974.876996767776;
                    attribute Iyy : Real = 123033.1667278489;
                    attribute sigma_Iyy : Real = 21047.87926816473;
                    attribute Izz : Real = 132082.53788150358;
                    attribute sigma_Izz : Real = 21918.75361646779;
                    attribute Ixy : Real = 6613.618381547369;
                    attribute sigma_Ixy : Real = 10294.048520300945;
                    attribute Ixz : Real = 3954.173763627394;
                    attribute sigma_Ixz : Real = 10010.760201953146;
                    attribute Iyz : Real = -8875.575780306566;
                    attribute sigma_Iyz : Real = 9745.933274318486;
                    part <'C.1.1.4.1.1'> 'Assembly 40' {
                        attribute POIconv : String = "-";
                        attribute Ipoint : Boolean = false;
                        attribute mass : Real = 11.06298564883042;
                        attribute sigma_mass : Real = 1.2265207905297186;
                        attribute Cx : Real = -19.848967123085288;
                        attribute sigma_Cx : Real = 9.782367991927398;
                        attribute Cy : Real = -16.85251623856646;
                        attribute sigma_Cy : Real = 9.9422858354822;
                        attribute Cz : Real = -13.108299099752704;
                        attribute sigma_Cz : Real = 10.156054877939894;
                        attribute Ixx : Real = 80865.13194669355;
                        attribute sigma_Ixx : Real = 16774.134473493952;
                        attribute Iyy : Real = 80770.52031155906;
                        attribute sigma_Iyy : Real = 16937.983117894495;
                        attribute Izz : Real = 80455.69016222123;
                        attribute sigma_Izz : Real = 16772.89545539456;
                        attribute Ixy : Real = 9762.731172521278;
                        attribute sigma_Ixy : Real = 8028.333760897886;
                        attribute Ixz : Real = 370.69951159243146;
                        attribute sigma_Ixz : Real = 8252.550483548877;
                        attribute Iyz : Real = -2075.0312512509327;
                        attribute sigma_Iyz : Real = 8279.120192624609;
                        part <'C.1.1.4.1.1.1'> 'Subassembly 146' {
                            attribute POIconv : String = "-";
                            attribute Ipoint : Boolean = false;
                            attribute mass : Real = 2.1841751735098662;
                            attribute sigma_mass : Real = 0.5781874454998993;
                            attribute Cx : Real = -39.182119512354596;
                            attribute sigma_Cx : Real = 20.22537274223434;
                            attribute Cy : Real = 23.616235246878933;
                            attribute sigma_Cy : Real = 20.84443243328816;
                            attribute Cz : Real = -47.08905170510482;
                            attribute sigma_Cz : Real = 18.87184885126722;
                            attribute Ixx : Real = 5643.070787556779;
                            attribute sigma_Ixx : Real = 4221.4510854064265;
                            attribute Iyy : Real = 5751.2176440649355;
                            attribute sigma_Iyy : Real = 3998.8894165303827;
                            attribute Izz : Real = 7890.400570244408;
                            attribute sigma_Izz : Real = 4907.9485056130425;
                            attribute Ixy : Real = -2574.17583300954;
                            attribute sigma_Ixy : Real = 2359.200067257328;
                            attribute Ixz : Real = 2108.414975591904;
                            attribute sigma_Ixz : Real = 1942.9488176137452;
                            attribute Iyz : Real = 466.0602242955624;
                            attribute sigma_Iyz : Real = 2013.8403690801922;
                            part <'C.1.1.4.1.1.1.1'> 'Part 499' {
                                attribute POIconv : String = "-";
                                attribute Ipoint : Boolean = false;
                                attribute mass : Real = 0.10599838715069927;
                                attribute sigma_mass : Real = 0.28909372274994966;
                                attribute Cx : Real = -84.07895197160542;
                                attribute sigma_Cx : Real = 28.721044428837228;
                                attribute Cy : Real = -47.38326636143029;
                                attribute sigma_Cy : Real = 28.23690002309109;
                                attribute Cz : Real = 6.345878820866346;
                                attribute sigma_Cz : Real = 29.057750463592832;
                                attribute Ixx : Real = 0.15278704907736385;
                                attribute sigma_Ixx : Real = 0.37074144170588635;
                                attribute Iyy : Real = 0.15308000367046964;
                                attribute sigma_Iyy : Real = 0.3723953238821935;
                                attribute Izz : Real = 0.15540248025267547;
                                attribute sigma_Izz : Real = 0.37017423652493897;
                                attribute Ixy : Real = 0.00398034431935545;
                                attribute sigma_Ixy : Real = 0.02351283871158888;
                                attribute Ixz : Real = 0.0052492795259989795;
                                attribute sigma_Ixz : Real = 0.022566176940390956;
                                attribute Iyz : Real = 0.0026196613458009067;
                                attribute sigma_Iyz : Real = 0.02209918015384651;
                            }
                            part <'C.1.1.4.1.1.1.2'> 'Part 500' {
                                attribute POIconv : String = "-";
                                attribute Ipoint : Boolean = false;
                                attribute mass : Real = 0.6371688674567267;
                                attribute sigma_mass : Real = 0.28909372274994966;
                                attribute Cx : Real = 19.163903687149286;
                                attribute sigma_Cx : Real = 28.721044428837228;
                                attribute Cy : Real = 37.46871817857027;
                                attribute sigma_Cy : Real = 28.23690002309109;
                                attribute Cz : Real = -88.84721449576318;
                                attribute sigma_Cz : Real = 29.057750463592832;
                                attribute Ixx : Real = 0.9004757441134695;
                                attribute sigma_Ixx : Real = 0.37074144170588635;
                                attribute Iyy : Real = 0.9801932116768823;
                                attribute sigma_Iyy : Real = 0.3723953238821935;
                                attribute Izz : Real = 0.8920301554460848;
                                attribute sigma_Izz : Real = 0.37017423652493897;
                                attribute Ixy : Real = -0.012147946118455318;
                                attribute sigma_Ixy : Real = 0.02351283871158888;
                                attribute Ixz : Real = -0.0075942226184956794;
                                attribute sigma_Ixz : Real = 0.022566176940390956;
                                attribute Iyz : Real = -0.007629964553041381;
                                attribute sigma_Iyz : Real = 0.02209918015384651;
                            }
                            part <'C.1.1.4.1.1.1.3'> 'Part 501' {
                                attribute POIconv : String = "+";
                                attribute Ipoint : Boolean = false;
                                attribute mass : Real = 0.8959677613631356;
                                attribute sigma_mass : Real = 0.28909372274994966;
                                attribute Cx : Real = -42.340896278619766;
                                attribute sigma_Cx : Real = 28.721044428837228;
                                attribute Cy : Real = 59.6509097609669;
                                attribute sigma_Cy : Real = 28.23690002309109;
                                attribute Cz : Real = -28.858464350923896;
                                attribute sigma_Cz : Real = 29.057750463592832;
                                attribute Ixx : Real = 1.259001407422434;
                                attribute sigma_Ixx : Real = 0.37074144170588635;
                                attribute Iyy : Real = 1.1515209076494384;
                                attribute sigma_Iyy : Real = 0.3723953238821935;
                                attribute Izz : Real = 1.3046469321727268;
                                attribute sigma_Izz : Real = 0.37017423652493897;
                                attribute Ixy : Real = 0.027184001078134335;
                                attribute sigma_Ixy : Real = 0.02351283871158888;
                                attribute Ixz : Real = 0.049499085633612785;
                                attribute sigma_Ixz : Real = 0.022566176940390956;
                                attribute Iyz : Real = 0.0470255881304107;
                                attribute sigma_Iyz : Real = 0.02209918015384651;
                            }
                            part <'C.1.1.4.1.1.1.4'> 'Part 502' {
                                attribute POIconv : String = "-";
                                attribute Ipoint : Boolean = false;
                                attribute mass : Real = 0.5450401575393043;
                                attribute sigma_mass : Real = 0.28909372274994966;
                                attribute Cx : Real = -93.46640505827963;
                                attribute sigma_Cx : Real = 28.721044428837228;
                                attribute Cy : Real = -38.00572855398059;
                                attribute sigma_Cy : Real = 28.23690002309109;
                                attribute Cz : Real = -38.63285589031875;
                                attribute sigma_Cz : Real = 29.057750463592832;
                                attribute Ixx : Real = 0.6172863254542152;
                                attribute sigma_Ixx : Real = 0.37074144170588635;
                                attribute Iyy : Real = 0.6575374937140223;
                                attribute sigma_Iyy : Real = 0.3723953238821935;
                                attribute Izz : Real = 0.5697219682827084;
                                attribute sigma_Izz : Real = 0.37017423652493897;
                                attribute Ixy : Real = -0.038603057131318154;
                                attribute sigma_Ixy : Real = 0.02351283871158888;
                                attribute Ixz : Real = -0.032253717968582854;
                                attribute sigma_Ixz : Real = 0.022566176940390956;
                                attribute Iyz : Real = -0.025629205204220074;
                                attribute sigma_Iyz : Real = 0.02209918015384651;
                            }
                        }
                        part <'C.1.1.4.1.1.2'> 'Subassembly 147' {
                            attribute POIconv : String = "-";
                            attribute Ipoint : Boolean = false;
                            attribute mass : Real = 1.6994527743111831;
                            attribute sigma_mass : Real = 0.5781874454998993;
                            attribute Cx : Real = -2.791149730836339;
                            attribute sigma_Cx : Real = 21.605841695106495;
                            attribute Cy : Real = -68.47369816492333;
                            attribute sigma_Cy : Real = 16.9423127440173;
                            attribute Cz : Real = 25.8673596575601;
                            attribute sigma_Cz : Real = 28.950084526379012;
                            attribute Ixx : Real = 8719.234600653877;
                            attribute sigma_Ixx : Real = 5453.104099865773;
                            attribute Iyy : Real = 10672.696203328833;
                            attribute sigma_Iyy : Real = 6254.074349663063;
                            attribute Izz : Real = 3577.6250910957556;
                            attribute sigma_Izz : Real = 2673.7021306424335;
                            attribute Ixy : Real = -1204.0340826377653;
                            attribute sigma_Ixy : Real = 1238.7437618783713;
                            attribute Ixz : Real = -1609.8244086319091;
                            attribute sigma_Ixz : Real = 2770.8678225797867;
                            attribute Iyz : Real = -1644.4331894392612;
                            attribute sigma_Iyz : Real = 2030.8686720988883;
                            part <'C.1.1.4.1.1.2.1'> 'Part 503' {
                                attribute POIconv : String = "+";
                                attribute Ipoint : Boolean = false;
                                attribute mass : Real = 0.2985605688514188;
                                attribute sigma_mass : Real = 0.28909372274994966;
                                attribute Cx : Real = 42.47858445160091;
                                attribute sigma_Cx : Real = 28.721044428837228;
                                attribute Cy : Real = -72.608512500301;
                                attribute sigma_Cy : Real = 28.23690002309109;
                                attribute Cz : Real = -14.873924944549799;
                                attribute sigma_Cz : Real = 29.057750463592832;
                                attribute Ixx : Real = 0.39686811994325477;
                                attribute sigma_Ixx : Real = 0.37074144170588635;
                                attribute Iyy : Real = 0.4186613130472625;
                                attribute sigma_Iyy : Real = 0.3723953238821935;
                                attribute Izz : Real = 0.41960603939966684;
                                attribute sigma_Izz : Real = 0.37017423652493897;
                                attribute Ixy : Real = 0.008888219400596102;
                                attribute sigma_Ixy : Real = 0.02351283871158888;
                                attribute Ixz : Real = -0.0070280152672081014;
                                attribute sigma_Ixz : Real = 0.022566176940390956;
                                attribute Iyz : Real = -0.004296165015230066;
                                attribute sigma_Iyz : Real = 0.02209918015384651;
                            }
                            part <'C.1.1.4.1.1.2.2'> 'Part 504' {
                                attribute POIconv : String = "+";
                                attribute Ipoint : Boolean = false;
                                attribute mass : Real = 0.37265111112524757;
                                attribute sigma_mass : Real = 0.28909372274994966;
                                attribute Cx : Real = -54.33716285042465;
                                attribute sigma_Cx : Real = 28.721044428837228;
                                attribute Cy : Real = -96.24383323825896;
                                attribute sigma_Cy : Real = 28.23690002309109;
                                attribute Cz : Real = -84.89596317522228;
                                attribute sigma_Cz : Real = 29.057750463592832;
                                attribute Ixx : Real = 0.48709901323801563;
                                attribute sigma_Ixx : Real = 0.37074144170588635;
                                attribute Iyy : Real = 0.520270368495399;
                                attribute sigma_Iyy : Real = 0.3723953238821935;
                                attribute Izz : Real = 0.4647380356074044;
                                attribute sigma_Izz : Real = 0.37017423652493897;
                                attribute Ixy : Real = -0.05488208152097072;
                                attribute sigma_Ixy : Real = 0.02351283871158888;
                                attribute Ixz : Real = -0.023222607450379754;
                                attribute sigma_Ixz : Real = 0.022566176940390956;
                                attribute Iyz : Real = -0.022944397091971838;
                                attribute sigma_Iyz : Real = 0.02209918015384651;
                            }
                            part <'C.1.1.4.1.1.2.3'> 'Part 505' {
                                attribute POIconv : String = "+";
                                attribute Ipoint : Boolean = false;
                                attribute mass : Real = 0.7397677671948913;
                                attribute sigma_mass : Real = 0.28909372274994966;
                                attribute Cx : Real = 23.455810546875;
                                attribute sigma_Cx : Real = 28.721044428837228;
                                attribute Cy : Real = -45.0782778672874;
                                attribute sigma_Cy : Real = 28.23690002309109;
                                attribute Cz : Real = 73.02248226478696;
                                attribute sigma_Cz : Real = 29.057750463592832;
                                attribute Ixx : Real = 1.0063665260534227;
                                attribute sigma_Ixx : Real = 0.37074144170588635;
                                attribute Iyy : Real = 0.8706827870985145;
                                attribute sigma_Iyy : Real = 0.3723953238821935;
                                attribute Izz : Real = 0.9042224637998537;
                                attribute sigma_Izz : Real = 0.37017423652493897;
                                attribute Ixy : Real = -0.0070543235260011865;
                                attribute sigma_Ixy : Real = 0.02351283871158888;
                                attribute Ixz : Real = 0.06793677252515268;
                                attribute sigma_Ixz : Real = 0.022566176940390956;
                                attribute Iyz : Real = 0.0035243387354903333;
                                attribute sigma_Iyz : Real = 0.02209918015384651;
                            }
                            part <'C.1.1.4.1.1.2.4'> 'Part 506' {
                                attribute POIconv : String = "-";
                                attribute Ipoint : Boolean = false;
                                attribute mass : Real = 0.2884733271396253;
                                attribute sigma_mass : Real = 0.28909372274994966;
                                attribute Cx : Real = -50.3648157697171;
                                attribute sigma_Cx : Real = 28.721044428837228;
                                attribute Cy : Real = -88.31648114137352;
                                attribute sigma_Cy : Real = 28.23690002309109;
                                attribute Cz : Real = 90.19211665727198;
                                attribute sigma_Cz : Real = 29.057750463592832;
                                attribute Ixx : Real = 0.36546593879405004;
                                attribute sigma_Ixx : Real = 0.37074144170588635;
                                attribute Iyy : Real = 0.3823836746117036;
                                attribute sigma_Iyy : Real = 0.3723953238821935;
                                attribute Izz : Real = 0.35777025923503464;
                                attribute sigma_Izz : Real = 0.37017423652493897;
                                attribute Ixy : Real = 0.03321225145191976;
                                attribute sigma_Ixy : Real = 0.02351283871158888;
                                attribute Ixz : Real = -9.27428305742713e-06;
                                attribute sigma_Ixz : Real = 0.022566176940390956;
                                attribute Iyz : Real = -3.258799532586333e-05;
                                attribute sigma_Iyz : Real = 0.02209918015384651;
                            }
                        }
                        part <'C.1.1.4.1.1.3'> 'Subassembly 148' {
                            attribute POIconv : String = "-";
                            attribute Ipoint : Boolean = false;
                            attribute mass : Real = 1.0292361675493884;
                            attribute sigma_mass : Real = 0.40884026350990615;
                            attribute Cx : Real = -34.29559814968252;
                            attribute sigma_Cx : Real = 22.361938894864014;
                            attribute Cy : Real = 35.47772116913336;
                            attribute sigma_Cy : Real = 30.563145886868647;
                            attribute Cz : Real = 32.00392209668803;
                            attribute sigma_Cz : Real = 22.91868752555049;
                            attribute Ixx : Real = 2937.767921591192;
                            attribute sigma_Ixx : Real = 2665.86439069248;
                            attribute Iyy : Real = 555.6120870041044;
                            attribute sigma_Iyy : Real = 976.5534252862336;
                            attribute Izz : Real = 2860.9388527033325;
                            attribute sigma_Izz : Real = 2614.6319496142455;
                            attribute Ixy : Real = -791.019171551439;
                            attribute sigma_Ixy : Real = 1133.8903395619552;
                            attribute Ixz : Real = 274.4546556447517;
                            attribute sigma_Ixz : Real = 487.08689088338565;
                            attribute Iyz : Real = 909.4041405749444;
                            attribute sigma_Iyz : Real = 1183.9897987052684;
                            part <'C.1.1.4.1.1.3.1'> 'Part 507' {
                                attribute POIconv : String = "-";
                                attribute Ipoint : Boolean = false;
                                attribute mass : Real = 0.6799589239286724;
                                attribute sigma_mass : Real = 0.28909372274994966;
                                attribute Cx : Real = -23.37936842814088;
                                attribute sigma_Cx : Real = 28.721044428837228;
                                attribute Cy : Real = 71.64420271292329;
                                attribute sigma_Cy : Real = 28.23690002309109;
                                attribute Cz : Real = 19.454904785379767;
                                attribute sigma_Cz : Real = 29.057750463592832;
                                attribute Ixx : Real = 0.9396641733695398;
                                attribute sigma_Ixx : Real = 0.37074144170588635;
                                attribute Iyy : Real = 0.8836162410866945;
                                attribute sigma_Iyy : Real = 0.3723953238821935;
                                attribute Izz : Real = 0.9031940903405005;
                                attribute sigma_Izz : Real = 0.37017423652493897;
                                attribute Ixy : Real = 0.05485065543238274;
                                attribute sigma_Ixy : Real = 0.02351283871158888;
                                attribute Ixz : Real = -0.03919145476472046;
                                attribute sigma_Ixz : Real = 0.022566176940390956;
                                attribute Iyz : Real = 0.002945385441951963;
                                attribute sigma_Iyz : Real = 0.02209918015384651;
                            }
                            part <'C.1.1.4.1.1.3.2'> 'Part 508' {
                                attribute POIconv : String = "-";
                                attribute Ipoint : Boolean = false;
                                attribute mass : Real = 0.34927724362071605;
                                attribute sigma_mass : Real = 0.28909372274994966;
                                attribute Cx : Real = -55.54687618277967;
                                attribute sigma_Cx : Real = 28.721044428837228;
                                attribute Cy : Real = -34.929734002798796;
                                attribute sigma_Cy : Real = 28.23690002309109;
                                attribute Cz : Real = 56.43384549766779;
                                attribute sigma_Cz : Real = 29.057750463592832;
                                attribute Ixx : Real = 0.45713847653811635;
                                attribute sigma_Ixx : Real = 0.37074144170588635;
                                attribute Iyy : Real = 0.42781133169479196;
                                attribute sigma_Iyy : Real = 0.3723953238821935;
                                attribute Izz : Real = 0.4328969177629292;
                                attribute sigma_Izz : Real = 0.37017423652493897;
                                attribute Ixy : Real = -0.01961816360575059;
                                attribute sigma_Ixy : Real = 0.02351283871158888;
                                attribute Ixz : Real = 0.014412363623219269;
                                attribute sigma_Ixz : Real = 0.022566176940390956;
                                attribute Iyz : Real = 0.025370042095948682;
                                attribute sigma_Iyz : Real = 0.02209918015384651;
                            }
                        }
                        part <'C.1.1.4.1.1.4'> 'Subassembly 149' {
                            attribute POIconv : String = "-";
                            attribute Ipoint : Boolean = false;
                            attribute mass : Real = 2.471437142374925;
                            attribute sigma_mass : Real = 0.5007250159521434;
                            attribute Cx : Real = -27.573493969733846;
                            attribute sigma_Cx : Real = 21.11454162226154;
                            attribute Cy : Real = -35.026836136519414;
                            attribute sigma_Cy : Real = 20.5270187306847;
                            attribute Cz : Real = -79.84787812215035;
                            attribute sigma_Cz : Real = 17.571001658189253;
                            attribute Ixx : Real = 11114.053894368653;
                            attribute sigma_Ixx : Real = 6008.305493620447;
                            attribute Iyy : Real = 11679.28617967516;
                            attribute sigma_Iyy : Real = 6290.809621546567;
                            attribute Izz : Real = 20002.85297436474;
                            attribute sigma_Izz : Real = 8649.153833039622;
                            attribute Ixy : Real = 7497.973168353479;
                            attribute sigma_Ixy : Real = 4235.801343225187;
                            attribute Ixz : Real = 1728.264775109807;
                            attribute sigma_Ixz : Real = 2927.9388443627486;
                            attribute Iyz : Real = 905.0510323329174;
                            attribute sigma_Iyz : Real = 2886.78114744323;
                            part <'C.1.1.4.1.1.4.1'> 'Part 509' {
                                attribute POIconv : String = "+";
                                attribute Ipoint : Boolean = false;
                                attribute mass : Real = 0.8177969777865801;
                                attribute sigma_mass : Real = 0.28909372274994966;
                                attribute Cx : Real = 63.316851714625955;
                                attribute sigma_Cx : Real = 28.721044428837228;
                                attribute Cy : Real = -93.38567056693137;
                                attribute sigma_Cy : Real = 28.23690002309109;
                                attribute Cz : Real = -99.15952100418508;
                                attribute sigma_Cz : Real = 29.057750463592832;
                                attribute Ixx : Real = 0.9374087253379887;
                                attribute sigma_Ixx : Real = 0.37074144170588635;
                                attribute Iyy : Real = 0.9514757553391375;
                                attribute sigma_Iyy : Real = 0.3723953238821935;
                                attribute Izz : Real = 0.8685434771771978;
                                attribute sigma_Izz : Real = 0.37017423652493897;
                                attribute Ixy : Real = 0.0643372036197539;
                                attribute sigma_Ixy : Real = 0.02351283871158888;
                                attribute Ixz : Real = -0.04455661814485534;
                                attribute sigma_Ixz : Real = 0.022566176940390956;
                                attribute Iyz : Real = 0.01916930260284995;
                                attribute sigma_Iyz : Real = 0.02209918015384651;
                            }
                            part <'C.1.1.4.1.1.4.2'> 'Part 510' {
                                attribute POIconv : String = "+";
                                attribute Ipoint : Boolean = false;
                                attribute mass : Real = 0.9193144191103056;
                                attribute sigma_mass : Real = 0.28909372274994966;
                                attribute Cx : Real = -81.98665287345648;
                                attribute sigma_Cx : Real = 28.721044428837228;
                                attribute Cy : Real = 45.633562095463276;
                                attribute sigma_Cy : Real = 28.23690002309109;
                                attribute Cz : Real = -91.58319300040603;
                                attribute sigma_Cz : Real = 29.057750463592832;
                                attribute Ixx : Real = 0.9433558125814777;
                                attribute sigma_Ixx : Real = 0.37074144170588635;
                                attribute Iyy : Real = 1.195947309742223;
                                attribute sigma_Iyy : Real = 0.3723953238821935;
                                attribute Izz : Real = 1.2085314562068112;
                                attribute sigma_Izz : Real = 0.37017423652493897;
                                attribute Ixy : Real = -0.1005473448582731;
                                attribute sigma_Ixy : Real = 0.02351283871158888;
                                attribute Ixz : Real = -0.0029584935395142887;
                                attribute sigma_Ixz : Real = 0.022566176940390956;
                                attribute Iyz : Real = 0.003047434934544749;
                                attribute sigma_Iyz : Real = 0.02209918015384651;
                            }
                            part <'C.1.1.4.1.1.4.3'> 'Part 511' {
                                attribute POIconv : String = "+";
                                attribute Ipoint : Boolean = false;
                                attribute mass : Real = 0.7343257454780396;
                                attribute sigma_mass : Real = 0.28909372274994966;
                                attribute Cx : Real = -60.674673644825816;
                                attribute sigma_Cx : Real = 28.721044428837228;
                                attribute Cy : Real = -71.01439191028476;
                                attribute sigma_Cy : Real = 28.23690002309109;
                                attribute Cz : Real = -43.64943685941398;
                                attribute sigma_Cz : Real = 29.057750463592832;
                                attribute Ixx : Real = 0.9768430900978795;
                                attribute sigma_Ixx : Real = 0.37074144170588635;
                                attribute Iyy : Real = 0.9807778606629555;
                                attribute sigma_Iyy : Real = 0.3723953238821935;
                                attribute Izz : Real = 1.0248103057913742;
                                attribute sigma_Izz : Real = 0.37017423652493897;
                                attribute Ixy : Real = -0.02571439581950459;
                                attribute sigma_Ixy : Real = 0.02351283871158888;
                                attribute Ixz : Real = 0.05819663789954853;
                                attribute sigma_Ixz : Real = 0.022566176940390956;
                                attribute Iyz : Real = 0.06701639868147345;
                                attribute sigma_Iyz : Real = 0.02209918015384651;
                            }
                        }
                        part <'C.1.1.4.1.1.5'> 'Subassembly 150' {
                            attribute POIconv : String = "-";
                            attribute Ipoint : Boolean = false;
                            attribute mass : Real = 3.678684391085058;
                            attribute sigma_mass : Real = 0.6464332159373649;
                            attribute Cx : Real = -7.018914562542803;
                            attribute sigma_Cx : Real = 18.869935533677033;
                            attribute Cy : Real = -19.463929505224353;
                            attribute sigma_Cy : Real = 16.426192057293505;
                            attribute Cz : Real = 21.277409532162327;
                            attribute sigma_Cz : Real = 15.4187214006521;
                            attribute Ixx : Real = 18129.29599308303;
                            attribute sigma_Ixx : Real = 7704.310401322725;
                            attribute Iyy : Real = 27276.918118659036;
                            attribute sigma_Iyy : Real = 9900.84538289794;
                            attribute Izz : Real = 32079.57061800935;
                            attribute sigma_Izz : Real = 10824.414713011476;
                            attribute Ixy : Real = 3074.2787316112676;
                            attribute sigma_Ixy : Real = 5139.320629312636;
                            attribute Ixz : Real = 2660.4156494114827;
                            attribute sigma_Ixz : Real = 4693.297658095326;
                            attribute Iyz : Real = -4036.8036579710933;
                            attribute sigma_Iyz : Real = 3806.64146334936;
                            part <'C.1.1.4.1.1.5.1'> 'Part 512' {
                                attribute POIconv : String = "+";
                                attribute Ipoint : Boolean = false;
                                attribute mass : Real = 0.9244312414054293;
                                attribute sigma_mass : Real = 0.28909372274994966;
                                attribute Cx : Real = -89.39456627704203;
                                attribute sigma_Cx : Real = 28.721044428837228;
                                attribute Cy : Real = -72.10332262329757;
                                attribute sigma_Cy : Real = 28.23690002309109;
                                attribute Cz : Real = -11.877620220184326;
                                attribute sigma_Cz : Real = 29.057750463592832;
                                attribute Ixx : Real = 0.9625880694857643;
                                attribute sigma_Ixx : Real = 0.37074144170588635;
                                attribute Iyy : Real = 0.9995136022350133;
                                attribute sigma_Iyy : Real = 0.3723953238821935;
                                attribute Izz : Real = 0.931533633211416;
                                attribute sigma_Izz : Real = 0.37017423652493897;
                                attribute Ixy : Real = 0.0319529691275307;
                                attribute sigma_Ixy : Real = 0.02351283871158888;
                                attribute Ixz : Real = -0.0007976356947282433;
                                attribute sigma_Ixz : Real = 0.022566176940390956;
                                attribute Iyz : Real = 0.0019611538758315767;
                                attribute sigma_Iyz : Real = 0.02209918015384651;
                            }
                            part <'C.1.1.4.1.1.5.2'> 'Part 513' {
                                attribute POIconv : String = "+";
                                attribute Ipoint : Boolean = false;
                                attribute mass : Real = 0.9096533798619639;
                                attribute sigma_mass : Real = 0.28909372274994966;
                                attribute Cx : Real = 14.317942783236504;
                                attribute sigma_Cx : Real = 28.721044428837228;
                                attribute Cy : Real = 23.003308288753033;
                                attribute sigma_Cy : Real = 28.23690002309109;
                                attribute Cz : Real = 11.833685915917158;
                                attribute sigma_Cz : Real = 29.057750463592832;
                                attribute Ixx : Real = 1.1503000977823834;
                                attribute sigma_Ixx : Real = 0.37074144170588635;
                                attribute Iyy : Real = 1.352556402018026;
                                attribute sigma_Iyy : Real = 0.3723953238821935;
                                attribute Izz : Real = 1.1871868457136197;
                                attribute sigma_Izz : Real = 0.37017423652493897;
                                attribute Ixy : Real = 0.06340178962361812;
                                attribute sigma_Ixy : Real = 0.02351283871158888;
                                attribute Ixz : Real = -0.03235343579978285;
                                attribute sigma_Ixz : Real = 0.022566176940390956;
                                attribute Iyz : Real = 0.024507867845197238;
                                attribute sigma_Iyz : Real = 0.02209918015384651;
                            }
                            part <'C.1.1.4.1.1.5.3'> 'Part 514' {
                                attribute POIconv : String = "+";
                                attribute Ipoint : Boolean = false;
                                attribute mass : Real = 0.6854223290602677;
                                attribute sigma_mass : Real = 0.28909372274994966;
                                attribute Cx : Real = -81.22497540898621;
                                attribute sigma_Cx : Real = 28.721044428837228;
                                attribute Cy : Real = 61.280407942831516;
                                attribute sigma_Cy : Real = 28.23690002309109;
                                attribute Cz : Real = 91.70466652140021;
                                attribute sigma_Cz : Real = 29.057750463592832;
                                attribute Ixx : Real = 0.840288786584783;
                                attribute sigma_Ixx : Real = 0.37074144170588635;
                                attribute Iyy : Real = 0.765126331573571;
                                attribute sigma_Iyy : Real = 0.3723953238821935;
                                attribute Izz : Real = 0.9136166916816478;
                                attribute sigma_Izz : Real = 0.37017423652493897;
                                attribute Ixy : Real = -0.031214598633100672;
                                attribute sigma_Ixy : Real = 0.02351283871158888;
                                attribute Ixz : Real = -0.06336153824575526;
                                attribute sigma_Ixz : Real = 0.022566176940390956;
                                attribute Iyz : Real = 0.01069291073437795;
                                attribute sigma_Iyz : Real = 0.02209918015384651;
                            }
                            part <'C.1.1.4.1.1.5.4'> 'Part 515' {
                                attribute POIconv : String = "-";
                                attribute Ipoint : Boolean = false;
                                attribute mass : Real = 0.49952153636235747;
                                attribute sigma_mass : Real = 0.28909372274994966;
                                attribute Cx : Real = 72.25212324410677;
                                attribute sigma_Cx : Real = 28.721044428837228;
                                attribute Cy : Real = -92.67154415138066;
                                attribute sigma_Cy : Real = 28.23690002309109;
                                attribute Cz : Real = 62.323373928666115;
                                attribute sigma_Cz : Real = 29.057750463592832;
                                attribute Ixx : Real = 0.5346172155904334;
                                attribute sigma_Ixx : Real = 0.37074144170588635;
                                attribute Iyy : Real = 0.5911417852422811;
                                attribute sigma_Iyy : Real = 0.3723953238821935;
                                attribute Izz : Real = 0.6126056555355612;
                                attribute sigma_Izz : Real = 0.37017423652493897;
                                attribute Ixy : Real = -0.03708017841672464;
                                attribute sigma_Ixy : Real = 0.02351283871158888;
                                attribute Ixz : Real = 0.020139354272028558;
                                attribute sigma_Ixz : Real = 0.022566176940390956;
                                attribute Iyz : Real = 0.010303087585634347;
                                attribute sigma_Iyz : Real = 0.02209918015384651;
                            }
                            part <'C.1.1.4.1.1.5.5'> 'Part 516' {
                                attribute POIconv : String = "-";
                                attribute Ipoint : Boolean = false;
                                attribute mass : Real = 0.6596559043950401;
                                attribute sigma_mass : Real = 0.28909372274994966;
                                attribute Cx : Real = 96.07480685226619;
                                attribute sigma_Cx : Real = 28.721044428837228;
                                attribute Cy : Real = -32.71956550888717;
                                attribute sigma_Cy : Real = 28.23690002309109;
                                attribute Cz : Real = -23.496990418061614;
                                attribute sigma_Cz : Real = 29.057750463592832;
                                attribute Ixx : Real = 1.0029103028587736;
                                attribute sigma_Ixx : Real = 0.37074144170588635;
                                attribute Iyy : Real = 0.8145827853681636;
                                attribute sigma_Iyy : Real = 0.3723953238821935;
                                attribute Izz : Real = 0.7839846645719909;
                                attribute sigma_Izz : Real = 0.37017423652493897;
                                attribute Ixy : Real = -0.015701094904586873;
                                attribute sigma_Ixy : Real = 0.02351283871158888;
                                attribute Ixz : Real = 0.05128851210941665;
                                attribute sigma_Ixz : Real = 0.022566176940390956;
                                attribute Iyz : Real = 0.018949446427329923;
                                attribute sigma_Iyz : Real = 0.02209918015384651;
                            }
                        }
                    }
                    part <'C.1.1.4.1.2'> 'Assembly 41' {
                        attribute POIconv : String = "-";
                        attribute Ipoint : Boolean = false;
                        attribute mass : Real = 7.216313157902565;
                        attribute sigma_mass : Real = 1.001450031904287;
                        attribute Cx : Real = -10.787562618113247;
                        attribute sigma_Cx : Real = 12.53265475356088;
                        attribute Cy : Real = -0.1040860407431898;
                        attribute sigma_Cy : Real = 11.72531773038104;
                        attribute Cz : Real = -13.713855321445363;
                        attribute sigma_Cz : Real = 10.808898238155772;
                        attribute Ixx : Real = 35743.89203351809;
                        attribute sigma_Ixx : Real = 10608.787471738962;
                        attribute Iyy : Real = 41902.43749768554;
                        attribute sigma_Iyy : Real = 12430.894014349213;
                        attribute Izz : Real = 50043.12661832193;
                        attribute sigma_Izz : Real = 13872.18929083917;
                        attribute Ixy : Real = -2486.2894188927257;
                        attribute sigma_Ixy : Real = 6307.675629722405;
                        attribute Ixz : Real = 3559.509211006864;
                        attribute sigma_Ixz : Real = 5635.993961064739;
                        attribute Iyz : Real = -6844.839739210619;
                        attribute sigma_Iyz : Real = 5026.001890652663;
                        part <'C.1.1.4.1.2.1'> 'Subassembly 151' {
                            attribute POIconv : String = "-";
                            attribute Ipoint : Boolean = false;
                            attribute mass : Real = 1.2753560230182484;
                            attribute sigma_mass : Real = 0.40884026350990615;
                            attribute Cx : Real = 73.03096301567876;
                            attribute sigma_Cx : Real = 25.760110064133244;
                            attribute Cy : Real = 9.699611473914713;
                            attribute sigma_Cy : Real = 21.56952288946436;
                            attribute Cz : Real = -10.331112578522077;
                            attribute sigma_Cz : Real = 22.66173337781495;
                            attribute Ixx : Real = 513.5713725198705;
                            attribute sigma_Ixx : Real = 1004.7797029065646;
                            attribute Iyy : Real = 2269.163393759423;
                            attribute sigma_Iyy : Real = 2327.05067335648;
                            attribute Izz : Real = 2059.7511378521017;
                            attribute sigma_Izz : Real = 2188.1954801692564;
                            attribute Ixy : Real = -537.2709183886516;
                            attribute sigma_Ixy : Real = 992.4040870761726;
                            attribute Ixz : Real = 829.3628074799155;
                            attribute sigma_Ixz : Real = 1107.6213551998615;
                            attribute Iyz : Real = 233.64993820429567;
                            attribute sigma_Iyz : Real = 494.25047895609305;
                            part <'C.1.1.4.1.2.1.1'> 'Part 517' {
                                attribute POIconv : String = "-";
                                attribute Ipoint : Boolean = false;
                                attribute mass : Real = 0.41000311004486867;
                                attribute sigma_mass : Real = 0.28909372274994966;
                                attribute Cx : Real = 16.853980906307697;
                                attribute sigma_Cx : Real = 28.721044428837228;
                                attribute Cy : Real = -6.128946784883738;
                                attribute sigma_Cy : Real = 28.23690002309109;
                                attribute Cz : Real = 14.10215892829001;
                                attribute sigma_Cz : Real = 29.057750463592832;
                                attribute Ixx : Real = 0.47778954938366125;
                                attribute sigma_Ixx : Real = 0.37074144170588635;
                                attribute Iyy : Real = 0.5714028656326395;
                                attribute sigma_Iyy : Real = 0.3723953238821935;
                                attribute Izz : Real = 0.48031025401157584;
                                attribute sigma_Izz : Real = 0.37017423652493897;
                                attribute Ixy : Real = -0.004502894132199777;
                                attribute sigma_Ixy : Real = 0.02351283871158888;
                                attribute Ixz : Real = -0.018596824840074997;
                                attribute sigma_Ixz : Real = 0.022566176940390956;
                                attribute Iyz : Real = -0.02018899642869716;
                                attribute sigma_Iyz : Real = 0.02209918015384651;
                            }
                            part <'C.1.1.4.1.2.1.2'> 'Part 518' {
                                attribute POIconv : String = "+";
                                attribute Ipoint : Boolean = false;
                                attribute mass : Real = 0.8653529129733797;
                                attribute sigma_mass : Real = 0.28909372274994966;
                                attribute Cx : Real = 99.6475457213819;
                                attribute sigma_Cx : Real = 28.721044428837228;
                                attribute Cy : Real = 17.19916225410998;
                                attribute sigma_Cy : Real = 28.23690002309109;
                                attribute Cz : Real = -21.90756555646658;
                                attribute sigma_Cz : Real = 29.057750463592832;
                                attribute Ixx : Real = 0.9645578906122143;
                                attribute sigma_Ixx : Real = 0.37074144170588635;
                                attribute Iyy : Real = 0.8943157698886668;
                                attribute sigma_Iyy : Real = 0.3723953238821935;
                                attribute Izz : Real = 0.9146077309781221;
                                attribute sigma_Izz : Real = 0.37017423652493897;
                                attribute Ixy : Real = -0.04379352077068726;
                                attribute sigma_Ixy : Real = 0.02351283871158888;
                                attribute Ixz : Real = 0.021122798752214622;
                                attribute sigma_Ixz : Real = 0.022566176940390956;
                                attribute Iyz : Real = 0.024274443940810565;
                                attribute sigma_Iyz : Real = 0.02209918015384651;
                            }
                        }
                        part <'C.1.1.4.1.2.2'> 'Subassembly 152' {
                            attribute POIconv : String = "-";
                            attribute Ipoint : Boolean = false;
                            attribute mass : Real = 1.9863272017547864;
                            attribute sigma_mass : Real = 0.6464332159373649;
                            attribute Cx : Real = -25.64792777386371;
                            attribute sigma_Cx : Real = 23.93511774813393;
                            attribute Cy : Real = 11.101040202455827;
                            attribute sigma_Cy : Real = 25.0891768076395;
                            attribute Cz : Real = 7.582706646362277;
                            attribute sigma_Cz : Real = 19.44416909970867;
                            attribute Ixx : Real = 12279.730186973358;
                            attribute sigma_Ixx : Real = 5990.292250424986;
                            attribute Iyy : Real = 11520.747971991761;
                            attribute sigma_Iyy : Real = 6937.576293603617;
                            attribute Izz : Real = 15082.49350805903;
                            attribute sigma_Izz : Real = 8005.607943126942;
                            attribute Ixy : Real = 4207.861957931411;
                            attribute sigma_Ixy : Real = 3654.036498943014;
                            attribute Ixz : Real = 3538.7945135593463;
                            attribute sigma_Ixz : Real = 3075.5303734897398;
                            attribute Iyz : Real = -4186.631010826217;
                            attribute sigma_Iyz : Real = 2741.500820797883;
                            part <'C.1.1.4.1.2.2.1'> 'Part 519' {
                                attribute POIconv : String = "+";
                                attribute Ipoint : Boolean = false;
                                attribute mass : Real = 0.6837532957738731;
                                attribute sigma_mass : Real = 0.28909372274994966;
                                attribute Cx : Real = -56.20675147511065;
                                attribute sigma_Cx : Real = 28.721044428837228;
                                attribute Cy : Real = 55.573108745738864;
                                attribute sigma_Cy : Real = 28.23690002309109;
                                attribute Cz : Real = 66.8166727758944;
                                attribute sigma_Cz : Real = 29.057750463592832;
                                attribute Ixx : Real = 0.8410994866521762;
                                attribute sigma_Ixx : Real = 0.37074144170588635;
                                attribute Iyy : Real = 0.8097497730051931;
                                attribute sigma_Iyy : Real = 0.3723953238821935;
                                attribute Izz : Real = 0.718105479632145;
                                attribute sigma_Izz : Real = 0.37017423652493897;
                                attribute Ixy : Real = 0.021607717832973276;
                                attribute sigma_Ixy : Real = 0.02351283871158888;
                                attribute Ixz : Real = -0.028564621897542386;
                                attribute sigma_Ixz : Real = 0.022566176940390956;
                                attribute Iyz : Real = 0.003961467486292775;
                                attribute sigma_Iyz : Real = 0.02209918015384651;
                            }
                            part <'C.1.1.4.1.2.2.2'> 'Part 520' {
                                attribute POIconv : String = "-";
                                attribute Ipoint : Boolean = false;
                                attribute mass : Real = 0.39166785358823836;
                                attribute sigma_mass : Real = 0.28909372274994966;
                                attribute Cx : Real = 94.9291265103966;
                                attribute sigma_Cx : Real = 28.721044428837228;
                                attribute Cy : Real = -66.76699281670153;
                                attribute sigma_Cy : Real = 28.23690002309109;
                                attribute Cz : Real = -53.59317106194794;
                                attribute sigma_Cz : Real = 29.057750463592832;
                                attribute Ixx : Real = 0.43534843491940195;
                                attribute sigma_Ixx : Real = 0.37074144170588635;
                                attribute Iyy : Real = 0.380285334329808;
                                attribute sigma_Iyy : Real = 0.3723953238821935;
                                attribute Izz : Real = 0.4248309822193187;
                                attribute sigma_Izz : Real = 0.37017423652493897;
                                attribute Ixy : Real = 0.007679311515031858;
                                attribute sigma_Ixy : Real = 0.02351283871158888;
                                attribute Ixz : Real = 0.003376428021013025;
                                attribute sigma_Ixz : Real = 0.022566176940390956;
                                attribute Iyz : Real = -0.011841042450287682;
                                attribute sigma_Iyz : Real = 0.02209918015384651;
                            }
                            part <'C.1.1.4.1.2.2.3'> 'Part 521' {
                                attribute POIconv : String = "-";
                                attribute Ipoint : Boolean = false;
                                attribute mass : Real = 0.3471679254688788;
                                attribute sigma_mass : Real = 0.28909372274994966;
                                attribute Cx : Real = -46.54039852321148;
                                attribute sigma_Cx : Real = 28.721044428837228;
                                attribute Cy : Real = 97.59303494356573;
                                attribute sigma_Cy : Real = 28.23690002309109;
                                attribute Cz : Real = -0.3798075020313263;
                                attribute sigma_Cz : Real = 29.057750463592832;
                                attribute Ixx : Real = 0.38467490654491604;
                                attribute sigma_Ixx : Real = 0.37074144170588635;
                                attribute Iyy : Real = 0.4135284416805727;
                                attribute sigma_Iyy : Real = 0.3723953238821935;
                                attribute Izz : Real = 0.42745379410190576;
                                attribute sigma_Izz : Real = 0.37017423652493897;
                                attribute Ixy : Real = 0.01747201067888183;
                                attribute sigma_Ixy : Real = 0.02351283871158888;
                                attribute Ixz : Real = 0.004078329259058244;
                                attribute sigma_Ixz : Real = 0.022566176940390956;
                                attribute Iyz : Real = -0.003093103025726222;
                                attribute sigma_Iyz : Real = 0.02209918015384651;
                            }
                            part <'C.1.1.4.1.2.2.4'> 'Part 522' {
                                attribute POIconv : String = "+";
                                attribute Ipoint : Boolean = false;
                                attribute mass : Real = 0.18107663277769462;
                                attribute sigma_mass : Real = 0.28909372274994966;
                                attribute Cx : Real = -48.79382927902043;
                                attribute sigma_Cx : Real = 28.721044428837228;
                                attribute Cy : Real = -37.45818850584328;
                                attribute sigma_Cy : Real = 28.23690002309109;
                                attribute Cz : Real = 5.572905112057924;
                                attribute sigma_Cz : Real = 29.057750463592832;
                                attribute Ixx : Real = 0.2328714827508313;
                                attribute sigma_Ixx : Real = 0.37074144170588635;
                                attribute Iyy : Real = 0.2604739659824552;
                                attribute sigma_Iyy : Real = 0.3723953238821935;
                                attribute Izz : Real = 0.23155667554441034;
                                attribute sigma_Izz : Real = 0.37017423652493897;
                                attribute Ixy : Real = -0.01654653336893626;
                                attribute sigma_Ixy : Real = 0.02351283871158888;
                                attribute Ixz : Real = 0.012686905446272614;
                                attribute sigma_Ixz : Real = 0.022566176940390956;
                                attribute Iyz : Real = -0.006469262526130462;
                                attribute sigma_Iyz : Real = 0.02209918015384651;
                            }
                            part <'C.1.1.4.1.2.2.5'> 'Part 523' {
                                attribute POIconv : String = "+";
                                attribute Ipoint : Boolean = false;
                                attribute mass : Real = 0.3826614941461012;
                                attribute sigma_mass : Real = 0.28909372274994966;
                                attribute Cx : Real = -64.55197799950838;
                                attribute sigma_Cx : Real = 28.721044428837228;
                                attribute Cy : Real = -44.15359911508858;
                                attribute sigma_Cy : Real = 28.23690002309109;
                                attribute Cz : Real = -27.46795155107975;
                                attribute sigma_Cz : Real = 29.057750463592832;
                                attribute Ixx : Real = 0.5602413092688002;
                                attribute sigma_Ixx : Real = 0.37074144170588635;
                                attribute Iyy : Real = 0.5295045602444619;
                                attribute sigma_Iyy : Real = 0.3723953238821935;
                                attribute Izz : Real = 0.5264923557380612;
                                attribute sigma_Izz : Real = 0.37017423652493897;
                                attribute Ixy : Real = 0.03884203471140327;
                                attribute sigma_Ixy : Real = 0.02351283871158888;
                                attribute Ixz : Real = 0.026965996211844034;
                                attribute sigma_Ixz : Real = 0.022566176940390956;
                                attribute Iyz : Real = -0.01463950706222535;
                                attribute sigma_Iyz : Real = 0.02209918015384651;
                            }
                        }
                        part <'C.1.1.4.1.2.3'> 'Subassembly 153' {
                            attribute POIconv : String = "-";
                            attribute Ipoint : Boolean = false;
                            attribute mass : Real = 3.9546299331295307;
                            attribute sigma_mass : Real = 0.6464332159373649;
                            attribute Cx : Real = -30.35473205726577;
                            attribute sigma_Cx : Real = 14.77287667815908;
                            attribute Cy : Real = -8.893846983462497;
                            attribute sigma_Cy : Real = 15.625421009217424;
                            attribute Cz : Real = -25.501593355160985;
                            attribute sigma_Cz : Real = 14.976010630608954;
                            attribute Ixx : Real = 20808.106919136313;
                            attribute sigma_Ixx : Real = 8251.02463116321;
                            attribute Iyy : Real = 15734.70911269006;
                            attribute sigma_Iyy : Real = 7081.779340676361;
                            attribute Izz : Real = 21310.538584754486;
                            attribute sigma_Izz : Real = 8641.16989026268;
                            attribute Ixy : Real = -4759.4683882418385;
                            attribute sigma_Ixy : Real = 4163.533967784009;
                            attribute Ixz : Real = -163.5144526988272;
                            attribute sigma_Ixz : Real = 3456.6671529608016;
                            attribute Iyz : Real = -1965.8202185005332;
                            attribute sigma_Iyz : Real = 3907.4197594092234;
                            part <'C.1.1.4.1.2.3.1'> 'Part 524' {
                                attribute POIconv : String = "+";
                                attribute Ipoint : Boolean = false;
                                attribute mass : Real = 0.6760756892520003;
                                attribute sigma_mass : Real = 0.28909372274994966;
                                attribute Cx : Real = -48.60744355246425;
                                attribute sigma_Cx : Real = 28.721044428837228;
                                attribute Cy : Real = 1.9151626620441675;
                                attribute sigma_Cy : Real = 28.23690002309109;
                                attribute Cz : Real = -81.41932506114244;
                                attribute sigma_Cz : Real = 29.057750463592832;
                                attribute Ixx : Real = 0.7201907668695394;
                                attribute sigma_Ixx : Real = 0.37074144170588635;
                                attribute Iyy : Real = 0.922481063063426;
                                attribute sigma_Iyy : Real = 0.3723953238821935;
                                attribute Izz : Real = 0.8243393060295088;
                                attribute sigma_Izz : Real = 0.37017423652493897;
                                attribute Ixy : Real = -0.005033514329887098;
                                attribute sigma_Ixy : Real = 0.02351283871158888;
                                attribute Ixz : Real = 0.00998159031917946;
                                attribute sigma_Ixz : Real = 0.022566176940390956;
                                attribute Iyz : Real = 0.002482970801378602;
                                attribute sigma_Iyz : Real = 0.02209918015384651;
                            }
                            part <'C.1.1.4.1.2.3.2'> 'Part 525' {
                                attribute POIconv : String = "+";
                                attribute Ipoint : Boolean = false;
                                attribute mass : Real = 0.7991010712103452;
                                attribute sigma_mass : Real = 0.28909372274994966;
                                attribute Cx : Real = 33.9585923589766;
                                attribute sigma_Cx : Real = 28.721044428837228;
                                attribute Cy : Real = 17.71317757666111;
                                attribute sigma_Cy : Real = 28.23690002309109;
                                attribute Cz : Real = 22.58733408525586;
                                attribute sigma_Cz : Real = 29.057750463592832;
                                attribute Ixx : Real = 0.9998229199778262;
                                attribute sigma_Ixx : Real = 0.37074144170588635;
                                attribute Iyy : Real = 0.8945321315626844;
                                attribute sigma_Iyy : Real = 0.3723953238821935;
                                attribute Izz : Real = 0.8637840937328598;
                                attribute sigma_Izz : Real = 0.37017423652493897;
                                attribute Ixy : Real = 0.009636668893692189;
                                attribute sigma_Ixy : Real = 0.02351283871158888;
                                attribute Ixz : Real = -0.05779031517671056;
                                attribute sigma_Ixz : Real = 0.022566176940390956;
                                attribute Iyz : Real = -0.018506995438087405;
                                attribute sigma_Iyz : Real = 0.02209918015384651;
                            }
                            part <'C.1.1.4.1.2.3.3'> 'Part 526' {
                                attribute POIconv : String = "-";
                                attribute Ipoint : Boolean = false;
                                attribute mass : Real = 0.9110064355321229;
                                attribute sigma_mass : Real = 0.28909372274994966;
                                attribute Cx : Real = -94.47562443092465;
                                attribute sigma_Cx : Real = 28.721044428837228;
                                attribute Cy : Real = -90.03030015155673;
                                attribute sigma_Cy : Real = 28.23690002309109;
                                attribute Cz : Real = -1.1231498327106237;
                                attribute sigma_Cz : Real = 29.057750463592832;
                                attribute Ixx : Real = 1.096439154251778;
                                attribute sigma_Ixx : Real = 0.37074144170588635;
                                attribute Iyy : Real = 0.8712155216492115;
                                attribute sigma_Iyy : Real = 0.3723953238821935;
                                attribute Izz : Real = 1.0668016034817485;
                                attribute sigma_Izz : Real = 0.37017423652493897;
                                attribute Ixy : Real = -0.038325947877435616;
                                attribute sigma_Ixy : Real = 0.02351283871158888;
                                attribute Ixz : Real = -0.03377123354790197;
                                attribute sigma_Ixz : Real = 0.022566176940390956;
                                attribute Iyz : Real = -0.08827234052661215;
                                attribute sigma_Iyz : Real = 0.02209918015384651;
                            }
                            part <'C.1.1.4.1.2.3.4'> 'Part 527' {
                                attribute POIconv : String = "+";
                                attribute Ipoint : Boolean = false;
                                attribute mass : Real = 0.8071762318208348;
                                attribute sigma_mass : Real = 0.28909372274994966;
                                attribute Cx : Real = -37.0194410905242;
                                attribute sigma_Cx : Real = 28.721044428837228;
                                attribute Cy : Real = 76.13122160546482;
                                attribute sigma_Cy : Real = 28.23690002309109;
                                attribute Cz : Real = 0.8116914425045252;
                                attribute sigma_Cz : Real = 29.057750463592832;
                                attribute Ixx : Real = 1.1201184169649436;
                                attribute sigma_Ixx : Real = 0.37074144170588635;
                                attribute Iyy : Real = 1.1614061531548077;
                                attribute sigma_Iyy : Real = 0.3723953238821935;
                                attribute Izz : Real = 1.1666480153913994;
                                attribute sigma_Izz : Real = 0.37017423652493897;
                                attribute Ixy : Real = -0.036721524236853285;
                                attribute sigma_Ixy : Real = 0.02351283871158888;
                                attribute Ixz : Real = 0.024626946470446755;
                                attribute sigma_Ixz : Real = 0.022566176940390956;
                                attribute Iyz : Real = 0.03349693345283089;
                                attribute sigma_Iyz : Real = 0.02209918015384651;
                            }
                            part <'C.1.1.4.1.2.3.5'> 'Part 528' {
                                attribute POIconv : String = "+";
                                attribute Ipoint : Boolean = false;
                                attribute mass : Real = 0.7612705053142272;
                                attribute sigma_mass : Real = 0.28909372274994966;
                                attribute Cx : Real = 2.145552961155772;
                                attribute sigma_Cx : Real = 28.721044428837228;
                                attribute Cy : Real = -39.47928776033223;
                                attribute sigma_Cy : Real = 28.23690002309109;
                                attribute Cz : Real = -83.39385520666838;
                                attribute sigma_Cz : Real = 29.057750463592832;
                                attribute Ixx : Real = 1.1552668000444546;
                                attribute sigma_Ixx : Real = 0.37074144170588635;
                                attribute Iyy : Real = 1.206785808894924;
                                attribute sigma_Iyy : Real = 0.3723953238821935;
                                attribute Izz : Real = 1.1756614795846687;
                                attribute sigma_Izz : Real = 0.37017423652493897;
                                attribute Ixy : Real = 0.01825743615970654;
                                attribute sigma_Ixy : Real = 0.02351283871158888;
                                attribute Ixz : Real = -0.007411964907153561;
                                attribute sigma_Ixz : Real = 0.022566176940390956;
                                attribute Iyz : Real = 0.007563782476518617;
                                attribute sigma_Iyz : Real = 0.02209918015384651;
                            }
                        }
                    }
                }
                part <'C.1.1.4.2'> 'Subsystem 12' {
                    attribute POIconv : String = "-";
                    attribute Ipoint : Boolean = false;
                    attribute mass : Real = 18.895376798995073;
                    attribute sigma_mass : Real = 1.805389719922977;
                    attribute Cx : Real = -15.279181902800083;
                    attribute sigma_Cx : Real = 7.393866237877022;
                    attribute Cy : Real = -3.4323749165347492;
                    attribute sigma_Cy : Real = 8.048202395108124;
                    attribute Cz : Real = -2.795277754781757;
                    attribute sigma_Cz : Real = 8.128862296623232;
                    attribute Ixx : Real = 123780.02571989398;
                    attribute sigma_Ixx : Real = 24090.854043718024;
                    attribute Iyy : Real = 117355.16619031268;
                    attribute sigma_Iyy : Real = 21529.133267155063;
                    attribute Izz : Real = 99754.15908095233;
                    attribute sigma_Izz : Real = 21884.349994593544;
                    attribute Ixy : Real = 12473.993758313602;
                    attribute sigma_Ixy : Real = 10154.995080563329;
                    attribute Ixz : Real = -9562.238572935054;
                    attribute sigma_Ixz : Real = 10244.887993174047;
                    attribute Iyz : Real = 16315.711758488393;
                    attribute sigma_Iyz : Real = 10746.460523204809;
                    part <'C.1.1.4.2.1'> 'Assembly 42' {
                        attribute POIconv : String = "-";
                        attribute Ipoint : Boolean = false;
                        attribute mass : Real = 8.958404655794846;
                        attribute sigma_mass : Real = 1.1919639546010696;
                        attribute Cx : Real = -16.18772418212669;
                        attribute sigma_Cx : Real = 10.372057821360611;
                        attribute Cy : Real = 8.585900593565773;
                        attribute sigma_Cy : Real = 11.23628025127915;
                        attribute Cz : Real = -11.140076707724218;
                        attribute sigma_Cz : Real = 10.977678459851026;
                        attribute Ixx : Real = 63336.75710341278;
                        attribute sigma_Ixx : Real = 15219.56543131251;
                        attribute Iyy : Real = 56712.16646987146;
                        attribute sigma_Iyy : Real = 13719.943378973712;
                        attribute Izz : Real = 52578.69787282648;
                        attribute sigma_Izz : Real = 13738.5128050958;
                        attribute Ixy : Real = 15794.239139437817;
                        attribute sigma_Ixy : Real = 6479.065764101622;
                        attribute Ixz : Real = -12575.32936059726;
                        attribute sigma_Ixz : Real = 6630.795117738319;
                        attribute Iyz : Real = 4960.599693085545;
                        attribute sigma_Iyz : Real = 7180.959195185249;
                        part <'C.1.1.4.2.1.1'> 'Subassembly 154' {
                            attribute POIconv : String = "-";
                            attribute Ipoint : Boolean = false;
                            attribute mass : Real = 2.7516231605238284;
                            attribute sigma_mass : Real = 0.6464332159373649;
                            attribute Cx : Real = -34.49833425195016;
                            attribute sigma_Cx : Real = 17.067509462451515;
                            attribute Cy : Real = 36.0387821361655;
                            attribute sigma_Cy : Real = 19.984753702782076;
                            attribute Cz : Real = -8.20112874827087;
                            attribute sigma_Cz : Real = 19.542118313906496;
                            attribute Ixx : Real = 18026.08416041734;
                            attribute sigma_Ixx : Real = 8191.068958727249;
                            attribute Iyy : Real = 12552.244915223244;
                            attribute sigma_Iyy : Real = 6114.22985232806;
                            attribute Izz : Real = 12485.176526945796;
                            attribute sigma_Izz : Real = 6706.679274583518;
                            attribute Ixy : Real = 2017.0896989202174;
                            attribute sigma_Ixy : Real = 3048.568149319477;
                            attribute Ixz : Real = -3643.5328913899866;
                            attribute sigma_Ixz : Real = 2942.8371836722176;
                            attribute Iyz : Real = 1524.3145698744443;
                            attribute sigma_Iyz : Real = 3895.0204803952406;
                            part <'C.1.1.4.2.1.1.1'> 'Part 529' {
                                attribute POIconv : String = "+";
                                attribute Ipoint : Boolean = false;
                                attribute mass : Real = 0.6284591646608897;
                                attribute sigma_mass : Real = 0.28909372274994966;
                                attribute Cx : Real = -83.70220358483493;
                                attribute sigma_Cx : Real = 28.721044428837228;
                                attribute Cy : Real = 22.98341770656407;
                                attribute sigma_Cy : Real = 28.23690002309109;
                                attribute Cz : Real = -77.08602547645569;
                                attribute sigma_Cz : Real = 29.057750463592832;
                                attribute Ixx : Real = 0.7289515272536714;
                                attribute sigma_Ixx : Real = 0.37074144170588635;
                                attribute Iyy : Real = 0.8334239015420141;
                                attribute sigma_Iyy : Real = 0.3723953238821935;
                                attribute Izz : Real = 0.7199228073363848;
                                attribute sigma_Izz : Real = 0.37017423652493897;
                                attribute Ixy : Real = 0.07553193767996923;
                                attribute sigma_Ixy : Real = 0.02351283871158888;
                                attribute Ixz : Real = 0.001305894580315578;
                                attribute sigma_Ixz : Real = 0.022566176940390956;
                                attribute Iyz : Real = -0.014377140353095685;
                                attribute sigma_Iyz : Real = 0.02209918015384651;
                            }
                            part <'C.1.1.4.2.1.1.2'> 'Part 530' {
                                attribute POIconv : String = "-";
                                attribute Ipoint : Boolean = false;
                                attribute mass : Real = 0.9020827550760004;
                                attribute sigma_mass : Real = 0.28909372274994966;
                                attribute Cx : Real = -20.45930097810924;
                                attribute sigma_Cx : Real = 28.721044428837228;
                                attribute Cy : Real = 68.3692891150713;
                                attribute sigma_Cy : Real = 28.23690002309109;
                                attribute Cz : Real = -39.147092029452324;
                                attribute sigma_Cz : Real = 29.057750463592832;
                                attribute Ixx : Real = 1.046361233998187;
                                attribute sigma_Ixx : Real = 0.37074144170588635;
                                attribute Iyy : Real = 1.0315495523945122;
                                attribute sigma_Iyy : Real = 0.3723953238821935;
                                attribute Izz : Real = 0.9627952470400111;
                                attribute sigma_Izz : Real = 0.37017423652493897;
                                attribute Ixy : Real = 0.010770943595708456;
                                attribute sigma_Ixy : Real = 0.02351283871158888;
                                attribute Ixz : Real = 0.05680548400965103;
                                attribute sigma_Ixz : Real = 0.022566176940390956;
                                attribute Iyz : Real = 0.04825170812887449;
                                attribute sigma_Iyz : Real = 0.02209918015384651;
                            }
                            part <'C.1.1.4.2.1.1.3'> 'Part 531' {
                                attribute POIconv : String = "+";
                                attribute Ipoint : Boolean = false;
                                attribute mass : Real = 0.6377317892864812;
                                attribute sigma_mass : Real = 0.28909372274994966;
                                attribute Cx : Real = -38.39931106194854;
                                attribute sigma_Cx : Real = 28.721044428837228;
                                attribute Cy : Real = 91.98016212321818;
                                attribute sigma_Cy : Real = 28.23690002309109;
                                attribute Cz : Real = 57.15541415847838;
                                attribute sigma_Cz : Real = 29.057750463592832;
                                attribute Ixx : Real = 0.9075033494396808;
                                attribute sigma_Ixx : Real = 0.37074144170588635;
                                attribute Iyy : Real = 0.9017053980353069;
                                attribute sigma_Iyy : Real = 0.3723953238821935;
                                attribute Izz : Real = 0.8867787444231682;
                                attribute sigma_Izz : Real = 0.37017423652493897;
                                attribute Ixy : Real = 0.002319907716101171;
                                attribute sigma_Ixy : Real = 0.02351283871158888;
                                attribute Ixz : Real = 0.0016200842797732954;
                                attribute sigma_Ixz : Real = 0.022566176940390956;
                                attribute Iyz : Real = 0.003408526271620471;
                                attribute sigma_Iyz : Real = 0.02209918015384651;
                            }
                            part <'C.1.1.4.2.1.1.4'> 'Part 532' {
                                attribute POIconv : String = "+";
                                attribute Ipoint : Boolean = false;
                                attribute mass : Real = 0.462340191899566;
                                attribute sigma_mass : Real = 0.28909372274994966;
                                attribute Cx : Real = 22.843413753435016;
                                attribute sigma_Cx : Real = 28.721044428837228;
                                attribute Cy : Real = -74.99502301216125;
                                attribute sigma_Cy : Real = 28.23690002309109;
                                attribute Cz : Real = 63.385929726064205;
                                attribute sigma_Cz : Real = 29.057750463592832;
                                attribute Ixx : Real = 0.6094834430086261;
                                attribute sigma_Ixx : Real = 0.37074144170588635;
                                attribute Iyy : Real = 0.6522789903461221;
                                attribute sigma_Iyy : Real = 0.3723953238821935;
                                attribute Izz : Real = 0.6532951422963912;
                                attribute sigma_Izz : Real = 0.37017423652493897;
                                attribute Ixy : Real = -0.0006806878436304592;
                                attribute sigma_Ixy : Real = 0.02351283871158888;
                                attribute Ixz : Real = 0.016704705983983804;
                                attribute sigma_Ixz : Real = 0.022566176940390956;
                                attribute Iyz : Real = 0.02231075947651505;
                                attribute sigma_Iyz : Real = 0.02209918015384651;
                            }
                            part <'C.1.1.4.2.1.1.5'> 'Part 533' {
                                attribute POIconv : String = "+";
                                attribute Ipoint : Boolean = false;
                                attribute mass : Real = 0.1210092596008908;
                                attribute sigma_mass : Real = 0.28909372274994966;
                                attribute Cx : Real = -82.14233331382275;
                                attribute sigma_Cx : Real = 28.721044428837228;
                                attribute Cy : Real = -7.761460728943348;
                                attribute sigma_Cy : Real = 28.23690002309109;
                                attribute Cz : Real = -37.70593642257154;
                                attribute sigma_Cz : Real = 29.057750463592832;
                                attribute Ixx : Real = 0.14621557235676333;
                                attribute sigma_Ixx : Real = 0.37074144170588635;
                                attribute Iyy : Real = 0.15875580355933167;
                                attribute sigma_Iyy : Real = 0.3723953238821935;
                                attribute Izz : Real = 0.1598558902233007;
                                attribute sigma_Izz : Real = 0.37017423652493897;
                                attribute Ixy : Real = -0.0013767401604286532;
                                attribute sigma_Ixy : Real = 0.02351283871158888;
                                attribute Ixz : Real = -0.006732267851022406;
                                attribute sigma_Ixz : Real = 0.022566176940390956;
                                attribute Iyz : Real = 0.004230501478983469;
                                attribute sigma_Iyz : Real = 0.02209918015384651;
                            }
                        }
                        part <'C.1.1.4.2.1.2'> 'Subassembly 155' {
                            attribute POIconv : String = "-";
                            attribute Ipoint : Boolean = false;
                            attribute mass : Real = 2.776875978151569;
                            attribute sigma_mass : Real = 0.5781874454998993;
                            attribute Cx : Real = 17.37874337296569;
                            attribute sigma_Cx : Real = 15.12092324795614;
                            attribute Cy : Real = -45.299649530873864;
                            attribute sigma_Cy : Real = 15.445002964585212;
                            attribute Cz : Real = -6.9224991660185875;
                            attribute sigma_Cz : Real = 20.23555925046402;
                            attribute Ixx : Real = 13400.032825000548;
                            attribute sigma_Ixx : Real = 6679.473704219191;
                            attribute Iyy : Real = 12333.849866481414;
                            attribute sigma_Iyy : Real = 6428.750256667373;
                            attribute Izz : Real = 2345.7273219146778;
                            attribute sigma_Izz : Real = 2367.4755865005436;
                            attribute Ixy : Real = 127.58668973113609;
                            attribute sigma_Ixy : Real = 1186.3226236442754;
                            attribute Ixz : Real = 2286.777431986684;
                            attribute sigma_Ixz : Real = 2737.4674949835417;
                            attribute Iyz : Real = -434.49875345212786;
                            attribute sigma_Iyz : Real = 2881.466022432286;
                            part <'C.1.1.4.2.1.2.1'> 'Part 534' {
                                attribute POIconv : String = "+";
                                attribute Ipoint : Boolean = false;
                                attribute mass : Real = 0.4657461544717662;
                                attribute sigma_mass : Real = 0.28909372274994966;
                                attribute Cx : Real = 5.800252268090844;
                                attribute sigma_Cx : Real = 28.721044428837228;
                                attribute Cy : Real = -72.93368326500058;
                                attribute sigma_Cy : Real = 28.23690002309109;
                                attribute Cz : Real = -25.423532770946622;
                                attribute sigma_Cz : Real = 29.057750463592832;
                                attribute Ixx : Real = 0.5480583530158745;
                                attribute sigma_Ixx : Real = 0.37074144170588635;
                                attribute Iyy : Real = 0.5033229840496285;
                                attribute sigma_Iyy : Real = 0.3723953238821935;
                                attribute Izz : Real = 0.523754412413112;
                                attribute sigma_Izz : Real = 0.37017423652493897;
                                attribute Ixy : Real = -0.02342975070662707;
                                attribute sigma_Ixy : Real = 0.02351283871158888;
                                attribute Ixz : Real = -0.02320241428108455;
                                attribute sigma_Ixz : Real = 0.022566176940390956;
                                attribute Iyz : Real = 0.059725708379910356;
                                attribute sigma_Iyz : Real = 0.02209918015384651;
                            }
                            part <'C.1.1.4.2.1.2.2'> 'Part 535' {
                                attribute POIconv : String = "-";
                                attribute Ipoint : Boolean = false;
                                attribute mass : Real = 0.708368724582484;
                                attribute sigma_mass : Real = 0.28909372274994966;
                                attribute Cx : Real = -2.962869079783559;
                                attribute sigma_Cx : Real = 28.721044428837228;
                                attribute Cy : Real = -18.834841949865222;
                                attribute sigma_Cy : Real = 28.23690002309109;
                                attribute Cz : Real = 84.76543403230608;
                                attribute sigma_Cz : Real = 29.057750463592832;
                                attribute Ixx : Real = 0.9557488699156569;
                                attribute sigma_Ixx : Real = 0.37074144170588635;
                                attribute Iyy : Real = 0.9478724504228753;
                                attribute sigma_Iyy : Real = 0.3723953238821935;
                                attribute Izz : Real = 0.8907177825407292;
                                attribute sigma_Izz : Real = 0.37017423652493897;
                                attribute Ixy : Real = 0.0715800352531528;
                                attribute sigma_Ixy : Real = 0.02351283871158888;
                                attribute Ixz : Real = 0.07652906918950679;
                                attribute sigma_Ixz : Real = 0.022566176940390956;
                                attribute Iyz : Real = -0.011895995890804813;
                                attribute sigma_Iyz : Real = 0.02209918015384651;
                            }
                            part <'C.1.1.4.2.1.2.3'> 'Part 536' {
                                attribute POIconv : String = "+";
                                attribute Ipoint : Boolean = false;
                                attribute mass : Real = 0.6628257029645611;
                                attribute sigma_mass : Real = 0.28909372274994966;
                                attribute Cx : Real = 35.52412101998925;
                                attribute sigma_Cx : Real = 28.721044428837228;
                                attribute Cy : Real = -21.8517092987895;
                                attribute sigma_Cy : Real = 28.23690002309109;
                                attribute Cz : Real = -98.48964870907366;
                                attribute sigma_Cz : Real = 29.057750463592832;
                                attribute Ixx : Real = 0.9830451768702235;
                                attribute sigma_Ixx : Real = 0.37074144170588635;
                                attribute Iyy : Real = 0.9849088532831146;
                                attribute sigma_Iyy : Real = 0.3723953238821935;
                                attribute Izz : Real = 0.9842174754763611;
                                attribute sigma_Izz : Real = 0.37017423652493897;
                                attribute Ixy : Real = 0.003545144513851524;
                                attribute sigma_Ixy : Real = 0.02351283871158888;
                                attribute Ixz : Real = -0.0005210878980795506;
                                attribute sigma_Ixz : Real = 0.022566176940390956;
                                attribute Iyz : Real = -0.0015091910428400648;
                                attribute sigma_Iyz : Real = 0.02209918015384651;
                            }
                            part <'C.1.1.4.2.1.2.4'> 'Part 537' {
                                attribute POIconv : String = "+";
                                attribute Ipoint : Boolean = false;
                                attribute mass : Real = 0.9399353961327579;
                                attribute sigma_mass : Real = 0.28909372274994966;
                                attribute Cx : Real = 25.65035130828619;
                                attribute sigma_Cx : Real = 28.721044428837228;
                                attribute Cy : Real = -68.08663532137871;
                                attribute sigma_Cy : Real = 28.23690002309109;
                                attribute Cz : Real = -2.2828385699540377;
                                attribute sigma_Cz : Real = 29.057750463592832;
                                attribute Ixx : Real = 1.097678129085793;
                                attribute sigma_Ixx : Real = 0.37074144170588635;
                                attribute Iyy : Real = 1.1465270037558788;
                                attribute sigma_Iyy : Real = 0.3723953238821935;
                                attribute Izz : Real = 0.9542284492203658;
                                attribute sigma_Izz : Real = 0.37017423652493897;
                                attribute Ixy : Real = -0.02442688857373019;
                                attribute sigma_Ixy : Real = 0.02351283871158888;
                                attribute Ixz : Real = -0.055751840769548214;
                                attribute sigma_Ixz : Real = 0.022566176940390956;
                                attribute Iyz : Real = -0.046223090685541104;
                                attribute sigma_Iyz : Real = 0.02209918015384651;
                            }
                        }
                        part <'C.1.1.4.2.1.3'> 'Subassembly 156' {
                            attribute POIconv : String = "-";
                            attribute Ipoint : Boolean = false;
                            attribute mass : Real = 2.130981319835177;
                            attribute sigma_mass : Real = 0.6464332159373649;
                            attribute Cx : Real = 0.9303193157699206;
                            attribute sigma_Cx : Real = 22.958179987460255;
                            attribute Cy : Real = 17.433475942513105;
                            attribute sigma_Cy : Real = 20.21530567853172;
                            attribute Cz : Real = -1.9779331982533925;
                            attribute sigma_Cz : Real = 23.352005106095604;
                            attribute Ixx : Real = 13407.117227111441;
                            attribute sigma_Ixx : Real = 6584.452160008452;
                            attribute Iyy : Real = 19249.11408675341;
                            attribute sigma_Iyy : Real = 8461.236267363363;
                            attribute Izz : Real = 11361.306027293906;
                            attribute sigma_Izz : Real = 6255.075286921388;
                            attribute Ixy : Real = 2998.562352430605;
                            attribute sigma_Ixy : Real = 2905.887503932828;
                            attribute Ixz : Real = -8738.03442210185;
                            attribute sigma_Ixz : Real = 4102.590725241945;
                            attribute Iyz : Real = 3710.446634201728;
                            attribute sigma_Iyz : Real = 2867.15814242982;
                            part <'C.1.1.4.2.1.3.1'> 'Part 538' {
                                attribute POIconv : String = "-";
                                attribute Ipoint : Boolean = false;
                                attribute mass : Real = 0.7383363500193227;
                                attribute sigma_mass : Real = 0.28909372274994966;
                                attribute Cx : Real = -69.46453819982708;
                                attribute sigma_Cx : Real = 28.721044428837228;
                                attribute Cy : Real = 55.96396620385349;
                                attribute sigma_Cy : Real = 28.23690002309109;
                                attribute Cz : Real = -94.76968771778047;
                                attribute sigma_Cz : Real = 29.057750463592832;
                                attribute Ixx : Real = 0.7691287407056433;
                                attribute sigma_Ixx : Real = 0.37074144170588635;
                                attribute Iyy : Real = 0.7059330592358886;
                                attribute sigma_Iyy : Real = 0.3723953238821935;
                                attribute Izz : Real = 0.7518713933723802;
                                attribute sigma_Izz : Real = 0.37017423652493897;
                                attribute Ixy : Real = 0.002617184935424134;
                                attribute sigma_Ixy : Real = 0.02351283871158888;
                                attribute Ixz : Real = -0.012043657024025588;
                                attribute sigma_Ixz : Real = 0.022566176940390956;
                                attribute Iyz : Real = 0.017934178162199856;
                                attribute sigma_Iyz : Real = 0.02209918015384651;
                            }
                            part <'C.1.1.4.2.1.3.2'> 'Part 539' {
                                attribute POIconv : String = "-";
                                attribute Ipoint : Boolean = false;
                                attribute mass : Real = 0.3451222735252231;
                                attribute sigma_mass : Real = 0.28909372274994966;
                                attribute Cx : Real = 16.026701079681516;
                                attribute sigma_Cx : Real = 28.721044428837228;
                                attribute Cy : Real = 20.043739024549723;
                                attribute sigma_Cy : Real = 28.23690002309109;
                                attribute Cz : Real = 61.908615566790104;
                                attribute sigma_Cz : Real = 29.057750463592832;
                                attribute Ixx : Real = 0.375324994078699;
                                attribute sigma_Ixx : Real = 0.37074144170588635;
                                attribute Iyy : Real = 0.368040021751063;
                                attribute sigma_Iyy : Real = 0.3723953238821935;
                                attribute Izz : Real = 0.4115690276752031;
                                attribute sigma_Izz : Real = 0.37017423652493897;
                                attribute Ixy : Real = -0.0015055319594046539;
                                attribute sigma_Ixy : Real = 0.02351283871158888;
                                attribute Ixz : Real = -0.0026964433776489713;
                                attribute sigma_Ixz : Real = 0.022566176940390956;
                                attribute Iyz : Real = 0.008751069413777667;
                                attribute sigma_Iyz : Real = 0.02209918015384651;
                            }
                            part <'C.1.1.4.2.1.3.3'> 'Part 540' {
                                attribute POIconv : String = "+";
                                attribute Ipoint : Boolean = false;
                                attribute mass : Real = 0.052552033765474335;
                                attribute sigma_mass : Real = 0.28909372274994966;
                                attribute Cx : Real = -64.08582553267479;
                                attribute sigma_Cx : Real = 28.721044428837228;
                                attribute Cy : Real = 82.70698431879282;
                                attribute sigma_Cy : Real = 28.23690002309109;
                                attribute Cz : Real = -15.889395726844668;
                                attribute sigma_Cz : Real = 29.057750463592832;
                                attribute Ixx : Real = 0.06360908333705996;
                                attribute sigma_Ixx : Real = 0.37074144170588635;
                                attribute Iyy : Real = 0.06285384151786627;
                                attribute sigma_Iyy : Real = 0.3723953238821935;
                                attribute Izz : Real = 0.06517171056053056;
                                attribute sigma_Izz : Real = 0.37017423652493897;
                                attribute Ixy : Real = -0.0045690687115205455;
                                attribute sigma_Ixy : Real = 0.02351283871158888;
                                attribute Ixz : Real = -0.003387823044323876;
                                attribute sigma_Ixz : Real = 0.022566176940390956;
                                attribute Iyz : Real = 0.005779686744971064;
                                attribute sigma_Iyz : Real = 0.02209918015384651;
                            }
                            part <'C.1.1.4.2.1.3.4'> 'Part 541' {
                                attribute POIconv : String = "+";
                                attribute Ipoint : Boolean = false;
                                attribute mass : Real = 0.7164267662265338;
                                attribute sigma_mass : Real = 0.28909372274994966;
                                attribute Cx : Real = 80.08025335147977;
                                attribute sigma_Cx : Real = 28.721044428837228;
                                attribute Cy : Real = -3.715879423543811;
                                attribute sigma_Cy : Real = 28.23690002309109;
                                attribute Cz : Real = 61.16606825962663;
                                attribute sigma_Cz : Real = 29.057750463592832;
                                attribute Ixx : Real = 0.8430160260796978;
                                attribute sigma_Ixx : Real = 0.37074144170588635;
                                attribute Iyy : Real = 0.7708042621553833;
                                attribute sigma_Iyy : Real = 0.3723953238821935;
                                attribute Izz : Real = 0.7888681653646481;
                                attribute sigma_Izz : Real = 0.37017423652493897;
                                attribute Ixy : Real = -0.0748368805427142;
                                attribute sigma_Ixy : Real = 0.02351283871158888;
                                attribute Ixz : Real = -0.01976521840754839;
                                attribute sigma_Ixz : Real = 0.022566176940390956;
                                attribute Iyz : Real = 0.04886149207397042;
                                attribute sigma_Iyz : Real = 0.02209918015384651;
                            }
                            part <'C.1.1.4.2.1.3.5'> 'Part 542' {
                                attribute POIconv : String = "-";
                                attribute Ipoint : Boolean = false;
                                attribute mass : Real = 0.2785438962986227;
                                attribute sigma_mass : Real = 0.28909372274994966;
                                attribute Cx : Real = -22.489386424422264;
                                attribute sigma_Cx : Real = 28.721044428837228;
                                attribute Cy : Real = -45.85138885304332;
                                attribute sigma_Cy : Real = 28.23690002309109;
                                attribute Cz : Real = 5.043858662247658;
                                attribute sigma_Cz : Real = 29.057750463592832;
                                attribute Ixx : Real = 0.32740854031804395;
                                attribute sigma_Ixx : Real = 0.37074144170588635;
                                attribute Iyy : Real = 0.313891588789434;
                                attribute sigma_Iyy : Real = 0.3723953238821935;
                                attribute Izz : Real = 0.3250402143584981;
                                attribute sigma_Izz : Real = 0.37017423652493897;
                                attribute Ixy : Real = -0.009300320141077572;
                                attribute sigma_Ixy : Real = 0.02351283871158888;
                                attribute Ixz : Real = -0.014073114757763489;
                                attribute sigma_Ixz : Real = 0.022566176940390956;
                                attribute Iyz : Real = -0.008192898554829096;
                                attribute sigma_Iyz : Real = 0.02209918015384651;
                            }
                        }
                        part <'C.1.1.4.2.1.4'> 'Subassembly 157' {
                            attribute POIconv : String = "-";
                            attribute Ipoint : Boolean = false;
                            attribute mass : Real = 1.298924197284272;
                            attribute sigma_mass : Real = 0.5007250159521434;
                            attribute Cx : Real = -77.24151759489253;
                            attribute sigma_Cx : Real = 20.334508837510715;
                            attribute Cy : Real = 51.11300675984958;
                            attribute sigma_Cy : Real = 31.189716175084705;
                            attribute Cz : Real = -41.41353206786446;
                            attribute sigma_Cz : Real = 22.727573457253435;
                            attribute Ixx : Real = 4408.174244056164;
                            attribute sigma_Ixx : Real = 4931.1258724957925;
                            attribute Iyy : Real = 1616.9211887294919;
                            attribute sigma_Iyy : Real = 1874.91079523414;
                            attribute Izz : Real = 4216.078145644897;
                            attribute sigma_Izz : Real = 4280.3972078355055;
                            attribute Ixy : Real = 1195.3131713164112;
                            attribute sigma_Ixy : Real = 1398.1783984390456;
                            attribute Ixz : Real = 499.5373657265489;
                            attribute sigma_Ixz : Real = 845.8400471993326;
                            attribute Iyz : Real = -1748.2924537169615;
                            attribute sigma_Iyz : Real = 2144.032951672579;
                            part <'C.1.1.4.2.1.4.1'> 'Part 543' {
                                attribute POIconv : String = "+";
                                attribute Ipoint : Boolean = false;
                                attribute mass : Real = 0.6805268835944589;
                                attribute sigma_mass : Real = 0.28909372274994966;
                                attribute Cx : Real = -99.55102046951652;
                                attribute sigma_Cx : Real = 28.721044428837228;
                                attribute Cy : Real = 88.09943278320134;
                                attribute sigma_Cy : Real = 28.23690002309109;
                                attribute Cz : Real = -26.05195203796029;
                                attribute sigma_Cz : Real = 29.057750463592832;
                                attribute Ixx : Real = 0.8353861292482151;
                                attribute sigma_Ixx : Real = 0.37074144170588635;
                                attribute Iyy : Real = 0.8298846727665306;
                                attribute sigma_Iyy : Real = 0.3723953238821935;
                                attribute Izz : Real = 0.87564849004982;
                                attribute sigma_Izz : Real = 0.37017423652493897;
                                attribute Ixy : Real = 0.017574295771792432;
                                attribute sigma_Ixy : Real = 0.02351283871158888;
                                attribute Ixz : Real = -0.0007373827787249098;
                                attribute sigma_Ixz : Real = 0.022566176940390956;
                                attribute Iyz : Real = -0.0011680976378086743;
                                attribute sigma_Iyz : Real = 0.02209918015384651;
                            }
                            part <'C.1.1.4.2.1.4.2'> 'Part 544' {
                                attribute POIconv : String = "-";
                                attribute Ipoint : Boolean = false;
                                attribute mass : Real = 0.2165224535432644;
                                attribute sigma_mass : Real = 0.28909372274994966;
                                attribute Cx : Real = -51.99009836651385;
                                attribute sigma_Cx : Real = 28.721044428837228;
                                attribute Cy : Real = -57.73820839822292;
                                attribute sigma_Cy : Real = 28.23690002309109;
                                attribute Cz : Real = -99.54786384478211;
                                attribute sigma_Cz : Real = 29.057750463592832;
                                attribute Ixx : Real = 0.28376107568454423;
                                attribute sigma_Ixx : Real = 0.37074144170588635;
                                attribute Iyy : Real = 0.30767209346058827;
                                attribute sigma_Iyy : Real = 0.3723953238821935;
                                attribute Izz : Real = 0.2622591836229972;
                                attribute sigma_Izz : Real = 0.37017423652493897;
                                attribute Ixy : Real = -0.007219193944532361;
                                attribute sigma_Ixy : Real = 0.02351283871158888;
                                attribute Ixz : Real = 0.012428906731383332;
                                attribute sigma_Ixz : Real = 0.022566176940390956;
                                attribute Iyz : Real = -0.012101320503557035;
                                attribute sigma_Iyz : Real = 0.02209918015384651;
                            }
                            part <'C.1.1.4.2.1.4.3'> 'Part 545' {
                                attribute POIconv : String = "-";
                                attribute Ipoint : Boolean = false;
                                attribute mass : Real = 0.4018748601465486;
                                attribute sigma_mass : Real = 0.28909372274994966;
                                attribute Cx : Real = -53.06802932173014;
                                attribute sigma_Cx : Real = 28.721044428837228;
                                attribute Cy : Real = 47.127873031422496;
                                attribute sigma_Cy : Real = 28.23690002309109;
                                attribute Cz : Real = -36.10486467368901;
                                attribute sigma_Cz : Real = 29.057750463592832;
                                attribute Ixx : Real = 0.5553258955821561;
                                attribute sigma_Ixx : Real = 0.37074144170588635;
                                attribute Iyy : Real = 0.5007267768773431;
                                attribute sigma_Iyy : Real = 0.3723953238821935;
                                attribute Izz : Real = 0.506531662518624;
                                attribute sigma_Izz : Real = 0.37017423652493897;
                                attribute Ixy : Real = -0.05634551638548464;
                                attribute sigma_Ixy : Real = 0.02351283871158888;
                                attribute Ixz : Real = 0.024153508237850934;
                                attribute sigma_Ixz : Real = 0.022566176940390956;
                                attribute Iyz : Real = 0.02393250925198019;
                                attribute sigma_Iyz : Real = 0.02209918015384651;
                            }
                        }
                    }
                    part <'C.1.1.4.2.2'> 'Assembly 43' {
                        attribute POIconv : String = "-";
                        attribute Ipoint : Boolean = false;
                        attribute mass : Real = 3.694085677728755;
                        attribute sigma_mass : Real = 0.8176805270198123;
                        attribute Cx : Real = -58.141624703044975;
                        attribute sigma_Cx : Real = 13.540449890241248;
                        attribute Cy : Real = -18.789256914278134;
                        attribute sigma_Cy : Real = 14.17808965079476;
                        attribute Cz : Real = 27.560896085513043;
                        attribute sigma_Cz : Real = 18.08011261748741;
                        attribute Ixx : Real = 20656.296028670782;
                        attribute sigma_Ixx : Real = 8159.214799879371;
                        attribute Iyy : Real = 18535.65308019059;
                        attribute sigma_Iyy : Real = 7851.901832099162;
                        attribute Izz : Real = 7651.024982952108;
                        attribute sigma_Izz : Real = 4224.394066039429;
                        attribute Ixy : Real = 357.55090030643134;
                        attribute sigma_Ixy : Real = 1850.3114827117058;
                        attribute Ixz : Real = -3010.7717512425093;
                        attribute sigma_Ixz : Real = 3402.8146633562747;
                        attribute Iyz : Real = 1229.5186160937665;
                        attribute sigma_Iyz : Real = 3458.076395239755;
                        part <'C.1.1.4.2.2.1'> 'Subassembly 158' {
                            attribute POIconv : String = "-";
                            attribute Ipoint : Boolean = false;
                            attribute mass : Real = 1.5231474720067344;
                            attribute sigma_mass : Real = 0.5781874454998993;
                            attribute Cx : Real = -44.93612701366761;
                            attribute sigma_Cx : Real = 22.926073490123816;
                            attribute Cy : Real = -29.030677555784493;
                            attribute sigma_Cy : Real = 19.90416470045429;
                            attribute Cz : Real = 23.39767332194726;
                            attribute sigma_Cz : Real = 31.788617675819218;
                            attribute Ixx : Real = 8833.919611877274;
                            attribute sigma_Ixx : Real = 5697.806522201302;
                            attribute Iyy : Real = 10291.060638423329;
                            attribute sigma_Iyy : Real = 6108.393779370501;
                            attribute Izz : Real = 2658.186967354895;
                            attribute sigma_Izz : Real = 2369.865475463687;
                            attribute Ixy : Real = 511.83710714224935;
                            attribute sigma_Ixy : Real = 953.9310265802908;
                            attribute Ixz : Real = -2726.0640628086994;
                            attribute sigma_Ixz : Real = 2574.632896649602;
                            attribute Iyz : Real = 2043.4132216551998;
                            attribute sigma_Iyz : Real = 2255.8092884881194;
                            part <'C.1.1.4.2.2.1.1'> 'Part 546' {
                                attribute POIconv : String = "-";
                                attribute Ipoint : Boolean = false;
                                attribute mass : Real = 0.25636351422360165;
                                attribute sigma_mass : Real = 0.28909372274994966;
                                attribute Cx : Real = 16.567286243662238;
                                attribute sigma_Cx : Real = 28.721044428837228;
                                attribute Cy : Real = -25.547335715964437;
                                attribute sigma_Cy : Real = 28.23690002309109;
                                attribute Cz : Real = 29.57569658756256;
                                attribute sigma_Cz : Real = 29.057750463592832;
                                attribute Ixx : Real = 0.304352013479283;
                                attribute sigma_Ixx : Real = 0.37074144170588635;
                                attribute Iyy : Real = 0.2688870682151256;
                                attribute sigma_Iyy : Real = 0.3723953238821935;
                                attribute Izz : Real = 0.31801408114176444;
                                attribute sigma_Izz : Real = 0.37017423652493897;
                                attribute Ixy : Real = 0.04057703859762528;
                                attribute sigma_Ixy : Real = 0.02351283871158888;
                                attribute Ixz : Real = 0.004149136417418268;
                                attribute sigma_Ixz : Real = 0.022566176940390956;
                                attribute Iyz : Real = -0.010230417881111144;
                                attribute sigma_Iyz : Real = 0.02209918015384651;
                            }
                            part <'C.1.1.4.2.2.1.2'> 'Part 547' {
                                attribute POIconv : String = "+";
                                attribute Ipoint : Boolean = false;
                                attribute mass : Real = 0.4265429007196799;
                                attribute sigma_mass : Real = 0.28909372274994966;
                                attribute Cx : Real = -94.37498175539076;
                                attribute sigma_Cx : Real = 28.721044428837228;
                                attribute Cy : Real = -7.771098846569657;
                                attribute sigma_Cy : Real = 28.23690002309109;
                                attribute Cz : Real = -82.91450361721218;
                                attribute sigma_Cz : Real = 29.057750463592832;
                                attribute Ixx : Real = 0.5306955308005038;
                                attribute sigma_Ixx : Real = 0.37074144170588635;
                                attribute Iyy : Real = 0.5304025783148245;
                                attribute sigma_Iyy : Real = 0.3723953238821935;
                                attribute Izz : Real = 0.4667624810250703;
                                attribute sigma_Izz : Real = 0.37017423652493897;
                                attribute Ixy : Real = 0.026647985301828984;
                                attribute sigma_Ixy : Real = 0.02351283871158888;
                                attribute Ixz : Real = -0.05231512571603075;
                                attribute sigma_Ixz : Real = 0.022566176940390956;
                                attribute Iyz : Real = -0.03131181646354376;
                                attribute sigma_Iyz : Real = 0.02209918015384651;
                            }
                            part <'C.1.1.4.2.2.1.3'> 'Part 548' {
                                attribute POIconv : String = "-";
                                attribute Ipoint : Boolean = false;
                                attribute mass : Real = 0.07483926034369506;
                                attribute sigma_mass : Real = 0.28909372274994966;
                                attribute Cx : Real = -50.029705138877034;
                                attribute sigma_Cx : Real = 28.721044428837228;
                                attribute Cy : Real = 18.062815396115184;
                                attribute sigma_Cy : Real = 28.23690002309109;
                                attribute Cz : Real = -41.40526936389506;
                                attribute sigma_Cz : Real = 29.057750463592832;
                                attribute Ixx : Real = 0.09031389749193572;
                                attribute sigma_Ixx : Real = 0.37074144170588635;
                                attribute Iyy : Real = 0.10456432226114966;
                                attribute sigma_Iyy : Real = 0.3723953238821935;
                                attribute Izz : Real = 0.09110165943614627;
                                attribute sigma_Izz : Real = 0.37017423652493897;
                                attribute Ixy : Real = -0.010910682490777191;
                                attribute sigma_Ixy : Real = 0.02351283871158888;
                                attribute Ixz : Real = -0.006770658948247846;
                                attribute sigma_Ixz : Real = 0.022566176940390956;
                                attribute Iyz : Real = -3.697602270605658e-07;
                                attribute sigma_Iyz : Real = 0.02209918015384651;
                            }
                            part <'C.1.1.4.2.2.1.4'> 'Part 549' {
                                attribute POIconv : String = "+";
                                attribute Ipoint : Boolean = false;
                                attribute mass : Real = 0.7654017967197578;
                                attribute sigma_mass : Real = 0.28909372274994966;
                                attribute Cx : Real = -37.4867572914809;
                                attribute sigma_Cx : Real = 28.721044428837228;
                                attribute Cy : Real = -46.64961490780115;
                                attribute sigma_Cy : Real = 28.23690002309109;
                                attribute Cz : Real = 86.91031346097589;
                                attribute sigma_Cz : Real = 29.057750463592832;
                                attribute Ixx : Real = 1.025983105500719;
                                attribute sigma_Ixx : Real = 0.37074144170588635;
                                attribute Iyy : Real = 0.9522094112097353;
                                attribute sigma_Iyy : Real = 0.3723953238821935;
                                attribute Izz : Real = 1.1253164273782172;
                                attribute sigma_Izz : Real = 0.37017423652493897;
                                attribute Ixy : Real = -0.02816918943121456;
                                attribute sigma_Ixy : Real = 0.02351283871158888;
                                attribute Ixz : Real = -0.022442803188690328;
                                attribute sigma_Ixz : Real = 0.022566176940390956;
                                attribute Iyz : Real = 0.04084812667436109;
                                attribute sigma_Iyz : Real = 0.02209918015384651;
                            }
                        }
                        part <'C.1.1.4.2.2.2'> 'Subassembly 159' {
                            attribute POIconv : String = "-";
                            attribute Ipoint : Boolean = false;
                            attribute mass : Real = 2.170938205722021;
                            attribute sigma_mass : Real = 0.5781874454998993;
                            attribute Cx : Real = -67.40670667044088;
                            attribute sigma_Cx : Real = 15.927240619282573;
                            attribute Cy : Real = -11.603794924271865;
                            attribute sigma_Cy : Real = 19.388683806136097;
                            attribute Cz : Real = 30.481846212519134;
                            attribute sigma_Cz : Real = 21.147965888808944;
                            attribute Ixx : Real = 11505.608921593395;
                            attribute sigma_Ixx : Real = 5754.615642774952;
                            attribute Iyy : Real = 7747.698817795693;
                            attribute sigma_Iyy : Real = 4777.976299736824;
                            attribute Izz : Real = 4269.021242256114;
                            attribute sigma_Izz : Real = 3191.276250633651;
                            attribute Ixy : Real = -504.80913729248823;
                            attribute sigma_Ixy : Real = 1415.6547791680216;
                            attribute Ixz : Real = -427.1981782116377;
                            attribute sigma_Ixz : Real = 2080.3988866346513;
                            attribute Iyz : Real = -703.3872185961641;
                            attribute sigma_Iyz : Real = 2546.191883708664;
                            part <'C.1.1.4.2.2.2.1'> 'Part 550' {
                                attribute POIconv : String = "+";
                                attribute Ipoint : Boolean = false;
                                attribute mass : Real = 0.5870577115502674;
                                attribute sigma_mass : Real = 0.28909372274994966;
                                attribute Cx : Real = -67.26254322566092;
                                attribute sigma_Cx : Real = 28.721044428837228;
                                attribute Cy : Real = -38.265931187197566;
                                attribute sigma_Cy : Real = 28.23690002309109;
                                attribute Cz : Real = -50.29050302691758;
                                attribute sigma_Cz : Real = 29.057750463592832;
                                attribute Ixx : Real = 0.9474624115586364;
                                attribute sigma_Ixx : Real = 0.37074144170588635;
                                attribute Iyy : Real = 0.9292519126193977;
                                attribute sigma_Iyy : Real = 0.3723953238821935;
                                attribute Izz : Real = 0.9060865628793592;
                                attribute sigma_Izz : Real = 0.37017423652493897;
                                attribute Ixy : Real = 0.03298156795088358;
                                attribute sigma_Ixy : Real = 0.02351283871158888;
                                attribute Ixz : Real = 0.004370402340443938;
                                attribute sigma_Ixz : Real = 0.022566176940390956;
                                attribute Iyz : Real = -0.005939288031687957;
                                attribute sigma_Iyz : Real = 0.02209918015384651;
                            }
                            part <'C.1.1.4.2.2.2.2'> 'Part 551' {
                                attribute POIconv : String = "-";
                                attribute Ipoint : Boolean = false;
                                attribute mass : Real = 0.8029823325271718;
                                attribute sigma_mass : Real = 0.28909372274994966;
                                attribute Cx : Real = -62.90370328351855;
                                attribute sigma_Cx : Real = 28.721044428837228;
                                attribute Cy : Real = -28.55105842463672;
                                attribute sigma_Cy : Real = 28.23690002309109;
                                attribute Cz : Real = 96.41939611174166;
                                attribute sigma_Cz : Real = 29.057750463592832;
                                attribute Ixx : Real = 0.9374900921613957;
                                attribute sigma_Ixx : Real = 0.37074144170588635;
                                attribute Iyy : Real = 0.9804289116120805;
                                attribute sigma_Iyy : Real = 0.3723953238821935;
                                attribute Izz : Real = 0.9499191182170574;
                                attribute sigma_Izz : Real = 0.37017423652493897;
                                attribute Ixy : Real = -0.06876600890451912;
                                attribute sigma_Ixy : Real = 0.02351283871158888;
                                attribute Ixz : Real = 0.05487835049668996;
                                attribute sigma_Ixz : Real = 0.022566176940390956;
                                attribute Iyz : Real = -0.07923946599343144;
                                attribute sigma_Iyz : Real = 0.02209918015384651;
                            }
                            part <'C.1.1.4.2.2.2.3'> 'Part 552' {
                                attribute POIconv : String = "-";
                                attribute Ipoint : Boolean = false;
                                attribute mass : Real = 0.552696571841836;
                                attribute sigma_mass : Real = 0.28909372274994966;
                                attribute Cx : Real = -61.351537657901645;
                                attribute sigma_Cx : Real = 28.721044428837228;
                                attribute Cy : Real = 60.49366411752999;
                                attribute sigma_Cy : Real = 28.23690002309109;
                                attribute Cz : Real = 31.701836129650474;
                                attribute sigma_Cz : Real = 29.057750463592832;
                                attribute Ixx : Real = 0.68733282373598;
                                attribute sigma_Ixx : Real = 0.37074144170588635;
                                attribute Iyy : Real = 0.6772730218494515;
                                attribute sigma_Iyy : Real = 0.3723953238821935;
                                attribute Izz : Real = 0.6441308233078188;
                                attribute sigma_Izz : Real = 0.37017423652493897;
                                attribute Ixy : Real = -0.02291490719414696;
                                attribute sigma_Ixy : Real = 0.02351283871158888;
                                attribute Ixz : Real = -0.00406134666606856;
                                attribute sigma_Ixz : Real = 0.022566176940390956;
                                attribute Iyz : Real = 0.013507009809684462;
                                attribute sigma_Iyz : Real = 0.02209918015384651;
                            }
                            part <'C.1.1.4.2.2.2.4'> 'Part 553' {
                                attribute POIconv : String = "-";
                                attribute Ipoint : Boolean = false;
                                attribute mass : Real = 0.22820158980274574;
                                attribute sigma_mass : Real = 0.28909372274994966;
                                attribute Cx : Real = -98.28789196908474;
                                attribute sigma_Cx : Real = 28.721044428837228;
                                attribute Cy : Real = -57.99896940588951;
                                attribute sigma_Cy : Real = 28.23690002309109;
                                attribute Cz : Real = 3.299996303394437;
                                attribute sigma_Cz : Real = 29.057750463592832;
                                attribute Ixx : Real = 0.27265577626979587;
                                attribute sigma_Ixx : Real = 0.37074144170588635;
                                attribute Iyy : Real = 0.2583815740212346;
                                attribute sigma_Iyy : Real = 0.3723953238821935;
                                attribute Izz : Real = 0.2448786297821035;
                                attribute sigma_Izz : Real = 0.37017423652493897;
                                attribute Ixy : Real = 0.020159222194703827;
                                attribute sigma_Ixy : Real = 0.02351283871158888;
                                attribute Ixz : Real = -0.02437106528308207;
                                attribute sigma_Ixz : Real = 0.022566176940390956;
                                attribute Iyz : Real = 0.037826121537472016;
                                attribute sigma_Iyz : Real = 0.02209918015384651;
                            }
                        }
                    }
                    part <'C.1.1.4.2.3'> 'Assembly 44' {
                        attribute POIconv : String = "-";
                        attribute Ipoint : Boolean = false;
                        attribute mass : Real = 6.2428864654714715;
                        attribute sigma_mass : Real = 1.081689663197327;
                        attribute Cx : Real = 11.387429185951472;
                        attribute sigma_Cx : Real = 12.73600973973877;
                        attribute Cy : Real = -11.591251058779093;
                        attribute sigma_Cy : Real = 15.865531977777835;
                        attribute Cz : Real = -8.783248452170131;
                        attribute sigma_Cz : Real = 14.943589617734922;
                        attribute Ixx : Real = 32954.50976574415;
                        attribute sigma_Ixx : Real = 15803.475245737985;
                        attribute Iyy : Real = 26622.09283115464;
                        attribute sigma_Iyy : Real = 12291.659923161578;
                        attribute Izz : Real = 25710.235781210016;
                        attribute sigma_Izz : Real = 14875.188192554544;
                        attribute Ixy : Real = -2702.305410554612;
                        attribute sigma_Ixy : Real = 6564.65133361089;
                        attribute Ixz : Real = 288.40267840576143;
                        attribute sigma_Ixz : Real = 5542.883491000898;
                        attribute Iyz : Real = 7810.056378840933;
                        attribute sigma_Iyz : Real = 6722.065646069609;
                        part <'C.1.1.4.2.3.1'> 'Subassembly 160' {
                            attribute POIconv : String = "-";
                            attribute Ipoint : Boolean = false;
                            attribute mass : Real = 2.8056827578104566;
                            attribute sigma_mass : Real = 0.6464332159373649;
                            attribute Cx : Real = 16.023186381412376;
                            attribute sigma_Cx : Real = 16.653902418845348;
                            attribute Cy : Real = 25.624940465358343;
                            attribute sigma_Cy : Real = 16.12198315192817;
                            attribute Cz : Real = -33.8591977644566;
                            attribute sigma_Cz : Real = 20.451838604134863;
                            attribute Ixx : Real = 7217.544015990396;
                            attribute sigma_Ixx : Real = 6553.5796127356525;
                            attribute Iyy : Real = 5139.3993939355005;
                            attribute sigma_Iyy : Real = 7362.242922063029;
                            attribute Izz : Real = 5626.065775790281;
                            attribute sigma_Izz : Real = 4041.1776695113504;
                            attribute Ixy : Real = -672.6548853509155;
                            attribute sigma_Ixy : Real = 1829.6310276266054;
                            attribute Ixz : Real = -1186.2048846797888;
                            attribute sigma_Ixz : Real = 3239.009246737235;
                            attribute Iyz : Real = -238.74150424425767;
                            attribute sigma_Iyz : Real = 2091.951298622244;
                            part <'C.1.1.4.2.3.1.1'> 'Part 554' {
                                attribute POIconv : String = "+";
                                attribute Ipoint : Boolean = false;
                                attribute mass : Real = 0.6390874491217546;
                                attribute sigma_mass : Real = 0.28909372274994966;
                                attribute Cx : Real = 44.47537660598755;
                                attribute sigma_Cx : Real = 28.721044428837228;
                                attribute Cy : Real = 77.97959730960429;
                                attribute sigma_Cy : Real = 28.23690002309109;
                                attribute Cz : Real = -36.490082601085305;
                                attribute sigma_Cz : Real = 29.057750463592832;
                                attribute Ixx : Real = 0.5718513319100267;
                                attribute sigma_Ixx : Real = 0.37074144170588635;
                                attribute Iyy : Real = 0.593640463540544;
                                attribute sigma_Iyy : Real = 0.3723953238821935;
                                attribute Izz : Real = 0.595917365410761;
                                attribute sigma_Izz : Real = 0.37017423652493897;
                                attribute Ixy : Real = -0.024137199261449593;
                                attribute sigma_Ixy : Real = 0.02351283871158888;
                                attribute Ixz : Real = 0.01996523645553008;
                                attribute sigma_Ixz : Real = 0.022566176940390956;
                                attribute Iyz : Real = -0.011746420250287628;
                                attribute sigma_Iyz : Real = 0.02209918015384651;
                            }
                            part <'C.1.1.4.2.3.1.2'> 'Part 555' {
                                attribute POIconv : String = "+";
                                attribute Ipoint : Boolean = false;
                                attribute mass : Real = 0.6867221168074756;
                                attribute sigma_mass : Real = 0.28909372274994966;
                                attribute Cx : Real = -10.688582994043827;
                                attribute sigma_Cx : Real = 28.721044428837228;
                                attribute Cy : Real = 23.70650079101324;
                                attribute sigma_Cy : Real = 28.23690002309109;
                                attribute Cz : Real = -79.03767903335392;
                                attribute sigma_Cz : Real = 29.057750463592832;
                                attribute Ixx : Real = 0.9231429596934091;
                                attribute sigma_Ixx : Real = 0.37074144170588635;
                                attribute Iyy : Real = 0.9236895947026476;
                                attribute sigma_Iyy : Real = 0.3723953238821935;
                                attribute Izz : Real = 0.9285492114978481;
                                attribute sigma_Izz : Real = 0.37017423652493897;
                                attribute Ixy : Real = 0.005315808831326371;
                                attribute sigma_Ixy : Real = 0.02351283871158888;
                                attribute Ixz : Real = -0.021973862324148163;
                                attribute sigma_Ixz : Real = 0.022566176940390956;
                                attribute Iyz : Real = 0.013402329831122786;
                                attribute sigma_Iyz : Real = 0.02209918015384651;
                            }
                            part <'C.1.1.4.2.3.1.3'> 'Part 556' {
                                attribute POIconv : String = "+";
                                attribute Ipoint : Boolean = false;
                                attribute mass : Real = 0.7489517897311598;
                                attribute sigma_mass : Real = 0.28909372274994966;
                                attribute Cx : Real = -1.8283696379512548;
                                attribute sigma_Cx : Real = 28.721044428837228;
                                attribute Cy : Real = 28.59921739436686;
                                attribute sigma_Cy : Real = 28.23690002309109;
                                attribute Cz : Real = -5.588723905384541;
                                attribute sigma_Cz : Real = 29.057750463592832;
                                attribute Ixx : Real = 0.751780520643569;
                                attribute sigma_Ixx : Real = 0.37074144170588635;
                                attribute Iyy : Real = 0.7858954161948697;
                                attribute sigma_Iyy : Real = 0.3723953238821935;
                                attribute Izz : Real = 0.7520851906183658;
                                attribute sigma_Izz : Real = 0.37017423652493897;
                                attribute Ixy : Real = 0.013360890583591106;
                                attribute sigma_Ixy : Real = 0.02351283871158888;
                                attribute Ixz : Real = 0.03372653169667156;
                                attribute sigma_Ixz : Real = 0.022566176940390956;
                                attribute Iyz : Real = -0.026624408490709968;
                                attribute sigma_Iyz : Real = 0.02209918015384651;
                            }
                            part <'C.1.1.4.2.3.1.4'> 'Part 557' {
                                attribute POIconv : String = "-";
                                attribute Ipoint : Boolean = false;
                                attribute mass : Real = 0.6538818781422451;
                                attribute sigma_mass : Real = 0.28909372274994966;
                                attribute Cx : Real = 27.86654271185398;
                                attribute sigma_Cx : Real = 28.721044428837228;
                                attribute Cy : Real = -30.13402889482677;
                                attribute sigma_Cy : Real = 28.23690002309109;
                                attribute Cz : Real = -31.85533881187439;
                                attribute sigma_Cz : Real = 29.057750463592832;
                                attribute Ixx : Real = 0.7845183122916826;
                                attribute sigma_Ixx : Real = 0.37074144170588635;
                                attribute Iyy : Real = 0.8793151402722938;
                                attribute sigma_Iyy : Real = 0.3723953238821935;
                                attribute Izz : Real = 0.8231047052948112;
                                attribute sigma_Izz : Real = 0.37017423652493897;
                                attribute Ixy : Real = -0.05421460090447962;
                                attribute sigma_Ixy : Real = 0.02351283871158888;
                                attribute Ixz : Real = 0.03553407384820725;
                                attribute sigma_Ixz : Real = 0.022566176940390956;
                                attribute Iyz : Real = 0.03931396092729838;
                                attribute sigma_Iyz : Real = 0.02209918015384651;
                            }
                            part <'C.1.1.4.2.3.1.5'> 'Part 558' {
                                attribute POIconv : String = "-";
                                attribute Ipoint : Boolean = false;
                                attribute mass : Real = 0.07703952400782145;
                                attribute sigma_mass : Real = 0.28909372274994966;
                                attribute Cx : Real = 91.12650458700955;
                                attribute sigma_Cx : Real = 28.721044428837228;
                                attribute Cy : Real = 52.75932983495295;
                                attribute sigma_Cy : Real = 28.23690002309109;
                                attribute Cz : Real = 98.83786719292402;
                                attribute sigma_Cz : Real = 29.057750463592832;
                                attribute Ixx : Real = 0.09003545196587522;
                                attribute sigma_Ixx : Real = 0.37074144170588635;
                                attribute Iyy : Real = 0.09319265062849776;
                                attribute sigma_Iyy : Real = 0.3723953238821935;
                                attribute Izz : Real = 0.10503822958214182;
                                attribute sigma_Izz : Real = 0.37017423652493897;
                                attribute Ixy : Real = -0.002071234390311979;
                                attribute sigma_Ixy : Real = 0.02351283871158888;
                                attribute Ixz : Real = 0.005433185009588266;
                                attribute sigma_Ixz : Real = 0.022566176940390956;
                                attribute Iyz : Real = -0.005962003645871171;
                                attribute sigma_Iyz : Real = 0.02209918015384651;
                            }
                        }
                        part <'C.1.1.4.2.3.2'> 'Subassembly 161' {
                            attribute POIconv : String = "-";
                            attribute Ipoint : Boolean = false;
                            attribute mass : Real = 1.5327791157760657;
                            attribute sigma_mass : Real = 0.5781874454998993;
                            attribute Cx : Real = -10.280747542086655;
                            attribute sigma_Cx : Real = 34.13139862982351;
                            attribute Cy : Real = -56.39480310104474;
                            attribute sigma_Cy : Real = 41.08973872255616;
                            attribute Cz : Real = 52.60563567716931;
                            attribute sigma_Cz : Real = 21.52987746920077;
                            attribute Ixx : Real = 324.2870937524732;
                            attribute sigma_Ixx : Real = 7669.5056973811415;
                            attribute Iyy : Real = 5514.234906086864;
                            attribute sigma_Iyy : Real = 5323.427327039419;
                            attribute Izz : Real = 5820.2311082592805;
                            attribute sigma_Izz : Real = 11209.611821718276;
                            attribute Ixy : Real = 459.53363104863394;
                            attribute sigma_Ixy : Real = 5006.928094516998;
                            attribute Ixz : Real = -22.896448144677755;
                            attribute sigma_Ixz : Real = 2029.724438136477;
                            attribute Iyz : Real = -45.11935633684945;
                            attribute sigma_Iyz : Real = 1354.4595331046437;
                            part <'C.1.1.4.2.3.2.1'> 'Part 559' {
                                attribute POIconv : String = "+";
                                attribute Ipoint : Boolean = false;
                                attribute mass : Real = 0.8591342536716257;
                                attribute sigma_mass : Real = 0.28909372274994966;
                                attribute Cx : Real = 41.44640960730612;
                                attribute sigma_Cx : Real = 28.721044428837228;
                                attribute Cy : Real = -63.33728148601949;
                                attribute sigma_Cy : Real = 28.23690002309109;
                                attribute Cz : Real = 52.37458241172135;
                                attribute sigma_Cz : Real = 29.057750463592832;
                                attribute Ixx : Real = 1.0965468854936127;
                                attribute sigma_Ixx : Real = 0.37074144170588635;
                                attribute Iyy : Real = 1.0847419509756013;
                                attribute sigma_Iyy : Real = 0.3723953238821935;
                                attribute Izz : Real = 1.066529365277042;
                                attribute sigma_Izz : Real = 0.37017423652493897;
                                attribute Ixy : Real = -0.01188852046246876;
                                attribute sigma_Ixy : Real = 0.02351283871158888;
                                attribute Ixz : Real = 0.005844404768099375;
                                attribute sigma_Ixz : Real = 0.022566176940390956;
                                attribute Iyz : Real = 0.028539371019446154;
                                attribute sigma_Iyz : Real = 0.02209918015384651;
                            }
                            part <'C.1.1.4.2.3.2.2'> 'Part 560' {
                                attribute POIconv : String = "-";
                                attribute Ipoint : Boolean = false;
                                attribute mass : Real = 0.0049375325427390634;
                                attribute sigma_mass : Real = 0.28909372274994966;
                                attribute Cx : Real = 95.65344690345228;
                                attribute sigma_Cx : Real = 28.721044428837228;
                                attribute Cy : Real = 83.07131957262754;
                                attribute sigma_Cy : Real = 28.23690002309109;
                                attribute Cz : Real = 77.80659068375826;
                                attribute sigma_Cz : Real = 29.057750463592832;
                                attribute Ixx : Real = 0.00610876098741308;
                                attribute sigma_Ixx : Real = 0.37074144170588635;
                                attribute Iyy : Real = 0.005442463683858844;
                                attribute sigma_Iyy : Real = 0.3723953238821935;
                                attribute Izz : Real = 0.006308753217115438;
                                attribute sigma_Izz : Real = 0.37017423652493897;
                                attribute Ixy : Real = 0.0001403527327509397;
                                attribute sigma_Ixy : Real = 0.02351283871158888;
                                attribute Ixz : Real = 1.3260319660579889e-05;
                                attribute sigma_Ixz : Real = 0.022566176940390956;
                                attribute Iyz : Real = 8.883368461058734e-05;
                                attribute sigma_Iyz : Real = 0.02209918015384651;
                            }
                            part <'C.1.1.4.2.3.2.3'> 'Part 561' {
                                attribute POIconv : String = "-";
                                attribute Ipoint : Boolean = false;
                                attribute mass : Real = 0.009036969212582336;
                                attribute sigma_mass : Real = 0.28909372274994966;
                                attribute Cx : Real = 40.00760447233915;
                                attribute sigma_Cx : Real = 28.721044428837228;
                                attribute Cy : Real = 72.95060381293297;
                                attribute sigma_Cy : Real = 28.23690002309109;
                                attribute Cz : Real = 75.86175962351263;
                                attribute sigma_Cz : Real = 29.057750463592832;
                                attribute Ixx : Real = 0.01090247294954537;
                                attribute sigma_Ixx : Real = 0.37074144170588635;
                                attribute Iyy : Real = 0.012545484649135883;
                                attribute sigma_Iyy : Real = 0.3723953238821935;
                                attribute Izz : Real = 0.012485647303607668;
                                attribute sigma_Izz : Real = 0.37017423652493897;
                                attribute Ixy : Real = 8.836987982284184e-05;
                                attribute sigma_Ixy : Real = 0.02351283871158888;
                                attribute Ixz : Real = 7.419283863169482e-05;
                                attribute sigma_Ixz : Real = 0.022566176940390956;
                                attribute Iyz : Real = -1.7849561648082135e-06;
                                attribute sigma_Iyz : Real = 0.02209918015384651;
                            }
                            part <'C.1.1.4.2.3.2.4'> 'Part 562' {
                                attribute POIconv : String = "+";
                                attribute Ipoint : Boolean = false;
                                attribute mass : Real = 0.6596703603491187;
                                attribute sigma_mass : Real = 0.28909372274994966;
                                attribute Cx : Real = -79.13040807470679;
                                attribute sigma_Cx : Real = 28.721044428837228;
                                attribute Cy : Real = -50.16894810833037;
                                attribute sigma_Cy : Real = 28.23690002309109;
                                attribute Cz : Real = 52.39933622069657;
                                attribute sigma_Cz : Real = 29.057750463592832;
                                attribute Ixx : Real = 0.8684199615390704;
                                attribute sigma_Ixx : Real = 0.37074144170588635;
                                attribute Iyy : Real = 0.9679389923495302;
                                attribute sigma_Iyy : Real = 0.3723953238821935;
                                attribute Izz : Real = 0.8710903445486811;
                                attribute sigma_Izz : Real = 0.37017423652493897;
                                attribute Ixy : Real = 0.04275996013393244;
                                attribute sigma_Ixy : Real = 0.02351283871158888;
                                attribute Ixz : Real = 0.038811496128369524;
                                attribute sigma_Ixz : Real = 0.022566176940390956;
                                attribute Iyz : Real = 0.022350567648236255;
                                attribute sigma_Iyz : Real = 0.02209918015384651;
                            }
                        }
                        part <'C.1.1.4.2.3.3'> 'Subassembly 162' {
                            attribute POIconv : String = "-";
                            attribute Ipoint : Boolean = false;
                            attribute mass : Real = 1.9044245918849483;
                            attribute sigma_mass : Real = 0.6464332159373649;
                            attribute Cx : Real = 21.997492098960798;
                            attribute sigma_Cx : Real = 18.102718691962746;
                            attribute Cy : Real = -30.3595856728033;
                            attribute sigma_Cy : Real = 25.726922098585657;
                            attribute Cz : Real = -21.249187515443563;
                            attribute sigma_Cz : Real = 27.456058529598938;
                            attribute Ixx : Real = 9942.417753884507;
                            attribute sigma_Ixx : Real = 7877.712774354054;
                            attribute Iyy : Real = 7137.528022894845;
                            attribute sigma_Iyy : Real = 5483.7482025953295;
                            attribute Izz : Real = 5635.933762984687;
                            attribute sigma_Izz : Real = 4887.331096908763;
                            attribute Ixy : Real = -896.3280228923061;
                            attribute sigma_Ixy : Real = 1794.5605912557653;
                            attribute Ixz : Real = -1119.4130732945428;
                            attribute sigma_Ixz : Real = 1657.1836772972415;
                            attribute Iyz : Real = 1705.3176297234495;
                            attribute sigma_Iyz : Real = 3426.6069247801934;
                            part <'C.1.1.4.2.3.3.1'> 'Part 563' {
                                attribute POIconv : String = "-";
                                attribute Ipoint : Boolean = false;
                                attribute mass : Real = 0.6277585705115926;
                                attribute sigma_mass : Real = 0.28909372274994966;
                                attribute Cx : Real = 35.83303205668926;
                                attribute sigma_Cx : Real = 28.721044428837228;
                                attribute Cy : Real = -24.605528684332967;
                                attribute sigma_Cy : Real = 28.23690002309109;
                                attribute Cz : Real = 13.133471505716443;
                                attribute sigma_Cz : Real = 29.057750463592832;
                                attribute Ixx : Real = 0.6588166881277798;
                                attribute sigma_Ixx : Real = 0.37074144170588635;
                                attribute Iyy : Real = 0.68855310931017;
                                attribute sigma_Iyy : Real = 0.3723953238821935;
                                attribute Izz : Real = 0.747473104081539;
                                attribute sigma_Izz : Real = 0.37017423652493897;
                                attribute Ixy : Real = 0.005145008010603911;
                                attribute sigma_Ixy : Real = 0.02351283871158888;
                                attribute Ixz : Real = 0.009485129676954314;
                                attribute sigma_Ixz : Real = 0.022566176940390956;
                                attribute Iyz : Real = -0.05088716452832105;
                                attribute sigma_Iyz : Real = 0.02209918015384651;
                            }
                            part <'C.1.1.4.2.3.3.2'> 'Part 564' {
                                attribute POIconv : String = "+";
                                attribute Ipoint : Boolean = false;
                                attribute mass : Real = 0.6717972078570165;
                                attribute sigma_mass : Real = 0.28909372274994966;
                                attribute Cx : Real = -3.6818392109125853;
                                attribute sigma_Cx : Real = 28.721044428837228;
                                attribute Cy : Real = -66.98945756070316;
                                attribute sigma_Cy : Real = 28.23690002309109;
                                attribute Cz : Real = -63.15990178845823;
                                attribute sigma_Cz : Real = 29.057750463592832;
                                attribute Ixx : Real = 0.6848663668307794;
                                attribute sigma_Ixx : Real = 0.37074144170588635;
                                attribute Iyy : Real = 0.6865844209665427;
                                attribute sigma_Iyy : Real = 0.3723953238821935;
                                attribute Izz : Real = 0.615360991149833;
                                attribute sigma_Izz : Real = 0.37017423652493897;
                                attribute Ixy : Real = -0.005363122223356696;
                                attribute sigma_Ixy : Real = 0.02351283871158888;
                                attribute Ixz : Real = 0.007347015021025872;
                                attribute sigma_Ixz : Real = 0.022566176940390956;
                                attribute Iyz : Real = -0.03821034159040357;
                                attribute sigma_Iyz : Real = 0.02209918015384651;
                            }
                            part <'C.1.1.4.2.3.3.3'> 'Part 565' {
                                attribute POIconv : String = "-";
                                attribute Ipoint : Boolean = false;
                                attribute mass : Real = 0.2436396779124625;
                                attribute sigma_mass : Real = 0.28909372274994966;
                                attribute Cx : Real = 75.95817060209811;
                                attribute sigma_Cx : Real = 28.721044428837228;
                                attribute Cy : Real = 26.662041386589408;
                                attribute sigma_Cy : Real = 28.23690002309109;
                                attribute Cz : Real = -42.508628219366074;
                                attribute sigma_Cz : Real = 29.057750463592832;
                                attribute Ixx : Real = 0.3299325861738954;
                                attribute sigma_Ixx : Real = 0.37074144170588635;
                                attribute Iyy : Real = 0.3223920137726299;
                                attribute sigma_Iyy : Real = 0.3723953238821935;
                                attribute Izz : Real = 0.30894218608930507;
                                attribute sigma_Izz : Real = 0.37017423652493897;
                                attribute Ixy : Real = 0.0006379470038580912;
                                attribute sigma_Ixy : Real = 0.02351283871158888;
                                attribute Ixz : Real = -0.0010388216119853457;
                                attribute sigma_Ixz : Real = 0.022566176940390956;
                                attribute Iyz : Real = 0.001437451576463343;
                                attribute sigma_Iyz : Real = 0.02209918015384651;
                            }
                            part <'C.1.1.4.2.3.3.4'> 'Part 566' {
                                attribute POIconv : String = "-";
                                attribute Ipoint : Boolean = false;
                                attribute mass : Real = 0.19961190195451492;
                                attribute sigma_mass : Real = 0.28909372274994966;
                                attribute Cx : Real = 23.01814374513924;
                                attribute sigma_Cx : Real = 28.721044428837228;
                                attribute Cy : Real = -83.50895131006837;
                                attribute sigma_Cy : Real = 28.23690002309109;
                                attribute Cz : Real = 97.36863914877176;
                                attribute sigma_Cz : Real = 29.057750463592832;
                                attribute Ixx : Real = 0.2654232912503311;
                                attribute sigma_Ixx : Real = 0.37074144170588635;
                                attribute Iyy : Real = 0.27809692576339706;
                                attribute sigma_Iyy : Real = 0.3723953238821935;
                                attribute Izz : Real = 0.26425225296215754;
                                attribute sigma_Izz : Real = 0.37017423652493897;
                                attribute Ixy : Real = -0.00157327623618214;
                                attribute sigma_Ixy : Real = 0.02351283871158888;
                                attribute Ixz : Real = -0.013981965897234766;
                                attribute sigma_Ixz : Real = 0.022566176940390956;
                                attribute Iyz : Real = -0.010154826337579002;
                                attribute sigma_Iyz : Real = 0.02209918015384651;
                            }
                            part <'C.1.1.4.2.3.3.5'> 'Part 567' {
                                attribute POIconv : String = "-";
                                attribute Ipoint : Boolean = false;
                                attribute mass : Real = 0.16161723364936187;
                                attribute sigma_mass : Real = 0.28909372274994966;
                                attribute Cx : Real = -7.608089875429869;
                                attribute sigma_Cx : Real = 28.721044428837228;
                                attribute Cy : Real = 79.23393836244941;
                                attribute sigma_Cy : Real = 28.23690002309109;
                                attribute Cz : Real = -95.04326554015279;
                                attribute sigma_Cz : Real = 29.057750463592832;
                                attribute Ixx : Real = 0.18490934789817873;
                                attribute sigma_Ixx : Real = 0.37074144170588635;
                                attribute Iyy : Real = 0.17710767664219454;
                                attribute sigma_Iyy : Real = 0.3723953238821935;
                                attribute Izz : Real = 0.17571955929648203;
                                attribute sigma_Izz : Real = 0.37017423652493897;
                                attribute Ixy : Real = 0.004375307414183448;
                                attribute sigma_Ixy : Real = 0.02351283871158888;
                                attribute Ixz : Real = -0.0020381048765742565;
                                attribute sigma_Ixz : Real = 0.022566176940390956;
                                attribute Iyz : Real = 0.014013253837733686;
                                attribute sigma_Iyz : Real = 0.02209918015384651;
                            }
                        }
                    }
                }
                part <'C.1.1.4.3'> 'Subsystem 13' {
                    attribute POIconv : String = "-";
                    attribute Ipoint : Boolean = false;
                    attribute mass : Real = 28.661211896482158;
                    attribute sigma_mass : Real = 2.182609743038185;
                    attribute Cx : Real = -2.539935567465075;
                    attribute sigma_Cx : Real = 6.345161759253232;
                    attribute Cy : Real = 6.394255903478225;
                    attribute sigma_Cy : Real = 6.572644057440153;
                    attribute Cz : Real = 0.007562045256758512;
                    attribute sigma_Cz : Real = 6.488261208733657;
                    attribute Ixx : Real = 184245.87799056387;
                    attribute sigma_Ixx : Real = 28604.223975880635;
                    attribute Iyy : Real = 188970.1127349171;
                    attribute sigma_Iyy : Real = 27059.763548760468;
                    attribute Izz : Real = 190697.37335814006;
                    attribute sigma_Izz : Real = 28023.371590235067;
                    attribute Ixy : Real = -22506.307198311133;
                    attribute sigma_Ixy : Real = 13423.149764257487;
                    attribute Ixz : Real = -19880.92016843664;
                    attribute sigma_Ixz : Real = 13179.039639421408;
                    attribute Iyz : Real = -10909.315663533536;
                    attribute sigma_Iyz : Real = 13629.26227072128;
                    part <'C.1.1.4.3.1'> 'Assembly 45' {
                        attribute POIconv : String = "-";
                        attribute Ipoint : Boolean = false;
                        attribute mass : Real = 8.276784756872804;
                        attribute sigma_mass : Real = 1.0014500319042867;
                        attribute Cx : Real = 1.56163180389151;
                        attribute sigma_Cx : Real = 11.827720259395464;
                        attribute Cy : Real = 18.518446603736493;
                        attribute sigma_Cy : Real = 11.543790763524175;
                        attribute Cz : Real = -5.428710821870944;
                        attribute sigma_Cz : Real = 11.959265472484063;
                        attribute Ixx : Real = 58318.12742392662;
                        attribute sigma_Ixx : Real = 15382.277640984008;
                        attribute Iyy : Real = 65591.04539328055;
                        attribute sigma_Iyy : Real = 15979.009348951056;
                        attribute Izz : Real = 60830.67129926845;
                        attribute sigma_Izz : Real = 15116.304075668504;
                        attribute Ixy : Real = 1310.831932653301;
                        attribute sigma_Ixy : Real = 7457.148133493446;
                        attribute Ixz : Real = -21243.50078372054;
                        attribute sigma_Ixz : Real = 8054.670148790735;
                        attribute Iyz : Real = -2467.6712883877317;
                        attribute sigma_Iyz : Real = 7563.508033485237;
                        part <'C.1.1.4.3.1.1'> 'Subassembly 163' {
                            attribute POIconv : String = "-";
                            attribute Ipoint : Boolean = false;
                            attribute mass : Real = 2.0210982513511553;
                            attribute sigma_mass : Real = 0.5007250159521434;
                            attribute Cx : Real = -26.133202034445887;
                            attribute sigma_Cx : Real = 17.187156935021385;
                            attribute Cy : Real = 5.811015587411931;
                            attribute sigma_Cy : Real = 22.581119112489645;
                            attribute Cz : Real = 2.260971244198367;
                            attribute sigma_Cz : Real = 20.067116877670248;
                            attribute Ixx : Real = 11564.238645863234;
                            attribute sigma_Ixx : Real = 5982.836951480414;
                            attribute Iyy : Real = 3799.8874616438234;
                            attribute sigma_Iyy : Real = 3169.441667890077;
                            attribute Izz : Real = 8589.883524472147;
                            attribute sigma_Izz : Real = 4966.780539222374;
                            attribute Ixy : Real = 1655.0435716888865;
                            attribute sigma_Ixy : Real = 2309.6191168130104;
                            attribute Ixz : Real = 1153.7521819714284;
                            attribute sigma_Ixz : Real = 1469.5943906356208;
                            attribute Iyz : Real = -4154.356361727645;
                            attribute sigma_Iyz : Real = 2925.976648780144;
                            part <'C.1.1.4.3.1.1.1'> 'Part 568' {
                                attribute POIconv : String = "+";
                                attribute Ipoint : Boolean = false;
                                attribute mass : Real = 0.8065986763322726;
                                attribute sigma_mass : Real = 0.28909372274994966;
                                attribute Cx : Real = -10.833349404856563;
                                attribute sigma_Cx : Real = 28.721044428837228;
                                attribute Cy : Real = -72.0840894151479;
                                attribute sigma_Cy : Real = 28.23690002309109;
                                attribute Cz : Real = -35.41034609079361;
                                attribute sigma_Cz : Real = 29.057750463592832;
                                attribute Ixx : Real = 0.8727911528726691;
                                attribute sigma_Ixx : Real = 0.37074144170588635;
                                attribute Iyy : Real = 0.8798708728587485;
                                attribute sigma_Iyy : Real = 0.3723953238821935;
                                attribute Izz : Real = 0.7773476110004565;
                                attribute sigma_Izz : Real = 0.37017423652493897;
                                attribute Ixy : Real = -0.035036843269332915;
                                attribute sigma_Ixy : Real = 0.02351283871158888;
                                attribute Ixz : Real = -0.07660405653541293;
                                attribute sigma_Ixz : Real = 0.022566176940390956;
                                attribute Iyz : Real = 0.07264522211248191;
                                attribute sigma_Iyz : Real = 0.02209918015384651;
                            }
                            part <'C.1.1.4.3.1.1.2'> 'Part 569' {
                                attribute POIconv : String = "-";
                                attribute Ipoint : Boolean = false;
                                attribute mass : Real = 0.6751535173088777;
                                attribute sigma_mass : Real = 0.28909372274994966;
                                attribute Cx : Real = -28.28746736049652;
                                attribute sigma_Cx : Real = 28.721044428837228;
                                attribute Cy : Real = 53.00339697860181;
                                attribute sigma_Cy : Real = 28.23690002309109;
                                attribute Cz : Real = -3.930800361558795;
                                attribute sigma_Cz : Real = 29.057750463592832;
                                attribute Ixx : Real = 1.000326475243058;
                                attribute sigma_Ixx : Real = 0.37074144170588635;
                                attribute Iyy : Real = 0.826854712009798;
                                attribute sigma_Iyy : Real = 0.3723953238821935;
                                attribute Izz : Real = 0.9027142988374947;
                                attribute sigma_Izz : Real = 0.37017423652493897;
                                attribute Ixy : Real = 0.03131651596773279;
                                attribute sigma_Ixy : Real = 0.02351283871158888;
                                attribute Ixz : Real = 0.07934209751355806;
                                attribute sigma_Ixz : Real = 0.022566176940390956;
                                attribute Iyz : Real = 0.016300339201205466;
                                attribute sigma_Iyz : Real = 0.02209918015384651;
                            }
                            part <'C.1.1.4.3.1.1.3'> 'Part 570' {
                                attribute POIconv : String = "-";
                                attribute Ipoint : Boolean = false;
                                attribute mass : Real = 0.539346057710005;
                                attribute sigma_mass : Real = 0.28909372274994966;
                                attribute Cx : Real = -46.31761037744582;
                                attribute sigma_Cx : Real = 28.721044428837228;
                                attribute Cy : Real = 63.228671392425895;
                                attribute sigma_Cy : Real = 28.23690002309109;
                                attribute Cz : Real = 66.34975168853998;
                                attribute sigma_Cz : Real = 29.057750463592832;
                                attribute Ixx : Real = 0.6057957122756009;
                                attribute sigma_Ixx : Real = 0.37074144170588635;
                                attribute Iyy : Real = 0.6535129085354897;
                                attribute sigma_Iyy : Real = 0.3723953238821935;
                                attribute Izz : Real = 0.6079532882499885;
                                attribute sigma_Izz : Real = 0.37017423652493897;
                                attribute Ixy : Real = -0.0237810064960045;
                                attribute sigma_Ixy : Real = 0.02351283871158888;
                                attribute Ixz : Real = 0.011299809443557782;
                                attribute sigma_Ixz : Real = 0.022566176940390956;
                                attribute Iyz : Real = 0.00980316885851607;
                                attribute sigma_Iyz : Real = 0.02209918015384651;
                            }
                        }
                        part <'C.1.1.4.3.1.2'> 'Subassembly 164' {
                            attribute POIconv : String = "-";
                            attribute Ipoint : Boolean = false;
                            attribute mass : Real = 1.0364939973549916;
                            attribute sigma_mass : Real = 0.40884026350990615;
                            attribute Cx : Real = -50.70266550974705;
                            attribute sigma_Cx : Real = 29.95554774330097;
                            attribute Cy : Real = 80.05295779603406;
                            attribute sigma_Cy : Real = 35.27061724474805;
                            attribute Cz : Real = -65.5808951009564;
                            attribute sigma_Cz : Real = 33.90794058325806;
                            attribute Ixx : Real = 2909.0097139542218;
                            attribute sigma_Ixx : Real = 4577.392127424302;
                            attribute Iyy : Real = 2014.3222121401243;
                            attribute sigma_Iyy : Real = 3262.891419254988;
                            attribute Izz : Real = 2328.1062734987363;
                            attribute sigma_Izz : Real = 3715.743159282674;
                            attribute Ixy : Real = 1073.8100079160408;
                            attribute sigma_Ixy : Real = 1739.2565613855365;
                            attribute Ixz : Real = -963.5542037905361;
                            attribute sigma_Ixz : Real = 1573.4535754595051;
                            attribute Iyz : Real = 1445.3370269234517;
                            attribute sigma_Iyz : Real = 2277.911914787345;
                            part <'C.1.1.4.3.1.2.1'> 'Part 571' {
                                attribute POIconv : String = "+";
                                attribute Ipoint : Boolean = false;
                                attribute mass : Real = 0.8712604045490734;
                                attribute sigma_mass : Real = 0.28909372274994966;
                                attribute Cx : Real = -62.147762067615986;
                                attribute sigma_Cx : Real = 28.721044428837228;
                                attribute Cy : Real = 97.22028323449194;
                                attribute sigma_Cy : Real = 28.23690002309109;
                                attribute Cz : Real = -80.98488850519061;
                                attribute sigma_Cz : Real = 29.057750463592832;
                                attribute Ixx : Real = 1.2674694936894066;
                                attribute sigma_Ixx : Real = 0.37074144170588635;
                                attribute Iyy : Real = 1.3650474460137054;
                                attribute sigma_Iyy : Real = 0.3723953238821935;
                                attribute Izz : Real = 1.2578833584376354;
                                attribute sigma_Izz : Real = 0.37017423652493897;
                                attribute Ixy : Real = 0.03160772878268484;
                                attribute sigma_Ixy : Real = 0.02351283871158888;
                                attribute Ixz : Real = 0.00939403217593755;
                                attribute sigma_Ixz : Real = 0.022566176940390956;
                                attribute Iyz : Real = -0.041928482569012854;
                                attribute sigma_Iyz : Real = 0.02209918015384651;
                            }
                            part <'C.1.1.4.3.1.2.2'> 'Part 572' {
                                attribute POIconv : String = "-";
                                attribute Ipoint : Boolean = false;
                                attribute mass : Real = 0.16523359280591832;
                                attribute sigma_mass : Real = 0.28909372274994966;
                                attribute Cx : Real = 9.646197501569986;
                                attribute sigma_Cx : Real = 28.721044428837228;
                                attribute Cy : Real = -10.468652565032244;
                                attribute sigma_Cy : Real = 28.23690002309109;
                                attribute Cz : Real = 15.642839716747403;
                                attribute sigma_Cz : Real = 29.057750463592832;
                                attribute Ixx : Real = 0.18605388394751585;
                                attribute sigma_Ixx : Real = 0.37074144170588635;
                                attribute Iyy : Real = 0.2221832698722716;
                                attribute sigma_Iyy : Real = 0.3723953238821935;
                                attribute Izz : Real = 0.21734918475683057;
                                attribute sigma_Izz : Real = 0.37017423652493897;
                                attribute Ixy : Real = 0.004220553160068899;
                                attribute sigma_Ixy : Real = 0.02351283871158888;
                                attribute Ixz : Real = -0.006009814813861999;
                                attribute sigma_Ixz : Real = 0.022566176940390956;
                                attribute Iyz : Real = 0.013788005873994294;
                                attribute sigma_Iyz : Real = 0.02209918015384651;
                            }
                        }
                        part <'C.1.1.4.3.1.3'> 'Subassembly 165' {
                            attribute POIconv : String = "-";
                            attribute Ipoint : Boolean = false;
                            attribute mass : Real = 2.2310221408952495;
                            attribute sigma_mass : Real = 0.5007250159521434;
                            attribute Cx : Real = -51.6007389133617;
                            attribute sigma_Cx : Real = 19.99525804205821;
                            attribute Cy : Real = -13.175120612082852;
                            attribute sigma_Cy : Real = 18.4352428668882;
                            attribute Cz : Real = -44.13675708679854;
                            attribute sigma_Cz : Real = 19.748497823514942;
                            attribute Ixx : Real = 3242.48185214378;
                            attribute sigma_Ixx : Real = 3243.316583800097;
                            attribute Iyy : Real = 6656.206897022232;
                            attribute sigma_Iyy : Real = 4847.1189525523705;
                            attribute Izz : Real = 4115.579261994705;
                            attribute sigma_Izz : Real = 3643.75015094498;
                            attribute Ixy : Real = -226.92983531989415;
                            attribute sigma_Ixy : Real = 1751.313936637167;
                            attribute Ixz : Real = -3221.443282732951;
                            attribute sigma_Ixz : Real = 2424.5688795144665;
                            attribute Iyz : Real = -405.11257212393076;
                            attribute sigma_Iyz : Real = 1548.6149516890173;
                            part <'C.1.1.4.3.1.3.1'> 'Part 573' {
                                attribute POIconv : String = "-";
                                attribute Ipoint : Boolean = false;
                                attribute mass : Real = 0.9844077281497885;
                                attribute sigma_mass : Real = 0.28909372274994966;
                                attribute Cx : Real = -6.16714246571064;
                                attribute sigma_Cx : Real = 28.721044428837228;
                                attribute Cy : Real = -12.968294229358435;
                                attribute sigma_Cy : Real = 28.23690002309109;
                                attribute Cz : Real = -6.8360373843461275;
                                attribute sigma_Cz : Real = 29.057750463592832;
                                attribute Ixx : Real = 1.097402270270673;
                                attribute sigma_Ixx : Real = 0.37074144170588635;
                                attribute Iyy : Real = 1.0169660815939237;
                                attribute sigma_Iyy : Real = 0.3723953238821935;
                                attribute Izz : Real = 1.1060157730603195;
                                attribute sigma_Izz : Real = 0.37017423652493897;
                                attribute Ixy : Real = 0.05025355058673975;
                                attribute sigma_Ixy : Real = 0.02351283871158888;
                                attribute Ixz : Real = -0.010566011771067281;
                                attribute sigma_Ixz : Real = 0.022566176940390956;
                                attribute Iyz : Real = 0.11968075547228059;
                                attribute sigma_Iyz : Real = 0.02209918015384651;
                            }
                            part <'C.1.1.4.3.1.3.2'> 'Part 574' {
                                attribute POIconv : String = "-";
                                attribute Ipoint : Boolean = false;
                                attribute mass : Real = 0.983066041162936;
                                attribute sigma_mass : Real = 0.28909372274994966;
                                attribute Cx : Real = -92.69731459207833;
                                attribute sigma_Cx : Real = 28.721044428837228;
                                attribute Cy : Real = -22.00828343629837;
                                attribute sigma_Cy : Real = 28.23690002309109;
                                attribute Cz : Real = -83.30649198032916;
                                attribute sigma_Cz : Real = 29.057750463592832;
                                attribute Ixx : Real = 1.3075234008202243;
                                attribute sigma_Ixx : Real = 0.37074144170588635;
                                attribute Iyy : Real = 1.3908132550135497;
                                attribute sigma_Iyy : Real = 0.3723953238821935;
                                attribute Izz : Real = 1.1410880881993417;
                                attribute sigma_Izz : Real = 0.37017423652493897;
                                attribute Ixy : Real = -0.01382025968840965;
                                attribute sigma_Ixy : Real = 0.02351283871158888;
                                attribute Ixz : Real = 1.4040649634041584e-07;
                                attribute sigma_Ixz : Real = 0.022566176940390956;
                                attribute Iyz : Real = 0.0023475482338300895;
                                attribute sigma_Iyz : Real = 0.02209918015384651;
                            }
                            part <'C.1.1.4.3.1.3.3'> 'Part 575' {
                                attribute POIconv : String = "+";
                                attribute Ipoint : Boolean = false;
                                attribute mass : Real = 0.26354837158252487;
                                attribute sigma_mass : Real = 0.28909372274994966;
                                attribute Cx : Real = -68.0096261203289;
                                attribute sigma_Cx : Real = 28.721044428837228;
                                attribute Cy : Real = 19.001063471660018;
                                attribute sigma_Cy : Real = 28.23690002309109;
                                attribute Cz : Real = -37.3550059273839;
                                attribute sigma_Cz : Real = 29.057750463592832;
                                attribute Ixx : Real = 0.4203564976739275;
                                attribute sigma_Ixx : Real = 0.37074144170588635;
                                attribute Iyy : Real = 0.4265443008644212;
                                attribute sigma_Iyy : Real = 0.3723953238821935;
                                attribute Izz : Real = 0.41808562670064187;
                                attribute sigma_Izz : Real = 0.37017423652493897;
                                attribute Ixy : Real = -0.002530499115762736;
                                attribute sigma_Ixy : Real = 0.02351283871158888;
                                attribute Ixz : Real = -0.003561421436528379;
                                attribute sigma_Ixz : Real = 0.022566176940390956;
                                attribute Iyz : Real = -0.002622962972975264;
                                attribute sigma_Iyz : Real = 0.02209918015384651;
                            }
                        }
                        part <'C.1.1.4.3.1.4'> 'Subassembly 166' {
                            attribute POIconv : String = "-";
                            attribute Ipoint : Boolean = false;
                            attribute mass : Real = 1.4483643829736392;
                            attribute sigma_mass : Real = 0.40884026350990615;
                            attribute Cx : Real = 70.7388305817685;
                            attribute sigma_Cx : Real = 22.261375490977677;
                            attribute Cy : Real = 70.99451487270255;
                            attribute sigma_Cy : Real = 21.35236364746494;
                            attribute Cz : Real = 78.91288290471138;
                            attribute sigma_Cz : Real = 22.171245516280205;
                            attribute Ixx : Real = 186.82486315115895;
                            attribute sigma_Ixx : Real = 627.3168274838987;
                            attribute Iyy : Real = 516.765972675103;
                            attribute sigma_Iyy : Real = 1058.7743502073874;
                            attribute Izz : Real = 394.55099131764683;
                            attribute sigma_Izz : Real = 915.1004526297561;
                            attribute Ixy : Real = 106.66465921386964;
                            attribute sigma_Ixy : Real = 445.2934029382822;
                            attribute Ixz : Real = 235.73182931625192;
                            attribute sigma_Ixz : Real = 529.7540131199136;
                            attribute Iyz : Real = -69.524142019299;
                            attribute sigma_Iyz : Real = 306.6748544972811;
                            part <'C.1.1.4.3.1.4.1'> 'Part 576' {
                                attribute POIconv : String = "+";
                                attribute Ipoint : Boolean = false;
                                attribute mass : Real = 0.4552455420200713;
                                attribute sigma_mass : Real = 0.28909372274994966;
                                attribute Cx : Real = 47.41039630025625;
                                attribute sigma_Cx : Real = 28.721044428837228;
                                attribute Cy : Real = 77.8739676810801;
                                attribute sigma_Cy : Real = 28.23690002309109;
                                attribute Cz : Real = 94.13015800528228;
                                attribute sigma_Cz : Real = 29.057750463592832;
                                attribute Ixx : Real = 0.5744331515348395;
                                attribute sigma_Ixx : Real = 0.37074144170588635;
                                attribute Iyy : Real = 0.5559206481007796;
                                attribute sigma_Iyy : Real = 0.3723953238821935;
                                attribute Izz : Real = 0.5726534718639972;
                                attribute sigma_Izz : Real = 0.37017423652493897;
                                attribute Ixy : Real = -0.0018468662969857925;
                                attribute sigma_Ixy : Real = 0.02351283871158888;
                                attribute Ixz : Real = -0.013806764760521648;
                                attribute sigma_Ixz : Real = 0.022566176940390956;
                                attribute Iyz : Real = 0.008184652031829212;
                                attribute sigma_Iyz : Real = 0.02209918015384651;
                            }
                            part <'C.1.1.4.3.1.4.2'> 'Part 577' {
                                attribute POIconv : String = "+";
                                attribute Ipoint : Boolean = false;
                                attribute mass : Real = 0.993118840953568;
                                attribute sigma_mass : Real = 0.28909372274994966;
                                attribute Cx : Real = 81.43258169293404;
                                attribute sigma_Cx : Real = 28.721044428837228;
                                attribute Cy : Real = 67.84097463823855;
                                attribute sigma_Cy : Real = 28.23690002309109;
                                attribute Cz : Real = 71.9372860621661;
                                attribute sigma_Cz : Real = 29.057750463592832;
                                attribute Ixx : Real = 1.0854334812130173;
                                attribute sigma_Ixx : Real = 0.37074144170588635;
                                attribute Iyy : Real = 1.1455400213171718;
                                attribute sigma_Iyy : Real = 0.3723953238821935;
                                attribute Izz : Real = 1.2353600302111918;
                                attribute sigma_Izz : Real = 0.37017423652493897;
                                attribute Ixy : Real = -0.11076367568579323;
                                attribute sigma_Ixy : Real = 0.02351283871158888;
                                attribute Ixz : Real = -0.02604495772071208;
                                attribute sigma_Ixz : Real = 0.022566176940390956;
                                attribute Iyz : Real = 0.011428361884830074;
                                attribute sigma_Iyz : Real = 0.02209918015384651;
                            }
                        }
                        part <'C.1.1.4.3.1.5'> 'Subassembly 167' {
                            attribute POIconv : String = "-";
                            attribute Ipoint : Boolean = false;
                            attribute mass : Real = 1.5398059842977672;
                            attribute sigma_mass : Real = 0.40884026350990615;
                            attribute Cx : Real = 85.0515307285443;
                            attribute sigma_Cx : Real = 21.15095872299733;
                            attribute Cy : Real = -9.662118593468605;
                            attribute sigma_Cy : Real = 25.512448897455183;
                            attribute Cz : Real = 1.71954224323221;
                            attribute sigma_Cz : Real = 27.187142545623892;
                            attribute Ixx : Real = 11118.024789463128;
                            attribute sigma_Ixx : Real = 6196.137179046096;
                            attribute Iyy : Real = 6658.354211899099;
                            attribute sigma_Iyy : Real = 4550.554212789798;
                            attribute Izz : Real = 5347.968676675937;
                            attribute sigma_Izz : Real = 3912.6856164682076;
                            attribute Ixy : Real = 1474.097135504625;
                            attribute sigma_Ixy : Real = 1863.3445774537338;
                            attribute Ixz : Real = -1659.3736178934873;
                            attribute sigma_Ixz : Real = 2084.5149043478336;
                            attribute Iyz : Real = 5519.1413481553955;
                            attribute sigma_Iyz : Real = 3084.400685811512;
                            part <'C.1.1.4.3.1.5.1'> 'Part 578' {
                                attribute POIconv : String = "+";
                                attribute Ipoint : Boolean = false;
                                attribute mass : Real = 0.6317836605468765;
                                attribute sigma_mass : Real = 0.28909372274994966;
                                attribute Cx : Real = 64.71298728138208;
                                attribute sigma_Cx : Real = 28.721044428837228;
                                attribute Cy : Real = 57.985171442851424;
                                attribute sigma_Cy : Real = 28.23690002309109;
                                attribute Cz : Real = -74.4332299567759;
                                attribute sigma_Cz : Real = 29.057750463592832;
                                attribute Ixx : Real = 0.8302302590252909;
                                attribute sigma_Ixx : Real = 0.37074144170588635;
                                attribute Iyy : Real = 0.7929546916747786;
                                attribute sigma_Iyy : Real = 0.3723953238821935;
                                attribute Izz : Real = 0.7824910653845862;
                                attribute sigma_Izz : Real = 0.37017423652493897;
                                attribute Ixy : Real = -0.0262613785025231;
                                attribute sigma_Ixy : Real = 0.02351283871158888;
                                attribute Ixz : Real = 0.007174324060803509;
                                attribute sigma_Ixz : Real = 0.022566176940390956;
                                attribute Iyz : Real = 0.003659208346762329;
                                attribute sigma_Iyz : Real = 0.02209918015384651;
                            }
                            part <'C.1.1.4.3.1.5.2'> 'Part 579' {
                                attribute POIconv : String = "-";
                                attribute Ipoint : Boolean = false;
                                attribute mass : Real = 0.9080223237508908;
                                attribute sigma_mass : Real = 0.28909372274994966;
                                attribute Cx : Real = 99.20267998240888;
                                attribute sigma_Cx : Real = 28.721044428837228;
                                attribute Cy : Real = -56.72974172048271;
                                attribute sigma_Cy : Real = 28.23690002309109;
                                attribute Cz : Real = 54.70510870218277;
                                attribute sigma_Cz : Real = 29.057750463592832;
                                attribute Ixx : Real = 1.3429724114963764;
                                attribute sigma_Ixx : Real = 0.37074144170588635;
                                attribute Iyy : Real = 1.2701845229348838;
                                attribute sigma_Iyy : Real = 0.3723953238821935;
                                attribute Izz : Real = 1.2709593863106332;
                                attribute sigma_Izz : Real = 0.37017423652493897;
                                attribute Ixy : Real = 0.03478001377515316;
                                attribute sigma_Ixy : Real = 0.02351283871158888;
                                attribute Ixz : Real = 0.004313622161004088;
                                attribute sigma_Ixz : Real = 0.022566176940390956;
                                attribute Iyz : Real = -0.027748598271113045;
                                attribute sigma_Iyz : Real = 0.02209918015384651;
                            }
                        }
                    }
                    part <'C.1.1.4.3.2'> 'Assembly 46' {
                        attribute POIconv : String = "-";
                        attribute Ipoint : Boolean = false;
                        attribute mass : Real = 8.765205808654194;
                        attribute sigma_mass : Real = 1.2265207905297186;
                        attribute Cx : Real = -0.583325361916016;
                        attribute sigma_Cx : Real = 11.370479966874319;
                        attribute Cy : Real = -1.5098320420436293;
                        attribute sigma_Cy : Real = 11.31115623573156;
                        attribute Cz : Real = -3.137198350848337;
                        attribute sigma_Cz : Real = 11.028443948941792;
                        attribute Ixx : Real = 42936.56762025345;
                        attribute sigma_Ixx : Real = 14603.682406157068;
                        attribute Iyy : Real = 50811.976226490326;
                        attribute sigma_Iyy : Real = 13483.85111240548;
                        attribute Izz : Real = 48207.982181961575;
                        attribute sigma_Izz : Real = 14735.571373134737;
                        attribute Ixy : Real = -10300.542154349208;
                        attribute sigma_Ixy : Real = 7202.303041201963;
                        attribute Ixz : Real = -9524.32735125857;
                        attribute sigma_Ixz : Real = 6525.808695327052;
                        attribute Iyz : Real = -5156.702164946029;
                        attribute sigma_Iyz : Real = 6760.072807735215;
                        part <'C.1.1.4.3.2.1'> 'Subassembly 168' {
                            attribute POIconv : String = "-";
                            attribute Ipoint : Boolean = false;
                            attribute mass : Real = 0.91761245964095;
                            attribute sigma_mass : Real = 0.40884026350990615;
                            attribute Cx : Real = 86.18671541483974;
                            attribute sigma_Cx : Real = 23.738473725419787;
                            attribute Cy : Real = 64.6507769683107;
                            attribute sigma_Cy : Real = 51.11244437434329;
                            attribute Cz : Real = 84.23859475454796;
                            attribute sigma_Cz : Real = 27.05192346854376;
                            attribute Ixx : Real = 4788.506766537272;
                            attribute sigma_Ixx : Real = 6471.9586186632105;
                            attribute Iyy : Real = 337.7788095589379;
                            attribute sigma_Iyy : Real = 718.6436769795055;
                            attribute Izz : Real = 4454.7512393648985;
                            attribute sigma_Izz : Real = 6043.493838053948;
                            attribute Ixy : Real = 81.47863804508617;
                            attribute sigma_Ixy : Real = 1040.1261021127546;
                            attribute Ixz : Real = 22.303953849007993;
                            attribute sigma_Ixz : Real = 285.9736480675474;
                            attribute Iyz : Real = -1221.4667177743693;
                            attribute sigma_Iyz : Real = 1899.9776123400682;
                            part <'C.1.1.4.3.2.1.1'> 'Part 580' {
                                attribute POIconv : String = "-";
                                attribute Ipoint : Boolean = false;
                                attribute mass : Real = 0.7358381890321616;
                                attribute sigma_mass : Real = 0.28909372274994966;
                                attribute Cx : Real = 85.55333097465336;
                                attribute sigma_Cx : Real = 28.721044428837228;
                                attribute Cy : Real = 99.2712639272213;
                                attribute sigma_Cy : Real = 28.23690002309109;
                                attribute Cz : Real = 93.73734663240612;
                                attribute sigma_Cz : Real = 29.057750463592832;
                                attribute Ixx : Real = 0.9293189078969663;
                                attribute sigma_Ixx : Real = 0.37074144170588635;
                                attribute Iyy : Real = 0.8943825958847074;
                                attribute sigma_Iyy : Real = 0.3723953238821935;
                                attribute Izz : Real = 0.863344267161111;
                                attribute sigma_Izz : Real = 0.37017423652493897;
                                attribute Ixy : Real = 0.025021063246738313;
                                attribute sigma_Ixy : Real = 0.02351283871158888;
                                attribute Ixz : Real = -0.04068541962047893;
                                attribute sigma_Ixz : Real = 0.022566176940390956;
                                attribute Iyz : Real = 0.06691461668440601;
                                attribute sigma_Iyz : Real = 0.02209918015384651;
                            }
                            part <'C.1.1.4.3.2.1.2'> 'Part 581' {
                                attribute POIconv : String = "+";
                                attribute Ipoint : Boolean = false;
                                attribute mass : Real = 0.18177427060878837;
                                attribute sigma_mass : Real = 0.28909372274994966;
                                attribute Cx : Real = 88.75071117654443;
                                attribute sigma_Cx : Real = 28.721044428837228;
                                attribute Cy : Real = -75.4959904588759;
                                attribute sigma_Cy : Real = 28.23690002309109;
                                attribute Cz : Real = 45.786814112216234;
                                attribute sigma_Cz : Real = 29.057750463592832;
                                attribute Ixx : Real = 0.2159100735788343;
                                attribute sigma_Ixx : Real = 0.37074144170588635;
                                attribute Iyy : Real = 0.24185380993458014;
                                attribute sigma_Iyy : Real = 0.3723953238821935;
                                attribute Izz : Real = 0.18853456525796025;
                                attribute sigma_Izz : Real = 0.37017423652493897;
                                attribute Ixy : Real = -0.00011197166823510621;
                                attribute sigma_Ixy : Real = 0.02351283871158888;
                                attribute Ixz : Real = 0.0035915518035626428;
                                attribute sigma_Ixz : Real = 0.022566176940390956;
                                attribute Iyz : Real = -0.009848288424389305;
                                attribute sigma_Iyz : Real = 0.02209918015384651;
                            }
                        }
                        part <'C.1.1.4.3.2.2'> 'Subassembly 169' {
                            attribute POIconv : String = "-";
                            attribute Ipoint : Boolean = false;
                            attribute mass : Real = 3.344304431135999;
                            attribute sigma_mass : Real = 0.6464332159373649;
                            attribute Cx : Real = -18.360890786455357;
                            attribute sigma_Cx : Real = 17.052885102897196;
                            attribute Cy : Real = -29.401736303894324;
                            attribute sigma_Cy : Real = 16.37222629719751;
                            attribute Cz : Real = 4.212741655039006;
                            attribute sigma_Cz : Real = 15.299747152473827;
                            attribute Ixx : Real = 5959.441727337654;
                            attribute sigma_Ixx : Real = 4171.387243382803;
                            attribute Iyy : Real = 8718.396037125312;
                            attribute sigma_Iyy : Real = 5180.4017856929;
                            attribute Izz : Real = 10028.48990467135;
                            attribute sigma_Izz : Real = 6114.8158932064525;
                            attribute Ixy : Real = -3972.980358744278;
                            attribute sigma_Ixy : Real = 3018.199650359832;
                            attribute Ixz : Real = -3391.3068542751207;
                            attribute sigma_Ixz : Real = 2433.61180105844;
                            attribute Iyz : Real = -1710.8195226508572;
                            attribute sigma_Iyz : Real = 1817.1584757501735;
                            part <'C.1.1.4.3.2.2.1'> 'Part 582' {
                                attribute POIconv : String = "+";
                                attribute Ipoint : Boolean = false;
                                attribute mass : Real = 0.8669420333269517;
                                attribute sigma_mass : Real = 0.28909372274994966;
                                attribute Cx : Real = -72.9844493791461;
                                attribute sigma_Cx : Real = 28.721044428837228;
                                attribute Cy : Real = -54.542559292167425;
                                attribute sigma_Cy : Real = 28.23690002309109;
                                attribute Cz : Real = -37.68028072081506;
                                attribute sigma_Cz : Real = 29.057750463592832;
                                attribute Ixx : Real = 1.0705245710311226;
                                attribute sigma_Ixx : Real = 0.37074144170588635;
                                attribute Iyy : Real = 1.07576171874703;
                                attribute sigma_Iyy : Real = 0.3723953238821935;
                                attribute Izz : Real = 1.3660182309242799;
                                attribute sigma_Izz : Real = 0.37017423652493897;
                                attribute Ixy : Real = 0.0053437163424603085;
                                attribute sigma_Ixy : Real = 0.02351283871158888;
                                attribute Ixz : Real = -0.023459772690525932;
                                attribute sigma_Ixz : Real = 0.022566176940390956;
                                attribute Iyz : Real = 0.043790615525153134;
                                attribute sigma_Iyz : Real = 0.02209918015384651;
                            }
                            part <'C.1.1.4.3.2.2.2'> 'Part 583' {
                                attribute POIconv : String = "+";
                                attribute Ipoint : Boolean = false;
                                attribute mass : Real = 0.3446949692459311;
                                attribute sigma_mass : Real = 0.28909372274994966;
                                attribute Cx : Real = 62.88189422339201;
                                attribute sigma_Cx : Real = 28.721044428837228;
                                attribute Cy : Real = 56.431751465424895;
                                attribute sigma_Cy : Real = 28.23690002309109;
                                attribute Cz : Real = 25.264057470485568;
                                attribute sigma_Cz : Real = 29.057750463592832;
                                attribute Ixx : Real = 0.502299963161536;
                                attribute sigma_Ixx : Real = 0.37074144170588635;
                                attribute Iyy : Real = 0.5115285741510668;
                                attribute sigma_Iyy : Real = 0.3723953238821935;
                                attribute Izz : Real = 0.5015946308286685;
                                attribute sigma_Izz : Real = 0.37017423652493897;
                                attribute Ixy : Real = 0.002704509236806771;
                                attribute sigma_Ixy : Real = 0.02351283871158888;
                                attribute Ixz : Real = 0.0027625676506873014;
                                attribute sigma_Ixz : Real = 0.022566176940390956;
                                attribute Iyz : Real = -0.010183550308785271;
                                attribute sigma_Iyz : Real = 0.02209918015384651;
                            }
                            part <'C.1.1.4.3.2.2.3'> 'Part 584' {
                                attribute POIconv : String = "+";
                                attribute Ipoint : Boolean = false;
                                attribute mass : Real = 0.9991648010311183;
                                attribute sigma_mass : Real = 0.28909372274994966;
                                attribute Cx : Real = -36.093724658712745;
                                attribute sigma_Cx : Real = 28.721044428837228;
                                attribute Cy : Real = -42.64837778173387;
                                attribute sigma_Cy : Real = 28.23690002309109;
                                attribute Cz : Real = 6.684871204197407;
                                attribute sigma_Cz : Real = 29.057750463592832;
                                attribute Ixx : Real = 0.9764572606991789;
                                attribute sigma_Ixx : Real = 0.37074144170588635;
                                attribute Iyy : Real = 0.9168374543124701;
                                attribute sigma_Iyy : Real = 0.3723953238821935;
                                attribute Izz : Real = 0.9441844556800005;
                                attribute sigma_Izz : Real = 0.37017423652493897;
                                attribute Ixy : Real = -0.022605669214486538;
                                attribute sigma_Ixy : Real = 0.02351283871158888;
                                attribute Ixz : Real = -0.0014970573623820506;
                                attribute sigma_Ixz : Real = 0.022566176940390956;
                                attribute Iyz : Real = 0.000367879143992848;
                                attribute sigma_Iyz : Real = 0.02209918015384651;
                            }
                            part <'C.1.1.4.3.2.2.4'> 'Part 585' {
                                attribute POIconv : String = "-";
                                attribute Ipoint : Boolean = false;
                                attribute mass : Real = 0.22930727002304047;
                                attribute sigma_mass : Real = 0.28909372274994966;
                                attribute Cx : Real = 10.920222429558635;
                                attribute sigma_Cx : Real = 28.721044428837228;
                                attribute Cy : Real = 9.986065980046988;
                                attribute sigma_Cy : Real = 28.23690002309109;
                                attribute Cz : Real = 35.70701773278415;
                                attribute sigma_Cz : Real = 29.057750463592832;
                                attribute Ixx : Real = 0.35489902247098315;
                                attribute sigma_Ixx : Real = 0.37074144170588635;
                                attribute Iyy : Real = 0.3703487215093558;
                                attribute sigma_Iyy : Real = 0.3723953238821935;
                                attribute Izz : Real = 0.35977977300296343;
                                attribute sigma_Izz : Real = 0.37017423652493897;
                                attribute Ixy : Real = -0.0021077304500223383;
                                attribute sigma_Ixy : Real = 0.02351283871158888;
                                attribute Ixz : Real = -4.4862380427924946e-05;
                                attribute sigma_Ixz : Real = 0.022566176940390956;
                                attribute Iyz : Real = 7.855969687733738e-05;
                                attribute sigma_Iyz : Real = 0.02209918015384651;
                            }
                            part <'C.1.1.4.3.2.2.5'> 'Part 586' {
                                attribute POIconv : String = "-";
                                attribute Ipoint : Boolean = false;
                                attribute mass : Real = 0.9041953575089574;
                                attribute sigma_mass : Real = 0.28909372274994966;
                                attribute Cx : Real = 15.210539009422064;
                                attribute sigma_Cx : Real = 28.721044428837228;
                                attribute Cy : Real = -33.36887317709625;
                                attribute sigma_Cy : Real = 28.23690002309109;
                                attribute Cz : Real = 25.635775830596685;
                                attribute sigma_Cz : Real = 29.057750463592832;
                                attribute Ixx : Real = 0.9809673462533376;
                                attribute sigma_Ixx : Real = 0.37074144170588635;
                                attribute Iyy : Real = 1.0259054973620636;
                                attribute sigma_Iyy : Real = 0.3723953238821935;
                                attribute Izz : Real = 0.847084015046195;
                                attribute sigma_Izz : Real = 0.37017423652493897;
                                attribute Ixy : Real = -0.01267750919999319;
                                attribute sigma_Ixy : Real = 0.02351283871158888;
                                attribute Ixz : Real = 0.01695835079185267;
                                attribute sigma_Ixz : Real = 0.022566176940390956;
                                attribute Iyz : Real = 0.01902947869014241;
                                attribute sigma_Iyz : Real = 0.02209918015384651;
                            }
                        }
                        part <'C.1.1.4.3.2.3'> 'Subassembly 170' {
                            attribute POIconv : String = "-";
                            attribute Ipoint : Boolean = false;
                            attribute mass : Real = 2.016333829658106;
                            attribute sigma_mass : Real = 0.6464332159373649;
                            attribute Cx : Real = 20.701466824556853;
                            attribute sigma_Cx : Real = 19.102378860167917;
                            attribute Cy : Real = -0.786254005059274;
                            attribute sigma_Cy : Real = 18.58831216786932;
                            attribute Cz : Real = -19.383814955569576;
                            attribute sigma_Cz : Real = 23.28118877295886;
                            attribute Ixx : Real = 6479.306122541577;
                            attribute sigma_Ixx : Real = 4930.0027542403695;
                            attribute Iyy : Real = 8869.916713811432;
                            attribute sigma_Iyy : Real = 5295.662955860167;
                            attribute Izz : Real = 6362.199765197556;
                            attribute sigma_Izz : Real = 3902.944565004138;
                            attribute Ixy : Real = 838.9262775227452;
                            attribute sigma_Ixy : Real = 1748.6792707210054;
                            attribute Ixz : Real = 707.5483799211961;
                            attribute sigma_Ixz : Real = 2197.728679132118;
                            attribute Iyz : Real = -1030.3386698964591;
                            attribute sigma_Iyz : Real = 2106.034996743111;
                            part <'C.1.1.4.3.2.3.1'> 'Part 587' {
                                attribute POIconv : String = "+";
                                attribute Ipoint : Boolean = false;
                                attribute mass : Real = 0.10974312634416857;
                                attribute sigma_mass : Real = 0.28909372274994966;
                                attribute Cx : Real = 37.778127985075116;
                                attribute sigma_Cx : Real = 28.721044428837228;
                                attribute Cy : Real = 52.712550619617105;
                                attribute sigma_Cy : Real = 28.23690002309109;
                                attribute Cz : Real = 76.85025939717889;
                                attribute sigma_Cz : Real = 29.057750463592832;
                                attribute Ixx : Real = 0.14545869476211204;
                                attribute sigma_Ixx : Real = 0.37074144170588635;
                                attribute Iyy : Real = 0.14430438866334505;
                                attribute sigma_Iyy : Real = 0.3723953238821935;
                                attribute Izz : Real = 0.12410002010498686;
                                attribute sigma_Izz : Real = 0.37017423652493897;
                                attribute Ixy : Real = 0.005910819981491447;
                                attribute sigma_Ixy : Real = 0.02351283871158888;
                                attribute Ixz : Real = -0.003263841324965932;
                                attribute sigma_Ixz : Real = 0.022566176940390956;
                                attribute Iyz : Real = 0.014093329485940678;
                                attribute sigma_Iyz : Real = 0.02209918015384651;
                            }
                            part <'C.1.1.4.3.2.3.2'> 'Part 588' {
                                attribute POIconv : String = "-";
                                attribute Ipoint : Boolean = false;
                                attribute mass : Real = 0.45529639883409256;
                                attribute sigma_mass : Real = 0.28909372274994966;
                                attribute Cx : Real = -8.79065990447998;
                                attribute sigma_Cx : Real = 28.721044428837228;
                                attribute Cy : Real = -0.7168313954025507;
                                attribute sigma_Cy : Real = 28.23690002309109;
                                attribute Cz : Real = 49.17320990934968;
                                attribute sigma_Cz : Real = 29.057750463592832;
                                attribute Ixx : Real = 0.634628509404182;
                                attribute sigma_Ixx : Real = 0.37074144170588635;
                                attribute Iyy : Real = 0.6096522944332439;
                                attribute sigma_Iyy : Real = 0.3723953238821935;
                                attribute Izz : Real = 0.6198715692581757;
                                attribute sigma_Izz : Real = 0.37017423652493897;
                                attribute Ixy : Real = -0.015789449918281604;
                                attribute sigma_Ixy : Real = 0.02351283871158888;
                                attribute Ixz : Real = -0.01928378526527994;
                                attribute sigma_Ixz : Real = 0.022566176940390956;
                                attribute Iyz : Real = -0.004918880867733209;
                                attribute sigma_Iyz : Real = 0.02209918015384651;
                            }
                            part <'C.1.1.4.3.2.3.3'> 'Part 589' {
                                attribute POIconv : String = "+";
                                attribute Ipoint : Boolean = false;
                                attribute mass : Real = 0.28313015251536855;
                                attribute sigma_mass : Real = 0.28909372274994966;
                                attribute Cx : Real = 34.413322200998664;
                                attribute sigma_Cx : Real = 28.721044428837228;
                                attribute Cy : Real = 57.712893979623914;
                                attribute sigma_Cy : Real = 28.23690002309109;
                                attribute Cz : Real = -30.869585927575827;
                                attribute sigma_Cz : Real = 29.057750463592832;
                                attribute Ixx : Real = 0.3952854533412433;
                                attribute sigma_Ixx : Real = 0.37074144170588635;
                                attribute Iyy : Real = 0.36342049563386675;
                                attribute sigma_Iyy : Real = 0.3723953238821935;
                                attribute Izz : Real = 0.3540532777624591;
                                attribute sigma_Izz : Real = 0.37017423652493897;
                                attribute Ixy : Real = -0.0118354610617851;
                                attribute sigma_Ixy : Real = 0.02351283871158888;
                                attribute Ixz : Real = 0.03769667273417954;
                                attribute sigma_Ixz : Real = 0.022566176940390956;
                                attribute Iyz : Real = -0.010576398360564832;
                                attribute sigma_Iyz : Real = 0.02209918015384651;
                            }
                            part <'C.1.1.4.3.2.3.4'> 'Part 590' {
                                attribute POIconv : String = "-";
                                attribute Ipoint : Boolean = false;
                                attribute mass : Real = 0.641334931537509;
                                attribute sigma_mass : Real = 0.28909372274994966;
                                attribute Cx : Real = 79.2581157758832;
                                attribute sigma_Cx : Real = 28.721044428837228;
                                attribute Cy : Real = -33.784930128604174;
                                attribute sigma_Cy : Real = 28.23690002309109;
                                attribute Cz : Real = -47.89508325047791;
                                attribute sigma_Cz : Real = 29.057750463592832;
                                attribute Ixx : Real = 0.6793592097573864;
                                attribute sigma_Ixx : Real = 0.37074144170588635;
                                attribute Iyy : Real = 0.607680210556734;
                                attribute sigma_Iyy : Real = 0.3723953238821935;
                                attribute Izz : Real = 0.6978975407343123;
                                attribute sigma_Izz : Real = 0.37017423652493897;
                                attribute Ixy : Real = -0.0050337870014808325;
                                attribute sigma_Ixy : Real = 0.02351283871158888;
                                attribute Ixz : Real = 0.009546757024649747;
                                attribute sigma_Ixz : Real = 0.022566176940390956;
                                attribute Iyz : Real = 0.007302995440491721;
                                attribute sigma_Iyz : Real = 0.02209918015384651;
                            }
                            part <'C.1.1.4.3.2.3.5'> 'Part 591' {
                                attribute POIconv : String = "+";
                                attribute Ipoint : Boolean = false;
                                attribute mass : Real = 0.5268292204269673;
                                attribute sigma_mass : Real = 0.28909372274994966;
                                attribute Cx : Real = -36.02099670097232;
                                attribute sigma_Cx : Real = 28.721044428837228;
                                attribute Cy : Real = -3.2584079541265965;
                                attribute sigma_Cy : Real = 28.23690002309109;
                                attribute Cz : Real = -57.79769471846521;
                                attribute sigma_Cz : Real = 29.057750463592832;
                                attribute Ixx : Real = 0.5152005969782072;
                                attribute sigma_Ixx : Real = 0.37074144170588635;
                                attribute Iyy : Real = 0.5003554709795122;
                                attribute sigma_Iyy : Real = 0.3723953238821935;
                                attribute Izz : Real = 0.4651185688899954;
                                attribute sigma_Izz : Real = 0.37017423652493897;
                                attribute Ixy : Real = -0.00515238008314637;
                                attribute sigma_Ixy : Real = 0.02351283871158888;
                                attribute Ixz : Real = 0.011558711851901134;
                                attribute sigma_Ixz : Real = 0.022566176940390956;
                                attribute Iyz : Real = -0.014553249124662052;
                                attribute sigma_Iyz : Real = 0.02209918015384651;
                            }
                        }
                        part <'C.1.1.4.3.2.4'> 'Subassembly 171' {
                            attribute POIconv : String = "-";
                            attribute Ipoint : Boolean = false;
                            attribute mass : Real = 1.70062033262942;
                            attribute sigma_mass : Real = 0.5007250159521434;
                            attribute Cx : Real = -2.967387797346855;
                            attribute sigma_Cx : Real = 22.620771092072435;
                            attribute Cy : Real = 18.42209324638709;
                            attribute sigma_Cy : Real = 16.531415894259883;
                            attribute Cz : Real = -46.56622587060293;
                            attribute sigma_Cz : Real = 20.503769553212237;
                            attribute Ixx : Real = 2878.9821792141847;
                            attribute sigma_Ixx : Real = 2632.3423736358936;
                            attribute Iyy : Real = 6717.376639612778;
                            attribute sigma_Iyy : Real = 4175.049317123323;
                            attribute Izz : Real = 3882.3526795952876;
                            attribute sigma_Izz : Real = 3126.390170184858;
                            attribute Ixy : Real = -284.2993487659188;
                            attribute sigma_Ixy : Real = 1246.2845144813652;
                            attribute Ixz : Real = -1087.2271217361445;
                            attribute sigma_Ixz : Real = 1872.518021368204;
                            attribute Iyz : Real = -94.12431204973892;
                            attribute sigma_Iyz : Real = 1197.5172109752637;
                            part <'C.1.1.4.3.2.4.1'> 'Part 592' {
                                attribute POIconv : String = "-";
                                attribute Ipoint : Boolean = false;
                                attribute mass : Real = 0.6222756587970071;
                                attribute sigma_mass : Real = 0.28909372274994966;
                                attribute Cx : Real = -41.583311930298805;
                                attribute sigma_Cx : Real = 28.721044428837228;
                                attribute Cy : Real = 15.35527459345758;
                                attribute sigma_Cy : Real = 28.23690002309109;
                                attribute Cz : Real = -97.60544435121119;
                                attribute sigma_Cz : Real = 29.057750463592832;
                                attribute Ixx : Real = 0.7633877135686887;
                                attribute sigma_Ixx : Real = 0.37074144170588635;
                                attribute Iyy : Real = 0.7326336942129332;
                                attribute sigma_Iyy : Real = 0.3723953238821935;
                                attribute Izz : Real = 0.6974698235665074;
                                attribute sigma_Izz : Real = 0.37017423652493897;
                                attribute Ixy : Real = 0.020541241309192344;
                                attribute sigma_Ixy : Real = 0.02351283871158888;
                                attribute Ixz : Real = 0.02252378312326079;
                                attribute sigma_Ixz : Real = 0.022566176940390956;
                                attribute Iyz : Real = 0.06140045773560951;
                                attribute sigma_Iyz : Real = 0.02209918015384651;
                            }
                            part <'C.1.1.4.3.2.4.2'> 'Part 593' {
                                attribute POIconv : String = "+";
                                attribute Ipoint : Boolean = false;
                                attribute mass : Real = 0.6343683958356269;
                                attribute sigma_mass : Real = 0.28909372274994966;
                                attribute Cx : Real = -20.117552764713764;
                                attribute sigma_Cx : Real = 28.721044428837228;
                                attribute Cy : Real = 17.424153303727508;
                                attribute sigma_Cy : Real = 28.23690002309109;
                                attribute Cz : Real = -3.173608426004648;
                                attribute sigma_Cz : Real = 29.057750463592832;
                                attribute Ixx : Real = 0.7160316039069908;
                                attribute sigma_Ixx : Real = 0.37074144170588635;
                                attribute Iyy : Real = 0.8192711213122226;
                                attribute sigma_Iyy : Real = 0.3723953238821935;
                                attribute Izz : Real = 0.7582056512860335;
                                attribute sigma_Izz : Real = 0.37017423652493897;
                                attribute Ixy : Real = -0.09059207532236102;
                                attribute sigma_Ixy : Real = 0.02351283871158888;
                                attribute Ixz : Real = -0.006717858152166623;
                                attribute sigma_Ixz : Real = 0.022566176940390956;
                                attribute Iyz : Real = -0.022894753323617713;
                                attribute sigma_Iyz : Real = 0.02209918015384651;
                            }
                            part <'C.1.1.4.3.2.4.3'> 'Part 594' {
                                attribute POIconv : String = "+";
                                attribute Ipoint : Boolean = false;
                                attribute mass : Real = 0.44397627799678596;
                                attribute sigma_mass : Real = 0.28909372274994966;
                                attribute Cx : Real = 75.66130026243627;
                                attribute sigma_Cx : Real = 28.721044428837228;
                                attribute Cy : Real = 24.1464264690876;
                                attribute sigma_Cy : Real = 28.23690002309109;
                                attribute Cz : Real = -37.03067544847727;
                                attribute sigma_Cz : Real = 29.057750463592832;
                                attribute Ixx : Real = 0.6070584513632067;
                                attribute sigma_Ixx : Real = 0.37074144170588635;
                                attribute Iyy : Real = 0.5748620740549539;
                                attribute sigma_Iyy : Real = 0.3723953238821935;
                                attribute Izz : Real = 0.47742288035191494;
                                attribute sigma_Izz : Real = 0.37017423652493897;
                                attribute Ixy : Real = 0.026180467016522532;
                                attribute sigma_Ixy : Real = 0.02351283871158888;
                                attribute Ixz : Real = 0.008559906189002825;
                                attribute sigma_Ixz : Real = 0.022566176940390956;
                                attribute Iyz : Real = 0.04092632033875103;
                                attribute sigma_Iyz : Real = 0.02209918015384651;
                            }
                        }
                        part <'C.1.1.4.3.2.5'> 'Subassembly 172' {
                            attribute POIconv : String = "-";
                            attribute Ipoint : Boolean = false;
                            attribute mass : Real = 0.7863347555897198;
                            attribute sigma_mass : Real = 0.5007250159521434;
                            attribute Cx : Real = -75.65382273909584;
                            attribute sigma_Cx : Real = 20.043871954385722;
                            attribute Cy : Real = -5.053351412291178;
                            attribute sigma_Cy : Real = 45.4465384586286;
                            attribute Cz : Real = -0.7751807292125447;
                            attribute sigma_Cz : Real = 36.13642155326206;
                            attribute Ixx : Real = 4595.135385122493;
                            attribute sigma_Ixx : Real = 4115.367077938035;
                            attribute Iyy : Real = 1917.9102408797905;
                            attribute sigma_Iyy : Real = 1944.4333876651851;
                            attribute Izz : Real = 2855.0236152959055;
                            attribute sigma_Izz : Real = 3162.9016317539645;
                            attribute Ixy : Real = 121.8163932705347;
                            attribute sigma_Ixy : Real = 945.7484927188752;
                            attribute Ixz : Real = 83.73239794866583;
                            attribute sigma_Ixz : Real = 751.889586928663;
                            attribute Iyz : Real = 2016.635802655377;
                            attribute sigma_Iyz : Real = 1752.98540090512;
                            part <'C.1.1.4.3.2.5.1'> 'Part 595' {
                                attribute POIconv : String = "-";
                                attribute Ipoint : Boolean = false;
                                attribute mass : Real = 0.21141506774141453;
                                attribute sigma_mass : Real = 0.28909372274994966;
                                attribute Cx : Real = -61.93469692952931;
                                attribute sigma_Cx : Real = 28.721044428837228;
                                attribute Cy : Real = 34.88537222146988;
                                attribute sigma_Cy : Real = 28.23690002309109;
                                attribute Cz : Real = -62.02297578565776;
                                attribute sigma_Cz : Real = 29.057750463592832;
                                attribute Ixx : Real = 0.21155481802466644;
                                attribute sigma_Ixx : Real = 0.37074144170588635;
                                attribute Iyy : Real = 0.19162972423682545;
                                attribute sigma_Iyy : Real = 0.3723953238821935;
                                attribute Izz : Real = 0.20454667459509468;
                                attribute sigma_Izz : Real = 0.37017423652493897;
                                attribute Ixy : Real = -0.0045764944922120215;
                                attribute sigma_Ixy : Real = 0.02351283871158888;
                                attribute Ixz : Real = -0.0028316954538534387;
                                attribute sigma_Ixz : Real = 0.022566176940390956;
                                attribute Iyz : Real = -0.00448013427923099;
                                attribute sigma_Iyz : Real = 0.02209918015384651;
                            }
                            part <'C.1.1.4.3.2.5.2'> 'Part 596' {
                                attribute POIconv : String = "+";
                                attribute Ipoint : Boolean = false;
                                attribute mass : Real = 0.42681109623238445;
                                attribute sigma_mass : Real = 0.28909372274994966;
                                attribute Cx : Real = -76.16292117163539;
                                attribute sigma_Cx : Real = 28.721044428837228;
                                attribute Cy : Real = -57.035246631130576;
                                attribute sigma_Cy : Real = 28.23690002309109;
                                attribute Cz : Real = 42.93741104193032;
                                attribute sigma_Cz : Real = 29.057750463592832;
                                attribute Ixx : Real = 0.40125260414341757;
                                attribute sigma_Ixx : Real = 0.37074144170588635;
                                attribute Iyy : Real = 0.39643732441148505;
                                attribute sigma_Iyy : Real = 0.3723953238821935;
                                attribute Izz : Real = 0.41806574057907264;
                                attribute sigma_Izz : Real = 0.37017423652493897;
                                attribute Ixy : Real = 0.0032411073175351583;
                                attribute sigma_Ixy : Real = 0.02351283871158888;
                                attribute Ixz : Real = 0.00011461311960420589;
                                attribute sigma_Ixz : Real = 0.022566176940390956;
                                attribute Iyz : Real = 0.010257559606107608;
                                attribute sigma_Iyz : Real = 0.02209918015384651;
                            }
                            part <'C.1.1.4.3.2.5.3'> 'Part 597' {
                                attribute POIconv : String = "+";
                                attribute Ipoint : Boolean = false;
                                attribute mass : Real = 0.14810859161592088;
                                attribute sigma_mass : Real = 0.28909372274994966;
                                attribute Cx : Real = -93.7698619440198;
                                attribute sigma_Cx : Real = 28.721044428837228;
                                attribute Cy : Real = 87.73533538915217;
                                attribute sigma_Cy : Real = 28.23690002309109;
                                attribute Cz : Real = -39.31658072397113;
                                attribute sigma_Cz : Real = 29.057750463592832;
                                attribute Ixx : Real = 0.19107249053578962;
                                attribute sigma_Ixx : Real = 0.37074144170588635;
                                attribute Iyy : Real = 0.17954552893449496;
                                attribute sigma_Iyy : Real = 0.3723953238821935;
                                attribute Izz : Real = 0.19238040576723525;
                                attribute sigma_Izz : Real = 0.37017423652493897;
                                attribute Ixy : Real = 0.006368426861721866;
                                attribute sigma_Ixy : Real = 0.02351283871158888;
                                attribute Ixz : Real = -0.004160709909507991;
                                attribute sigma_Ixz : Real = 0.022566176940390956;
                                attribute Iyz : Real = -0.0016844437592338237;
                                attribute sigma_Iyz : Real = 0.02209918015384651;
                            }
                        }
                    }
                    part <'C.1.1.4.3.3'> 'Assembly 47' {
                        attribute POIconv : String = "-";
                        attribute Ipoint : Boolean = false;
                        attribute mass : Real = 4.265620759699959;
                        attribute sigma_mass : Real = 1.0014500319042867;
                        attribute Cx : Real = 5.373902397818913;
                        attribute sigma_Cx : Real = 15.85795583135652;
                        attribute Cy : Real = -19.44964582876801;
                        attribute sigma_Cy : Real = 19.468017417810618;
                        attribute Cz : Real = -5.405982795955818;
                        attribute sigma_Cz : Real = 18.5610716709911;
                        attribute Ixx : Real = 32880.986530616145;
                        attribute sigma_Ixx : Real = 12483.790649742929;
                        attribute Iyy : Real = 25556.55492309847;
                        attribute sigma_Iyy : Real = 10130.001507240846;
                        attribute Izz : Real = 27974.829835509645;
                        attribute sigma_Izz : Real = 10808.350407412643;
                        attribute Ixy : Real = 611.2347514399145;
                        attribute sigma_Ixy : Real = 4512.976161909211;
                        attribute Ixz : Real = 7788.311181096751;
                        attribute sigma_Ixz : Real = 4613.039655510543;
                        attribute Iyz : Real = -1038.02946328607;
                        attribute sigma_Iyz : Real = 5925.829251716997;
                        part <'C.1.1.4.3.3.1'> 'Subassembly 173' {
                            attribute POIconv : String = "-";
                            attribute Ipoint : Boolean = false;
                            attribute mass : Real = 1.977383007567143;
                            attribute sigma_mass : Real = 0.6464332159373649;
                            attribute Cx : Real = -2.8466266280718346;
                            attribute sigma_Cx : Real = 24.590873426437156;
                            attribute Cy : Real = 3.8035327374768375;
                            attribute sigma_Cy : Real = 24.680029171874388;
                            attribute Cz : Real = -29.954201236562408;
                            attribute sigma_Cz : Real = 20.96908761281244;
                            attribute Ixx : Real = 9950.017580757958;
                            attribute sigma_Ixx : Real = 5708.248118882421;
                            attribute Iyy : Real = 7406.184542996731;
                            attribute sigma_Iyy : Real = 5114.204319891691;
                            attribute Izz : Real = 12221.649930828211;
                            attribute sigma_Izz : Real = 6531.110307653972;
                            attribute Ixy : Real = 451.34890057958887;
                            attribute sigma_Ixy : Real = 2773.355822269381;
                            attribute Ixz : Real = 3115.1146004482403;
                            attribute sigma_Ixz : Real = 2357.3744881572334;
                            attribute Iyz : Real = -1272.964951121102;
                            attribute sigma_Iyz : Real = 2660.137517141739;
                            part <'C.1.1.4.3.3.1.1'> 'Part 598' {
                                attribute POIconv : String = "+";
                                attribute Ipoint : Boolean = false;
                                attribute mass : Real = 0.9364393398214598;
                                attribute sigma_mass : Real = 0.28909372274994966;
                                attribute Cx : Real = 18.053495464846492;
                                attribute sigma_Cx : Real = 28.721044428837228;
                                attribute Cy : Real = 60.10230388492346;
                                attribute sigma_Cy : Real = 28.23690002309109;
                                attribute Cz : Real = -36.785451881587505;
                                attribute sigma_Cz : Real = 29.057750463592832;
                                attribute Ixx : Real = 1.481118330393314;
                                attribute sigma_Ixx : Real = 0.37074144170588635;
                                attribute Iyy : Real = 1.4671997173191935;
                                attribute sigma_Iyy : Real = 0.3723953238821935;
                                attribute Izz : Real = 1.4529240368855632;
                                attribute sigma_Izz : Real = 0.37017423652493897;
                                attribute Ixy : Real = -0.0034257630175328103;
                                attribute sigma_Ixy : Real = 0.02351283871158888;
                                attribute Ixz : Real = -0.008811573143954504;
                                attribute sigma_Ixz : Real = 0.022566176940390956;
                                attribute Iyz : Real = 0.03667034175302378;
                                attribute sigma_Iyz : Real = 0.02209918015384651;
                            }
                            part <'C.1.1.4.3.3.1.2'> 'Part 599' {
                                attribute POIconv : String = "-";
                                attribute Ipoint : Boolean = false;
                                attribute mass : Real = 0.3504300986316521;
                                attribute sigma_mass : Real = 0.28909372274994966;
                                attribute Cx : Real = -95.96335315145552;
                                attribute sigma_Cx : Real = 28.721044428837228;
                                attribute Cy : Real = 4.882714664563537;
                                attribute sigma_Cy : Real = 28.23690002309109;
                                attribute Cz : Real = 24.19962123967707;
                                attribute sigma_Cz : Real = 29.057750463592832;
                                attribute Ixx : Real = 0.44827762874589333;
                                attribute sigma_Ixx : Real = 0.37074144170588635;
                                attribute Iyy : Real = 0.4459444848445588;
                                attribute sigma_Iyy : Real = 0.3723953238821935;
                                attribute Izz : Real = 0.4109705619947464;
                                attribute sigma_Izz : Real = 0.37017423652493897;
                                attribute Ixy : Real = -0.006202891125401592;
                                attribute sigma_Ixy : Real = 0.02351283871158888;
                                attribute Ixz : Real = 0.015748807480085586;
                                attribute sigma_Ixz : Real = 0.022566176940390956;
                                attribute Iyz : Real = 0.018059685242964262;
                                attribute sigma_Iyz : Real = 0.02209918015384651;
                            }
                            part <'C.1.1.4.3.3.1.3'> 'Part 600' {
                                attribute POIconv : String = "-";
                                attribute Ipoint : Boolean = false;
                                attribute mass : Real = 0.16554944202816113;
                                attribute sigma_mass : Real = 0.28909372274994966;
                                attribute Cx : Real = 7.517693750560284;
                                attribute sigma_Cx : Real = 28.721044428837228;
                                attribute Cy : Real = -48.106974409893155;
                                attribute sigma_Cy : Real = 28.23690002309109;
                                attribute Cz : Real = 3.316257568076253;
                                attribute sigma_Cz : Real = 29.057750463592832;
                                attribute Ixx : Real = 0.23140397240232954;
                                attribute sigma_Ixx : Real = 0.37074144170588635;
                                attribute Iyy : Real = 0.22305672091389891;
                                attribute sigma_Iyy : Real = 0.3723953238821935;
                                attribute Izz : Real = 0.21675261238427423;
                                attribute sigma_Izz : Real = 0.37017423652493897;
                                attribute Ixy : Real = 0.0002860452119445841;
                                attribute sigma_Ixy : Real = 0.02351283871158888;
                                attribute Ixz : Real = 0.015978375674585703;
                                attribute sigma_Ixz : Real = 0.022566176940390956;
                                attribute Iyz : Real = -8.768428067218783e-05;
                                attribute sigma_Iyz : Real = 0.02209918015384651;
                            }
                            part <'C.1.1.4.3.3.1.4'> 'Part 601' {
                                attribute POIconv : String = "+";
                                attribute Ipoint : Boolean = false;
                                attribute mass : Real = 0.10452514446899296;
                                attribute sigma_mass : Real = 0.28909372274994966;
                                attribute Cx : Real = -74.16816940531135;
                                attribute sigma_Cx : Real = 28.721044428837228;
                                attribute Cy : Real = -42.442279448732734;
                                attribute sigma_Cy : Real = 28.23690002309109;
                                attribute Cz : Real = 8.191929431632161;
                                attribute sigma_Cz : Real = 29.057750463592832;
                                attribute Ixx : Real = 0.11225229261476123;
                                attribute sigma_Ixx : Real = 0.37074144170588635;
                                attribute Iyy : Real = 0.11816795145459982;
                                attribute sigma_Iyy : Real = 0.3723953238821935;
                                attribute Izz : Real = 0.1288751704164729;
                                attribute sigma_Izz : Real = 0.37017423652493897;
                                attribute Ixy : Real = 0.010037411725029779;
                                attribute sigma_Ixy : Real = 0.02351283871158888;
                                attribute Ixz : Real = 0.0013012015741664033;
                                attribute sigma_Ixz : Real = 0.022566176940390956;
                                attribute Iyz : Real = 0.0007657993104434903;
                                attribute sigma_Iyz : Real = 0.02209918015384651;
                            }
                            part <'C.1.1.4.3.3.1.5'> 'Part 602' {
                                attribute POIconv : String = "+";
                                attribute Ipoint : Boolean = false;
                                attribute mass : Real = 0.4204389826168772;
                                attribute sigma_mass : Real = 0.28909372274994966;
                                attribute Cx : Real = 41.86448487453163;
                                attribute sigma_Cx : Real = 28.721044428837228;
                                attribute Cy : Real = -90.55250431410968;
                                attribute sigma_Cy : Real = 28.23690002309109;
                                attribute Cz : Real = -82.45935449376702;
                                attribute sigma_Cz : Real = 29.057750463592832;
                                attribute Ixx : Real = 0.6034603438235938;
                                attribute sigma_Ixx : Real = 0.37074144170588635;
                                attribute Iyy : Real = 0.6316481335124572;
                                attribute sigma_Iyy : Real = 0.3723953238821935;
                                attribute Izz : Real = 0.5895291890872871;
                                attribute sigma_Izz : Real = 0.37017423652493897;
                                attribute Ixy : Real = 0.034116664588859494;
                                attribute sigma_Ixy : Real = 0.02351283871158888;
                                attribute Ixz : Real = 0.00896616449497183;
                                attribute sigma_Ixz : Real = 0.022566176940390956;
                                attribute Iyz : Real = -0.006897048633327298;
                                attribute sigma_Iyz : Real = 0.02209918015384651;
                            }
                        }
                        part <'C.1.1.4.3.3.2'> 'Subassembly 174' {
                            attribute POIconv : String = "-";
                            attribute Ipoint : Boolean = false;
                            attribute mass : Real = 1.4300033007457387;
                            attribute sigma_mass : Real = 0.5781874454998993;
                            attribute Cx : Real = 8.050080131705005;
                            attribute sigma_Cx : Real = 28.63243689242288;
                            attribute Cy : Real = -76.68651574713266;
                            attribute sigma_Cy : Real = 31.654914445369876;
                            attribute Cz : Real = 21.03950640761238;
                            attribute sigma_Cz : Real = 32.51655432340126;
                            attribute Ixx : Real = 5767.996648624112;
                            attribute sigma_Ixx : Real = 6226.244879746819;
                            attribute Iyy : Real = 9154.386355289116;
                            attribute sigma_Iyy : Real = 6373.862870904845;
                            attribute Izz : Real = 5600.869936165235;
                            attribute sigma_Izz : Real = 5169.367691279494;
                            attribute Ixy : Real = -50.42770607193745;
                            attribute sigma_Ixy : Real = 1958.3951328039711;
                            attribute Ixz : Real = 4459.19651712347;
                            attribute sigma_Ixz : Real = 3069.511091718913;
                            attribute Iyz : Real = 485.67300824684065;
                            attribute sigma_Iyz : Real = 2708.4433268506127;
                            part <'C.1.1.4.3.3.2.1'> 'Part 603' {
                                attribute POIconv : String = "-";
                                attribute Ipoint : Boolean = false;
                                attribute mass : Real = 0.4595927965408191;
                                attribute sigma_mass : Real = 0.28909372274994966;
                                attribute Cx : Real = -72.91880464181304;
                                attribute sigma_Cx : Real = 28.721044428837228;
                                attribute Cy : Real = -75.09202337823808;
                                attribute sigma_Cy : Real = 28.23690002309109;
                                attribute Cz : Real = 99.56393404863775;
                                attribute sigma_Cz : Real = 29.057750463592832;
                                attribute Ixx : Real = 0.40720172849512176;
                                attribute sigma_Ixx : Real = 0.37074144170588635;
                                attribute Iyy : Real = 0.4332272757671695;
                                attribute sigma_Iyy : Real = 0.3723953238821935;
                                attribute Izz : Real = 0.42965699625104203;
                                attribute sigma_Izz : Real = 0.37017423652493897;
                                attribute Ixy : Real = 0.0011794358640240476;
                                attribute sigma_Ixy : Real = 0.02351283871158888;
                                attribute Ixz : Real = 0.0028523070260651597;
                                attribute sigma_Ixz : Real = 0.022566176940390956;
                                attribute Iyz : Real = 0.005890855245595964;
                                attribute sigma_Iyz : Real = 0.02209918015384651;
                            }
                            part <'C.1.1.4.3.3.2.2'> 'Part 604' {
                                attribute POIconv : String = "+";
                                attribute Ipoint : Boolean = false;
                                attribute mass : Real = 0.014043472690973433;
                                attribute sigma_mass : Real = 0.28909372274994966;
                                attribute Cx : Real = 11.09547521919012;
                                attribute sigma_Cx : Real = 28.721044428837228;
                                attribute Cy : Real = 16.28094487823546;
                                attribute sigma_Cy : Real = 28.23690002309109;
                                attribute Cz : Real = 44.031385984271765;
                                attribute sigma_Cz : Real = 29.057750463592832;
                                attribute Ixx : Real = 0.019047714683683412;
                                attribute sigma_Ixx : Real = 0.37074144170588635;
                                attribute Iyy : Real = 0.015894725091493134;
                                attribute sigma_Iyy : Real = 0.3723953238821935;
                                attribute Izz : Real = 0.017437816721696097;
                                attribute sigma_Izz : Real = 0.37017423652493897;
                                attribute Ixy : Real = 0.000228975362489425;
                                attribute sigma_Ixy : Real = 0.02351283871158888;
                                attribute Ixz : Real = 0.0007297890490088315;
                                attribute sigma_Ixz : Real = 0.022566176940390956;
                                attribute Iyz : Real = -0.0011976925159597565;
                                attribute sigma_Iyz : Real = 0.02209918015384651;
                            }
                            part <'C.1.1.4.3.3.2.3'> 'Part 605' {
                                attribute POIconv : String = "-";
                                attribute Ipoint : Boolean = false;
                                attribute mass : Real = 0.11925877195596694;
                                attribute sigma_mass : Real = 0.28909372274994966;
                                attribute Cx : Real = 62.93086241930723;
                                attribute sigma_Cx : Real = 28.721044428837228;
                                attribute Cy : Real = 5.970837594941258;
                                attribute sigma_Cy : Real = 28.23690002309109;
                                attribute Cz : Real = -73.37302137166262;
                                attribute sigma_Cz : Real = 29.057750463592832;
                                attribute Ixx : Real = 0.13997082890234597;
                                attribute sigma_Ixx : Real = 0.37074144170588635;
                                attribute Iyy : Real = 0.1386223523515246;
                                attribute sigma_Iyy : Real = 0.3723953238821935;
                                attribute Izz : Real = 0.15082960895798023;
                                attribute sigma_Izz : Real = 0.37017423652493897;
                                attribute Ixy : Real = -0.000883477722562124;
                                attribute sigma_Ixy : Real = 0.02351283871158888;
                                attribute Ixz : Real = 0.0015367364212254399;
                                attribute sigma_Ixz : Real = 0.022566176940390956;
                                attribute Iyz : Real = 0.0023001925390887783;
                                attribute sigma_Iyz : Real = 0.02209918015384651;
                            }
                            part <'C.1.1.4.3.3.2.4'> 'Part 606' {
                                attribute POIconv : String = "-";
                                attribute Ipoint : Boolean = false;
                                attribute mass : Real = 0.8371082595579792;
                                attribute sigma_mass : Real = 0.28909372274994966;
                                attribute Cx : Real = 44.634277233853936;
                                attribute sigma_Cx : Real = 28.721044428837228;
                                attribute Cy : Real = -90.89736305177212;
                                attribute sigma_Cy : Real = 28.23690002309109;
                                attribute Cz : Real = -9.007533174008131;
                                attribute sigma_Cz : Real = 29.057750463592832;
                                attribute Ixx : Real = 0.9139273821368273;
                                attribute sigma_Ixx : Real = 0.37074144170588635;
                                attribute Iyy : Real = 0.8979005741579907;
                                attribute sigma_Iyy : Real = 0.3723953238821935;
                                attribute Izz : Real = 1.0832077165705272;
                                attribute sigma_Izz : Real = 0.37017423652493897;
                                attribute Ixy : Real = 0.00019820324130290134;
                                attribute sigma_Ixy : Real = 0.02351283871158888;
                                attribute Ixz : Real = -0.05103977255612301;
                                attribute sigma_Ixz : Real = 0.022566176940390956;
                                attribute Iyz : Real = -0.016637835465993567;
                                attribute sigma_Iyz : Real = 0.02209918015384651;
                            }
                        }
                        part <'C.1.1.4.3.3.3'> 'Subassembly 175' {
                            attribute POIconv : String = "-";
                            attribute Ipoint : Boolean = false;
                            attribute mass : Real = 0.8582344513870777;
                            attribute sigma_mass : Real = 0.5007250159521434;
                            attribute Cx : Real = 19.855016965153105;
                            attribute sigma_Cx : Real = 24.76133621111787;
                            attribute Cy : Real = 22.343680785921354;
                            attribute sigma_Cy : Real = 30.968499252726044;
                            attribute Cz : Real = 7.08954583521399;
                            attribute sigma_Cz : Real = 50.28466768342773;
                            attribute Ixx : Real = 7584.245922945025;
                            attribute sigma_Ixx : Real = 5428.039075708636;
                            attribute Iyy : Real = 6346.445962101474;
                            attribute sigma_Iyy : Real = 4798.51528393436;
                            attribute Izz : Real = 2575.4387577030775;
                            attribute sigma_Izz : Real = 2172.752566140083;
                            attribute Ixy : Real = 132.7032387209755;
                            attribute sigma_Ixy : Real = 917.6019067480931;
                            attribute Ixz : Real = 869.5368550530197;
                            attribute sigma_Ixz : Real = 1756.1552717018935;
                            attribute Iyz : Real = -3095.8144242293274;
                            attribute sigma_Iyz : Real = 2342.7408001134518;
                            part <'C.1.1.4.3.3.3.1'> 'Part 607' {
                                attribute POIconv : String = "+";
                                attribute Ipoint : Boolean = false;
                                attribute mass : Real = 0.33409749166760594;
                                attribute sigma_mass : Real = 0.28909372274994966;
                                attribute Cx : Real = 30.620905896648765;
                                attribute sigma_Cx : Real = 28.721044428837228;
                                attribute Cy : Real = -35.56217709556222;
                                attribute sigma_Cy : Real = 28.23690002309109;
                                attribute Cz : Real = -93.64090203307569;
                                attribute sigma_Cz : Real = 29.057750463592832;
                                attribute Ixx : Real = 0.4521524801301306;
                                attribute sigma_Ixx : Real = 0.37074144170588635;
                                attribute Iyy : Real = 0.4018983274983767;
                                attribute sigma_Iyy : Real = 0.3723953238821935;
                                attribute Izz : Real = 0.38307454046030576;
                                attribute sigma_Izz : Real = 0.37017423652493897;
                                attribute Ixy : Real = 0.03010189475768419;
                                attribute sigma_Ixy : Real = 0.02351283871158888;
                                attribute Ixz : Real = 0.01041018927097695;
                                attribute sigma_Ixz : Real = 0.022566176940390956;
                                attribute Iyz : Real = -0.0016853135406593922;
                                attribute sigma_Iyz : Real = 0.02209918015384651;
                            }
                            part <'C.1.1.4.3.3.3.2'> 'Part 608' {
                                attribute POIconv : String = "+";
                                attribute Ipoint : Boolean = false;
                                attribute mass : Real = 0.31380860361410307;
                                attribute sigma_mass : Real = 0.28909372274994966;
                                attribute Cx : Real = 40.80463903956115;
                                attribute sigma_Cx : Real = 28.721044428837228;
                                attribute Cy : Real = 68.83005886338651;
                                attribute sigma_Cy : Real = 28.23690002309109;
                                attribute Cz : Real = 58.59446604736149;
                                attribute sigma_Cz : Real = 29.057750463592832;
                                attribute Ixx : Real = 0.5048631354760448;
                                attribute sigma_Ixx : Real = 0.37074144170588635;
                                attribute Iyy : Real = 0.46284647589605754;
                                attribute sigma_Iyy : Real = 0.3723953238821935;
                                attribute Izz : Real = 0.4600216874064529;
                                attribute sigma_Izz : Real = 0.37017423652493897;
                                attribute Ixy : Real = 0.012849075120804406;
                                attribute sigma_Ixy : Real = 0.02351283871158888;
                                attribute Ixz : Real = -0.016918620194096044;
                                attribute sigma_Ixz : Real = 0.022566176940390956;
                                attribute Iyz : Real = 0.0026309038496957473;
                                attribute sigma_Iyz : Real = 0.02209918015384651;
                            }
                            part <'C.1.1.4.3.3.3.3'> 'Part 609' {
                                attribute POIconv : String = "+";
                                attribute Ipoint : Boolean = false;
                                attribute mass : Real = 0.2103283561053686;
                                attribute sigma_mass : Real = 0.28909372274994966;
                                attribute Cx : Real = -28.502837987616658;
                                attribute sigma_Cx : Real = 28.721044428837228;
                                attribute Cy : Real = 44.96724219061434;
                                attribute sigma_Cy : Real = 28.23690002309109;
                                attribute Cz : Real = 90.25048143230379;
                                attribute sigma_Cz : Real = 29.057750463592832;
                                attribute Ixx : Real = 0.2481775524098801;
                                attribute sigma_Ixx : Real = 0.37074144170588635;
                                attribute Iyy : Real = 0.28662023955904664;
                                attribute sigma_Iyy : Real = 0.3723953238821935;
                                attribute Izz : Real = 0.25178410703081316;
                                attribute sigma_Izz : Real = 0.37017423652493897;
                                attribute Ixy : Real = 0.028321664779133962;
                                attribute sigma_Ixy : Real = 0.02351283871158888;
                                attribute Ixz : Real = 0.012647883362059291;
                                attribute sigma_Ixz : Real = 0.022566176940390956;
                                attribute Iyz : Real = 0.006076796732560149;
                                attribute sigma_Iyz : Real = 0.02209918015384651;
                            }
                        }
                    }
                    part <'C.1.1.4.3.4'> 'Assembly 48' {
                        attribute POIconv : String = "-";
                        attribute Ipoint : Boolean = false;
                        attribute mass : Real = 4.4987449944333635;
                        attribute sigma_mass : Real = 0.867281168249849;
                        attribute Cx : Real = -21.925901397351616;
                        attribute sigma_Cx : Real = 16.23070805102158;
                        attribute Cy : Real = -0.10226854708189143;
                        attribute sigma_Cy : Real = 15.517318214260031;
                        attribute Cz : Real = 4.802923201106842;
                        attribute sigma_Cz : Real = 16.43850431556174;
                        attribute Ixx : Real = 26613.011697484173;
                        attribute sigma_Ixx : Real = 9713.820103137781;
                        attribute Iyy : Real = 29927.700052174856;
                        attribute sigma_Iyy : Real = 10482.937017814953;
                        attribute Izz : Real = 30991.342867693038;
                        attribute sigma_Izz : Real = 10615.14719171856;
                        attribute Ixy : Real = -9775.850318333185;
                        attribute sigma_Ixy : Real = 5150.813918664508;
                        attribute Ixz : Real = 2251.3135508679698;
                        attribute sigma_Ixz : Real = 4961.758533606417;
                        attribute Iyz : Real = -2655.985143685195;
                        attribute sigma_Iyz : Real = 4364.268165054927;
                        part <'C.1.1.4.3.4.1'> 'Subassembly 176' {
                            attribute POIconv : String = "-";
                            attribute Ipoint : Boolean = false;
                            attribute mass : Real = 2.840313159725163;
                            attribute sigma_mass : Real = 0.6464332159373649;
                            attribute Cx : Real = -11.040324997087065;
                            attribute sigma_Cx : Real = 21.69520018897342;
                            attribute Cy : Real = 7.112965785590977;
                            attribute sigma_Cy : Real = 20.93141080038951;
                            attribute Cz : Real = 10.716846526583543;
                            attribute sigma_Cz : Real = 18.049931924902225;
                            attribute Ixx : Real = 18424.092706495478;
                            attribute sigma_Ixx : Real = 7819.109563110674;
                            attribute Iyy : Real = 20341.162543758397;
                            attribute sigma_Iyy : Real = 8329.060031997295;
                            attribute Izz : Real = 26312.979209283527;
                            attribute sigma_Izz : Real = 9991.90755459546;
                            attribute Ixy : Real = -8570.24837905096;
                            attribute sigma_Ixy : Real = 4893.911644782777;
                            attribute Ixz : Real = 1342.8281656672057;
                            attribute sigma_Ixz : Real = 4058.683980136577;
                            attribute Iyz : Real = -489.40203660359714;
                            attribute sigma_Iyz : Real = 3678.9393003873865;
                            part <'C.1.1.4.3.4.1.1'> 'Part 610' {
                                attribute POIconv : String = "+";
                                attribute Ipoint : Boolean = false;
                                attribute mass : Real = 0.2656773105228785;
                                attribute sigma_mass : Real = 0.28909372274994966;
                                attribute Cx : Real = -80.33401514403522;
                                attribute sigma_Cx : Real = 28.721044428837228;
                                attribute Cy : Real = 94.28526987321675;
                                attribute sigma_Cy : Real = 28.23690002309109;
                                attribute Cz : Real = -21.640755468979478;
                                attribute sigma_Cz : Real = 29.057750463592832;
                                attribute Ixx : Real = 0.3267084257802191;
                                attribute sigma_Ixx : Real = 0.37074144170588635;
                                attribute Iyy : Real = 0.33815512254078517;
                                attribute sigma_Iyy : Real = 0.3723953238821935;
                                attribute Izz : Real = 0.3326086121627109;
                                attribute sigma_Izz : Real = 0.37017423652493897;
                                attribute Ixy : Real = 0.003268070653877986;
                                attribute sigma_Ixy : Real = 0.02351283871158888;
                                attribute Ixz : Real = -1.62476016236583e-05;
                                attribute sigma_Ixz : Real = 0.022566176940390956;
                                attribute Iyz : Real = 0.0002142950688256802;
                                attribute sigma_Iyz : Real = 0.02209918015384651;
                            }
                            part <'C.1.1.4.3.4.1.2'> 'Part 611' {
                                attribute POIconv : String = "+";
                                attribute Ipoint : Boolean = false;
                                attribute mass : Real = 0.6373585346913897;
                                attribute sigma_mass : Real = 0.28909372274994966;
                                attribute Cx : Real = 60.95930193550885;
                                attribute sigma_Cx : Real = 28.721044428837228;
                                attribute Cy : Real = 86.72547196038067;
                                attribute sigma_Cy : Real = 28.23690002309109;
                                attribute Cz : Real = 70.9997967351228;
                                attribute sigma_Cz : Real = 29.057750463592832;
                                attribute Ixx : Real = 0.601692236666902;
                                attribute sigma_Ixx : Real = 0.37074144170588635;
                                attribute Iyy : Real = 0.8008996587609389;
                                attribute sigma_Iyy : Real = 0.3723953238821935;
                                attribute Izz : Real = 0.7537394135934217;
                                attribute sigma_Izz : Real = 0.37017423652493897;
                                attribute Ixy : Real = 0.027813013919976932;
                                attribute sigma_Ixy : Real = 0.02351283871158888;
                                attribute Ixz : Real = 0.02472736154060891;
                                attribute sigma_Ixz : Real = 0.022566176940390956;
                                attribute Iyz : Real = 0.007003289602096967;
                                attribute sigma_Iyz : Real = 0.02209918015384651;
                            }
                            part <'C.1.1.4.3.4.1.3'> 'Part 612' {
                                attribute POIconv : String = "-";
                                attribute Ipoint : Boolean = false;
                                attribute mass : Real = 0.26737424880149774;
                                attribute sigma_mass : Real = 0.28909372274994966;
                                attribute Cx : Real = -88.10887238942087;
                                attribute sigma_Cx : Real = 28.721044428837228;
                                attribute Cy : Real = -57.8130520414561;
                                attribute sigma_Cy : Real = 28.23690002309109;
                                attribute Cz : Real = 59.29036121815443;
                                attribute sigma_Cz : Real = 29.057750463592832;
                                attribute Ixx : Real = 0.35475491658125613;
                                attribute sigma_Ixx : Real = 0.37074144170588635;
                                attribute Iyy : Real = 0.35650217239533155;
                                attribute sigma_Iyy : Real = 0.3723953238821935;
                                attribute Izz : Real = 0.34663442210444284;
                                attribute sigma_Izz : Real = 0.37017423652493897;
                                attribute Ixy : Real = -0.0028252134728761437;
                                attribute sigma_Ixy : Real = 0.02351283871158888;
                                attribute Ixz : Real = -0.006881694618507912;
                                attribute sigma_Ixz : Real = 0.022566176940390956;
                                attribute Iyz : Real = -0.004427563417236822;
                                attribute sigma_Iyz : Real = 0.02209918015384651;
                            }
                            part <'C.1.1.4.3.4.1.4'> 'Part 613' {
                                attribute POIconv : String = "-";
                                attribute Ipoint : Boolean = false;
                                attribute mass : Real = 0.9810857957242988;
                                attribute sigma_mass : Real = 0.28909372274994966;
                                attribute Cx : Real = -72.85161898471415;
                                attribute sigma_Cx : Real = 28.721044428837228;
                                attribute Cy : Real = -62.826147908344865;
                                attribute sigma_Cy : Real = 28.23690002309109;
                                attribute Cz : Real = 13.354952866211534;
                                attribute sigma_Cz : Real = 29.057750463592832;
                                attribute Ixx : Real = 1.2735345142686227;
                                attribute sigma_Ixx : Real = 0.37074144170588635;
                                attribute Iyy : Real = 1.0575627610220366;
                                attribute sigma_Iyy : Real = 0.3723953238821935;
                                attribute Izz : Real = 1.2096568508134407;
                                attribute sigma_Izz : Real = 0.37017423652493897;
                                attribute Ixy : Real = -0.04264771343180812;
                                attribute sigma_Ixy : Real = 0.02351283871158888;
                                attribute Ixz : Real = 0.05629149624704567;
                                attribute sigma_Ixz : Real = 0.022566176940390956;
                                attribute Iyz : Real = 0.009299563351676617;
                                attribute sigma_Iyz : Real = 0.02209918015384651;
                            }
                            part <'C.1.1.4.3.4.1.5'> 'Part 614' {
                                attribute POIconv : String = "+";
                                attribute Ipoint : Boolean = false;
                                attribute mass : Real = 0.6888172699850984;
                                attribute sigma_mass : Real = 0.28909372274994966;
                                attribute Cx : Real = 67.01885610818863;
                                attribute sigma_Cx : Real = 28.721044428837228;
                                attribute Cy : Real = 24.642146890982985;
                                attribute sigma_Cy : Real = 28.23690002309109;
                                attribute Cz : Real = -55.19423000514507;
                                attribute sigma_Cz : Real = 29.057750463592832;
                                attribute Ixx : Real = 0.8489431213330922;
                                attribute sigma_Ixx : Real = 0.37074144170588635;
                                attribute Iyy : Real = 0.8873412652922231;
                                attribute sigma_Iyy : Real = 0.3723953238821935;
                                attribute Izz : Real = 0.7792877189646696;
                                attribute sigma_Izz : Real = 0.37017423652493897;
                                attribute Ixy : Real = -0.044500647369686175;
                                attribute sigma_Ixy : Real = 0.02351283871158888;
                                attribute Ixz : Real = -0.024339757222151124;
                                attribute sigma_Ixz : Real = 0.022566176940390956;
                                attribute Iyz : Real = 0.0001828165040163568;
                                attribute sigma_Iyz : Real = 0.02209918015384651;
                            }
                        }
                        part <'C.1.1.4.3.4.2'> 'Subassembly 177' {
                            attribute POIconv : String = "-";
                            attribute Ipoint : Boolean = false;
                            attribute mass : Real = 1.6584318347082008;
                            attribute sigma_mass : Real = 0.5781874454998993;
                            attribute Cx : Real = -40.56908301856375;
                            attribute sigma_Cx : Real = 22.307991903024426;
                            attribute Cy : Real = -12.459439096209325;
                            attribute sigma_Cy : Real = 21.453750770912478;
                            attribute Cz : Real = -5.325557147265485;
                            attribute sigma_Cz : Real = 31.859513966839994;
                            attribute Ixx : Real = 7518.3408425540365;
                            attribute sigma_Ixx : Real = 5492.937907621139;
                            attribute Iyy : Real = 8404.083621831223;
                            attribute sigma_Iyy : Real = 5935.080109677314;
                            attribute Izz : Real = 3364.2727817465634;
                            attribute sigma_Izz : Real = 2745.06520800363;
                            attribute Ixy : Real = -600.4535977944555;
                            attribute sigma_Ixy : Real = 1137.8470508005282;
                            attribute Ixz : Real = 1404.4915753105042;
                            attribute sigma_Ixz : Real = 2564.6634893243468;
                            attribute Iyz : Real = -1837.8177059209306;
                            attribute sigma_Iyz : Real = 2165.556524208957;
                            part <'C.1.1.4.3.4.2.1'> 'Part 615' {
                                attribute POIconv : String = "-";
                                attribute Ipoint : Boolean = false;
                                attribute mass : Real = 0.30510484090121465;
                                attribute sigma_mass : Real = 0.28909372274994966;
                                attribute Cx : Real = 24.81723129749298;
                                attribute sigma_Cx : Real = 28.721044428837228;
                                attribute Cy : Real = -10.214749770238996;
                                attribute sigma_Cy : Real = 28.23690002309109;
                                attribute Cz : Real = -99.26368980668485;
                                attribute sigma_Cz : Real = 29.057750463592832;
                                attribute Ixx : Real = 0.36726805956294817;
                                attribute sigma_Ixx : Real = 0.37074144170588635;
                                attribute Iyy : Real = 0.36027594004515484;
                                attribute sigma_Iyy : Real = 0.3723953238821935;
                                attribute Izz : Real = 0.44165506129856763;
                                attribute sigma_Izz : Real = 0.37017423652493897;
                                attribute Ixy : Real = -0.007869226533338576;
                                attribute sigma_Ixy : Real = 0.02351283871158888;
                                attribute Ixz : Real = 0.00750034548684524;
                                attribute sigma_Ixz : Real = 0.022566176940390956;
                                attribute Iyz : Real = 0.01439152655906041;
                                attribute sigma_Iyz : Real = 0.02209918015384651;
                            }
                            part <'C.1.1.4.3.4.2.2'> 'Part 616' {
                                attribute POIconv : String = "-";
                                attribute Ipoint : Boolean = false;
                                attribute mass : Real = 0.23407681215344928;
                                attribute sigma_mass : Real = 0.28909372274994966;
                                attribute Cx : Real = -64.75849249400198;
                                attribute sigma_Cx : Real = 28.721044428837228;
                                attribute Cy : Real = -70.23985991254449;
                                attribute sigma_Cy : Real = 28.23690002309109;
                                attribute Cz : Real = -70.36133245564997;
                                attribute sigma_Cz : Real = 29.057750463592832;
                                attribute Ixx : Real = 0.2283135519671674;
                                attribute sigma_Ixx : Real = 0.37074144170588635;
                                attribute Iyy : Real = 0.2561044301878222;
                                attribute sigma_Iyy : Real = 0.3723953238821935;
                                attribute Izz : Real = 0.26985652001674604;
                                attribute sigma_Izz : Real = 0.37017423652493897;
                                attribute Ixy : Real = -0.008857264258454465;
                                attribute sigma_Ixy : Real = 0.02351283871158888;
                                attribute Ixz : Real = 0.00010401126086884647;
                                attribute sigma_Ixz : Real = 0.022566176940390956;
                                attribute Iyz : Real = 0.006339513881813936;
                                attribute sigma_Iyz : Real = 0.02209918015384651;
                            }
                            part <'C.1.1.4.3.4.2.3'> 'Part 617' {
                                attribute POIconv : String = "-";
                                attribute Ipoint : Boolean = false;
                                attribute mass : Real = 0.907384101170348;
                                attribute sigma_mass : Real = 0.28909372274994966;
                                attribute Cx : Real = -63.547415006905794;
                                attribute sigma_Cx : Real = 28.721044428837228;
                                attribute Cy : Real = -9.002038324251771;
                                attribute sigma_Cy : Real = 28.23690002309109;
                                attribute Cz : Real = 20.371656212955713;
                                attribute sigma_Cz : Real = 29.057750463592832;
                                attribute Ixx : Real = 1.0789642397667212;
                                attribute sigma_Ixx : Real = 0.37074144170588635;
                                attribute Iyy : Real = 1.2456587244945194;
                                attribute sigma_Iyy : Real = 0.3723953238821935;
                                attribute Izz : Real = 1.2938684443306618;
                                attribute sigma_Izz : Real = 0.37017423652493897;
                                attribute Ixy : Real = -0.032861802898589615;
                                attribute sigma_Ixy : Real = 0.02351283871158888;
                                attribute Ixz : Real = -0.02159219808528338;
                                attribute sigma_Ixz : Real = 0.022566176940390956;
                                attribute Iyz : Real = -0.013593625129310123;
                                attribute sigma_Iyz : Real = 0.02209918015384651;
                            }
                            part <'C.1.1.4.3.4.2.4'> 'Part 618' {
                                attribute POIconv : String = "-";
                                attribute Ipoint : Boolean = false;
                                attribute mass : Real = 0.21186608048318886;
                                attribute sigma_mass : Real = 0.28909372274994966;
                                attribute Cx : Real = -9.593516122549772;
                                attribute sigma_Cx : Real = 28.721044428837228;
                                attribute Cy : Real = 33.33836211822927;
                                attribute sigma_Cy : Real = 28.23690002309109;
                                attribute Cz : Real = 91.75040274858475;
                                attribute sigma_Cz : Real = 29.057750463592832;
                                attribute Ixx : Real = 0.24113315541219454;
                                attribute sigma_Ixx : Real = 0.37074144170588635;
                                attribute Iyy : Real = 0.2542320275473199;
                                attribute sigma_Iyy : Real = 0.3723953238821935;
                                attribute Izz : Real = 0.2384186919880083;
                                attribute sigma_Izz : Real = 0.37017423652493897;
                                attribute Ixy : Real = 0.008502206007822647;
                                attribute sigma_Ixy : Real = 0.02351283871158888;
                                attribute Ixz : Real = 0.00036909246326706144;
                                attribute sigma_Ixz : Real = 0.022566176940390956;
                                attribute Iyz : Real = -0.0021335869360487275;
                                attribute sigma_Iyz : Real = 0.02209918015384651;
                            }
                        }
                    }
                    part <'C.1.1.4.3.5'> 'Assembly 49' {
                        attribute POIconv : String = "-";
                        attribute Ipoint : Boolean = false;
                        attribute mass : Real = 2.8548555768218353;
                        attribute sigma_mass : Real = 0.7081321085790055;
                        attribute Cx : Real = -1.7142532431130788;
                        attribute sigma_Cx : Real = 20.06324267117567;
                        attribute Cy : Real = 44.363998495306916;
                        attribute sigma_Cy : Real = 19.481012701897754;
                        attribute Cz : Real = 25.955758989054427;
                        attribute sigma_Cz : Real = 20.039320183084264;
                        attribute Ixx : Real = 12096.221855954882;
                        attribute sigma_Ixx : Real = 7671.69096680848;
                        attribute Iyy : Real = 12468.296079567259;
                        attribute sigma_Iyy : Real = 7789.291653943113;
                        attribute Izz : Real = 11640.941958800155;
                        attribute sigma_Izz : Real = 7317.745179107659;
                        attribute Ixy : Real = -4292.29082922385;
                        attribute sigma_Ixy : Real = 3639.603710021837;
                        attribute Ixz : Real = 69.00315971310351;
                        attribute sigma_Ixz : Real = 3849.28865681072;
                        attribute Iyz : Real = 3350.794704194786;
                        attribute sigma_Iyz : Real = 3775.291784511488;
                        part <'C.1.1.4.3.5.1'> 'Subassembly 178' {
                            attribute POIconv : String = "-";
                            attribute Ipoint : Boolean = false;
                            attribute mass : Real = 1.6478570087696425;
                            attribute sigma_mass : Real = 0.5007250159521434;
                            attribute Cx : Real = 8.381597920260305;
                            attribute sigma_Cx : Real = 24.98558567126547;
                            attribute Cy : Real = 73.02944637850428;
                            attribute sigma_Cy : Real = 20.972539388692475;
                            attribute Cz : Real = 5.501333337349849;
                            attribute sigma_Cz : Real = 23.162668569839575;
                            attribute Ixx : Real = 5285.265772517626;
                            attribute sigma_Ixx : Real = 3668.381571961023;
                            attribute Iyy : Real = 7649.547079664058;
                            attribute sigma_Iyy : Real = 4876.607713605594;
                            attribute Izz : Real = 5645.068956529157;
                            attribute sigma_Izz : Real = 3960.831612459829;
                            attribute Ixy : Real = -2078.6118961059215;
                            attribute sigma_Ixy : Real = 1831.276604136901;
                            attribute Ixz : Real = -2098.7460472111666;
                            attribute sigma_Ixz : Real = 2362.3696045426086;
                            attribute Iyz : Real = 103.98422708913375;
                            attribute sigma_Iyz : Real = 1655.1113741115964;
                            part <'C.1.1.4.3.5.1.1'> 'Part 619' {
                                attribute POIconv : String = "-";
                                attribute Ipoint : Boolean = false;
                                attribute mass : Real = 0.36018784902687184;
                                attribute sigma_mass : Real = 0.28909372274994966;
                                attribute Cx : Real = -54.99962489120662;
                                attribute sigma_Cx : Real = 28.721044428837228;
                                attribute Cy : Real = 14.565082965418696;
                                attribute sigma_Cy : Real = 28.23690002309109;
                                attribute Cz : Real = 26.739184837788343;
                                attribute sigma_Cz : Real = 29.057750463592832;
                                attribute Ixx : Real = 0.46593398089072524;
                                attribute sigma_Ixx : Real = 0.37074144170588635;
                                attribute Iyy : Real = 0.4154572955856419;
                                attribute sigma_Iyy : Real = 0.3723953238821935;
                                attribute Izz : Real = 0.44596979356504857;
                                attribute sigma_Izz : Real = 0.37017423652493897;
                                attribute Ixy : Real = 0.03018700574865391;
                                attribute sigma_Ixy : Real = 0.02351283871158888;
                                attribute Ixz : Real = 0.012002372931002866;
                                attribute sigma_Ixz : Real = 0.022566176940390956;
                                attribute Iyz : Real = 0.005172284348578503;
                                attribute sigma_Iyz : Real = 0.02209918015384651;
                            }
                            part <'C.1.1.4.3.5.1.2'> 'Part 620' {
                                attribute POIconv : String = "-";
                                attribute Ipoint : Boolean = false;
                                attribute mass : Real = 0.42649520421214404;
                                attribute sigma_mass : Real = 0.28909372274994966;
                                attribute Cx : Real = 84.20097441412508;
                                attribute sigma_Cx : Real = 28.721044428837228;
                                attribute Cy : Real = 99.38832256011665;
                                attribute sigma_Cy : Real = 28.23690002309109;
                                attribute Cz : Real = 72.96246164478362;
                                attribute sigma_Cz : Real = 29.057750463592832;
                                attribute Ixx : Real = 0.648733878506769;
                                attribute sigma_Ixx : Real = 0.37074144170588635;
                                attribute Iyy : Real = 0.64468474392724;
                                attribute sigma_Iyy : Real = 0.3723953238821935;
                                attribute Izz : Real = 0.617968950476794;
                                attribute sigma_Izz : Real = 0.37017423652493897;
                                attribute Ixy : Real = 0.022996312027488773;
                                attribute sigma_Ixy : Real = 0.02351283871158888;
                                attribute Ixz : Real = 0.019348612174992758;
                                attribute sigma_Ixz : Real = 0.022566176940390956;
                                attribute Iyz : Real = 0.01929193355889416;
                                attribute sigma_Iyz : Real = 0.02209918015384651;
                            }
                            part <'C.1.1.4.3.5.1.3'> 'Part 621' {
                                attribute POIconv : String = "+";
                                attribute Ipoint : Boolean = false;
                                attribute mass : Real = 0.8611739555306267;
                                attribute sigma_mass : Real = 0.28909372274994966;
                                attribute Cx : Real = -2.658510860055685;
                                attribute sigma_Cx : Real = 28.721044428837228;
                                attribute Cy : Real = 84.4280946534127;
                                attribute sigma_Cy : Real = 28.23690002309109;
                                attribute Cz : Real = -36.79147348739207;
                                attribute sigma_Cz : Real = 29.057750463592832;
                                attribute Ixx : Real = 0.9745464104751347;
                                attribute sigma_Ixx : Real = 0.37074144170588635;
                                attribute Iyy : Real = 1.0348666460656122;
                                attribute sigma_Iyy : Real = 0.3723953238821935;
                                attribute Izz : Real = 0.9936865779140995;
                                attribute sigma_Izz : Real = 0.37017423652493897;
                                attribute Ixy : Real = -0.01074890360035264;
                                attribute sigma_Ixy : Real = 0.02351283871158888;
                                attribute Ixz : Real = 0.0589430824941516;
                                attribute sigma_Ixz : Real = 0.022566176940390956;
                                attribute Iyz : Real = 0.03205383412988933;
                                attribute sigma_Iyz : Real = 0.02209918015384651;
                            }
                        }
                        part <'C.1.1.4.3.5.2'> 'Subassembly 179' {
                            attribute POIconv : String = "-";
                            attribute Ipoint : Boolean = false;
                            attribute mass : Real = 1.206998568052193;
                            attribute sigma_mass : Real = 0.5007250159521434;
                            attribute Cx : Real = -15.497632560544533;
                            attribute sigma_Cx : Real = 32.21957327948007;
                            attribute Cy : Real = 5.228443197941329;
                            attribute sigma_Cy : Real = 29.971523357786324;
                            attribute Cz : Real = 53.881201125172545;
                            attribute sigma_Cz : Real = 32.254506920784834;
                            attribute Ixx : Real = 1977.5796746781289;
                            attribute sigma_Ixx : Real = 4956.181319982259;
                            attribute Iyy : Real = 2790.791417998234;
                            attribute sigma_Iyy : Real = 5251.8387428901415;
                            attribute Izz : Real = 2395.919627487306;
                            attribute sigma_Izz : Real = 4808.396057432731;
                            attribute Ixy : Real = -1085.706248769067;
                            attribute sigma_Ixy : Real = 2391.561929171787;
                            attribute Ixz : Real = 1362.8766124621611;
                            attribute sigma_Ixz : Real = 2619.7983544283898;
                            attribute Iyz : Real = 961.5119880718421;
                            attribute sigma_Iyz : Real = 2467.6069803417427;
                            part <'C.1.1.4.3.5.2.1'> 'Part 622' {
                                attribute POIconv : String = "+";
                                attribute Ipoint : Boolean = false;
                                attribute mass : Real = 0.3421195869478397;
                                attribute sigma_mass : Real = 0.28909372274994966;
                                attribute Cx : Real = 29.029591754078865;
                                attribute sigma_Cx : Real = 28.721044428837228;
                                attribute Cy : Real = 28.445147769525647;
                                attribute sigma_Cy : Real = 28.23690002309109;
                                attribute Cz : Real = 20.892047323286533;
                                attribute sigma_Cz : Real = 29.057750463592832;
                                attribute Ixx : Real = 0.35100196471735606;
                                attribute sigma_Ixx : Real = 0.37074144170588635;
                                attribute Iyy : Real = 0.36166656520119794;
                                attribute sigma_Iyy : Real = 0.3723953238821935;
                                attribute Izz : Real = 0.35903603307787907;
                                attribute sigma_Izz : Real = 0.37017423652493897;
                                attribute Ixy : Real = -0.010653515180882141;
                                attribute sigma_Ixy : Real = 0.02351283871158888;
                                attribute Ixz : Real = -0.012655681288910342;
                                attribute sigma_Ixz : Real = 0.022566176940390956;
                                attribute Iyz : Real = 0.0038556263087321874;
                                attribute sigma_Iyz : Real = 0.02209918015384651;
                            }
                            part <'C.1.1.4.3.5.2.2'> 'Part 623' {
                                attribute POIconv : String = "-";
                                attribute Ipoint : Boolean = false;
                                attribute mass : Real = 0.8102129244310782;
                                attribute sigma_mass : Real = 0.28909372274994966;
                                attribute Cx : Real = -40.272019570693374;
                                attribute sigma_Cx : Real = 28.721044428837228;
                                attribute Cy : Real = -10.40549916215241;
                                attribute sigma_Cy : Real = 28.23690002309109;
                                attribute Cz : Real = 74.13752945140004;
                                attribute sigma_Cz : Real = 29.057750463592832;
                                attribute Ixx : Real = 1.1239316887072173;
                                attribute sigma_Ixx : Real = 0.37074144170588635;
                                attribute Iyy : Real = 1.062737904100701;
                                attribute sigma_Iyy : Real = 0.3723953238821935;
                                attribute Izz : Real = 0.916419075046008;
                                attribute sigma_Izz : Real = 0.37017423652493897;
                                attribute Ixy : Real = -0.08185847323484557;
                                attribute sigma_Ixy : Real = 0.02351283871158888;
                                attribute Ixz : Real = 0.009321796889378741;
                                attribute sigma_Ixz : Real = 0.022566176940390956;
                                attribute Iyz : Real = -0.028886946978181692;
                                attribute sigma_Iyz : Real = 0.02209918015384651;
                            }
                            part <'C.1.1.4.3.5.2.3'> 'Part 624' {
                                attribute POIconv : String = "+";
                                attribute Ipoint : Boolean = false;
                                attribute mass : Real = 0.05466605667327531;
                                attribute sigma_mass : Real = 0.28909372274994966;
                                attribute Cx : Real = 73.01968978717923;
                                attribute sigma_Cx : Real = 28.721044428837228;
                                attribute Cy : Real = 91.64281198754907;
                                attribute sigma_Cy : Real = 28.23690002309109;
                                attribute Cz : Real = -39.88271108828485;
                                attribute sigma_Cz : Real = 29.057750463592832;
                                attribute Ixx : Real = 0.07400038338779258;
                                attribute sigma_Ixx : Real = 0.37074144170588635;
                                attribute Iyy : Real = 0.07007849895235144;
                                attribute sigma_Iyy : Real = 0.3723953238821935;
                                attribute Izz : Real = 0.06647157977087918;
                                attribute sigma_Izz : Real = 0.37017423652493897;
                                attribute Ixy : Real = -0.0024084044725299486;
                                attribute sigma_Ixy : Real = 0.02351283871158888;
                                attribute Ixz : Real = -0.000624158241917667;
                                attribute sigma_Ixz : Real = 0.022566176940390956;
                                attribute Iyz : Real = 0.002195849483704372;
                                attribute sigma_Iyz : Real = 0.02209918015384651;
                            }
                        }
                    }
                }
                part <'C.1.1.4.4'> 'Subsystem 14' {
                    attribute POIconv : String = "-";
                    attribute Ipoint : Boolean = false;
                    attribute mass : Real = 28.167723920844026;
                    attribute sigma_mass : Real = 2.124396325737017;
                    attribute Cx : Real = 2.056048786443661;
                    attribute sigma_Cx : Real = 6.4665819178484325;
                    attribute Cy : Real = 3.397692095367448;
                    attribute sigma_Cy : Real = 6.07048304771498;
                    attribute Cz : Real = -3.270803400290217;
                    attribute sigma_Cz : Real = 6.4712401742508865;
                    attribute Ixx : Real = 169559.88647929457;
                    attribute sigma_Ixx : Real = 25121.35921551392;
                    attribute Iyy : Real = 191969.162959659;
                    attribute sigma_Iyy : Real = 29013.443320828886;
                    attribute Izz : Real = 171256.07651376654;
                    attribute sigma_Izz : Real = 26084.764302697353;
                    attribute Ixy : Real = 1850.0911383761154;
                    attribute sigma_Ixy : Real = 11746.285956907152;
                    attribute Ixz : Real = 12639.075846552769;
                    attribute sigma_Ixz : Real = 13959.710181165952;
                    attribute Iyz : Real = 8252.7957013247;
                    attribute sigma_Iyz : Real = 11535.431619042622;
                    part <'C.1.1.4.4.1'> 'Assembly 50' {
                        attribute POIconv : String = "-";
                        attribute Ipoint : Boolean = false;
                        attribute mass : Real = 6.582668787552975;
                        attribute sigma_mass : Real = 1.0014500319042867;
                        attribute Cx : Real = 1.6179876104533664;
                        attribute sigma_Cx : Real = 12.61851373797613;
                        attribute Cy : Real = 8.942900580955204;
                        attribute sigma_Cy : Real = 11.449925469767654;
                        attribute Cz : Real = -8.090808274585365;
                        attribute sigma_Cz : Real = 13.453841130486015;
                        attribute Ixx : Real = 36790.8410552847;
                        attribute sigma_Ixx : Real = 11128.01662205959;
                        attribute Iyy : Real = 53625.77645988968;
                        attribute sigma_Iyy : Real = 13627.018947303335;
                        attribute Izz : Real = 36311.70975325151;
                        attribute sigma_Izz : Real = 11021.053915110728;
                        attribute Ixy : Real = -1687.0330905809683;
                        attribute sigma_Ixy : Real = 4835.3368815318845;
                        attribute Ixz : Real = 7805.077277596523;
                        attribute sigma_Ixz : Real = 6712.755576759602;
                        attribute Iyz : Real = -306.5845697538635;
                        attribute sigma_Iyz : Real = 5249.711652640092;
                        part <'C.1.1.4.4.1.1'> 'Subassembly 180' {
                            attribute POIconv : String = "-";
                            attribute Ipoint : Boolean = false;
                            attribute mass : Real = 2.4098068569339812;
                            attribute sigma_mass : Real = 0.5781874454998993;
                            attribute Cx : Real = 22.443901738035116;
                            attribute sigma_Cx : Real = 21.439141485089078;
                            attribute Cy : Real = 14.32684067831811;
                            attribute sigma_Cy : Real = 15.78448631772444;
                            attribute Cz : Real = 19.296469769445547;
                            attribute sigma_Cz : Real = 19.34198213332468;
                            attribute Ixx : Real = 4383.892743759461;
                            attribute sigma_Ixx : Real = 3449.135140914497;
                            attribute Iyy : Real = 15711.926293352708;
                            attribute sigma_Iyy : Real = 7483.17486564559;
                            attribute Izz : Real = 11416.817468806736;
                            attribute sigma_Izz : Real = 6248.098671687926;
                            attribute Ixy : Real = 11.714823930072953;
                            attribute sigma_Ixy : Real = 2718.726709738665;
                            attribute Ixz : Real = 6302.839716847189;
                            attribute sigma_Ixz : Real = 3597.8127333589446;
                            attribute Iyz : Real = 33.32023059102232;
                            attribute sigma_Iyz : Real = 1570.8492765502629;
                            part <'C.1.1.4.4.1.1.1'> 'Part 625' {
                                attribute POIconv : String = "+";
                                attribute Ipoint : Boolean = false;
                                attribute mass : Real = 0.7876343644401058;
                                attribute sigma_mass : Real = 0.28909372274994966;
                                attribute Cx : Real = -73.83402697741985;
                                attribute sigma_Cx : Real = 28.721044428837228;
                                attribute Cy : Real = 13.13617629930377;
                                attribute sigma_Cy : Real = 28.23690002309109;
                                attribute Cz : Real = 73.16198796033859;
                                attribute sigma_Cz : Real = 29.057750463592832;
                                attribute Ixx : Real = 1.139252763741179;
                                attribute sigma_Ixx : Real = 0.37074144170588635;
                                attribute Iyy : Real = 0.9711585230914291;
                                attribute sigma_Iyy : Real = 0.3723953238821935;
                                attribute Izz : Real = 0.9862007547185113;
                                attribute sigma_Izz : Real = 0.37017423652493897;
                                attribute Ixy : Real = 0.015287389186507846;
                                attribute sigma_Ixy : Real = 0.02351283871158888;
                                attribute Ixz : Real = 0.008703336641789189;
                                attribute sigma_Ixz : Real = 0.022566176940390956;
                                attribute Iyz : Real = -0.005018832835694189;
                                attribute sigma_Iyz : Real = 0.02209918015384651;
                            }
                            part <'C.1.1.4.4.1.1.2'> 'Part 626' {
                                attribute POIconv : String = "-";
                                attribute Ipoint : Boolean = false;
                                attribute mass : Real = 0.578128091476392;
                                attribute sigma_mass : Real = 0.28909372274994966;
                                attribute Cx : Real = 55.574284167960286;
                                attribute sigma_Cx : Real = 28.721044428837228;
                                attribute Cy : Real = 19.393894588574767;
                                attribute sigma_Cy : Real = 28.23690002309109;
                                attribute Cz : Real = -26.010617520660162;
                                attribute sigma_Cz : Real = 29.057750463592832;
                                attribute Ixx : Real = 0.5831513984532389;
                                attribute sigma_Ixx : Real = 0.37074144170588635;
                                attribute Iyy : Real = 0.5607295373395104;
                                attribute sigma_Iyy : Real = 0.3723953238821935;
                                attribute Izz : Real = 0.6249180587770601;
                                attribute sigma_Izz : Real = 0.37017423652493897;
                                attribute Ixy : Real = 0.0259678977135785;
                                attribute sigma_Ixy : Real = 0.02351283871158888;
                                attribute Ixz : Real = 0.0024976451974963983;
                                attribute sigma_Ixz : Real = 0.022566176940390956;
                                attribute Iyz : Real = 0.010692804773251394;
                                attribute sigma_Iyz : Real = 0.02209918015384651;
                            }
                            part <'C.1.1.4.4.1.1.3'> 'Part 627' {
                                attribute POIconv : String = "-";
                                attribute Ipoint : Boolean = false;
                                attribute mass : Real = 0.134961188639747;
                                attribute sigma_mass : Real = 0.28909372274994966;
                                attribute Cx : Real = 28.62754762172699;
                                attribute sigma_Cx : Real = 28.721044428837228;
                                attribute Cy : Real = 24.620764516294003;
                                attribute sigma_Cy : Real = 28.23690002309109;
                                attribute Cz : Real = 66.66370336897671;
                                attribute sigma_Cz : Real = 29.057750463592832;
                                attribute Ixx : Real = 0.16727766255622784;
                                attribute sigma_Ixx : Real = 0.37074144170588635;
                                attribute Iyy : Real = 0.16610874643914114;
                                attribute sigma_Iyy : Real = 0.3723953238821935;
                                attribute Izz : Real = 0.16012159839722556;
                                attribute sigma_Izz : Real = 0.37017423652493897;
                                attribute Ixy : Real = -0.0020515438828217396;
                                attribute sigma_Ixy : Real = 0.02351283871158888;
                                attribute Ixz : Real = -0.0035147450648254585;
                                attribute sigma_Ixz : Real = 0.022566176940390956;
                                attribute Iyz : Real = -0.002231452592443744;
                                attribute sigma_Iyz : Real = 0.02209918015384651;
                            }
                            part <'C.1.1.4.4.1.1.4'> 'Part 628' {
                                attribute POIconv : String = "+";
                                attribute Ipoint : Boolean = false;
                                attribute mass : Real = 0.9090832123777364;
                                attribute sigma_mass : Real = 0.28909372274994966;
                                attribute Cx : Real = 83.87243486940861;
                                attribute sigma_Cx : Real = 28.721044428837228;
                                attribute Cy : Real = 10.607843147590756;
                                attribute sigma_Cy : Real = 28.23690002309109;
                                attribute Cz : Real = -5.592089518904686;
                                attribute sigma_Cz : Real = 29.057750463592832;
                                attribute Ixx : Real = 1.1806435467087562;
                                attribute sigma_Ixx : Real = 0.37074144170588635;
                                attribute Iyy : Real = 1.1912181174350485;
                                attribute sigma_Iyy : Real = 0.3723953238821935;
                                attribute Izz : Real = 1.1621758224177816;
                                attribute sigma_Izz : Real = 0.37017423652493897;
                                attribute Ixy : Real = 0.0428009847603786;
                                attribute sigma_Ixy : Real = 0.02351283871158888;
                                attribute Ixz : Real = 0.001608703548696245;
                                attribute sigma_Ixz : Real = 0.022566176940390956;
                                attribute Iyz : Real = -0.0199117417816868;
                                attribute sigma_Iyz : Real = 0.02209918015384651;
                            }
                        }
                        part <'C.1.1.4.4.1.2'> 'Subassembly 181' {
                            attribute POIconv : String = "-";
                            attribute Ipoint : Boolean = false;
                            attribute mass : Real = 2.0388678192561493;
                            attribute sigma_mass : Real = 0.6464332159373649;
                            attribute Cx : Real = 1.7378847065954264;
                            attribute sigma_Cx : Real = 22.155497778761173;
                            attribute Cy : Real = -3.0902918959649397;
                            attribute sigma_Cy : Real = 22.7177420884471;
                            attribute Cz : Real = 33.21352225043901;
                            attribute sigma_Cz : Real = 22.63127584909556;
                            attribute Ixx : Real = 9775.556860165398;
                            attribute sigma_Ixx : Real = 6092.394783103686;
                            attribute Iyy : Real = 13659.050949044322;
                            attribute sigma_Iyy : Real = 6771.523595702645;
                            attribute Izz : Real = 10407.967241492453;
                            attribute sigma_Izz : Real = 6020.088368390808;
                            attribute Ixy : Real = -1327.759248805115;
                            attribute sigma_Ixy : Real = 2491.778765145221;
                            attribute Ixz : Real = 5140.484229421143;
                            attribute sigma_Ixz : Real = 3256.331037739022;
                            attribute Iyz : Real = -1349.2716555709374;
                            attribute sigma_Iyz : Real = 2507.6951697983864;
                            part <'C.1.1.4.4.1.2.1'> 'Part 629' {
                                attribute POIconv : String = "-";
                                attribute Ipoint : Boolean = false;
                                attribute mass : Real = 0.2530637267380953;
                                attribute sigma_mass : Real = 0.28909372274994966;
                                attribute Cx : Real = 36.555469408631325;
                                attribute sigma_Cx : Real = 28.721044428837228;
                                attribute Cy : Real = 95.08864753879607;
                                attribute sigma_Cy : Real = 28.23690002309109;
                                attribute Cz : Real = 88.61079043708742;
                                attribute sigma_Cz : Real = 29.057750463592832;
                                attribute Ixx : Real = 0.2751498190880859;
                                attribute sigma_Ixx : Real = 0.37074144170588635;
                                attribute Iyy : Real = 0.2884679399052517;
                                attribute sigma_Iyy : Real = 0.3723953238821935;
                                attribute Izz : Real = 0.27654683093940435;
                                attribute sigma_Izz : Real = 0.37017423652493897;
                                attribute Ixy : Real = 0.008134720288820205;
                                attribute sigma_Ixy : Real = 0.02351283871158888;
                                attribute Ixz : Real = -0.0037418441572790503;
                                attribute sigma_Ixz : Real = 0.022566176940390956;
                                attribute Iyz : Real = -0.007731692357026624;
                                attribute sigma_Iyz : Real = 0.02209918015384651;
                            }
                            part <'C.1.1.4.4.1.2.2'> 'Part 630' {
                                attribute POIconv : String = "+";
                                attribute Ipoint : Boolean = false;
                                attribute mass : Real = 0.5131104602287524;
                                attribute sigma_mass : Real = 0.28909372274994966;
                                attribute Cx : Real = 33.715164894238114;
                                attribute sigma_Cx : Real = 28.721044428837228;
                                attribute Cy : Real = -2.213059226050973;
                                attribute sigma_Cy : Real = 28.23690002309109;
                                attribute Cz : Real = 22.465278627350926;
                                attribute sigma_Cz : Real = 29.057750463592832;
                                attribute Ixx : Real = 0.5908585732543389;
                                attribute sigma_Ixx : Real = 0.37074144170588635;
                                attribute Iyy : Real = 0.6727778525177867;
                                attribute sigma_Iyy : Real = 0.3723953238821935;
                                attribute Izz : Real = 0.632929651044438;
                                attribute sigma_Izz : Real = 0.37017423652493897;
                                attribute Ixy : Real = 5.841571015980603e-05;
                                attribute sigma_Ixy : Real = 0.02351283871158888;
                                attribute Ixz : Real = 0.008695652902468383;
                                attribute sigma_Ixz : Real = 0.022566176940390956;
                                attribute Iyz : Real = -0.048628502840556684;
                                attribute sigma_Iyz : Real = 0.02209918015384651;
                            }
                            part <'C.1.1.4.4.1.2.3'> 'Part 631' {
                                attribute POIconv : String = "+";
                                attribute Ipoint : Boolean = false;
                                attribute mass : Real = 0.09627683711610735;
                                attribute sigma_mass : Real = 0.28909372274994966;
                                attribute Cx : Real = 44.73222210071981;
                                attribute sigma_Cx : Real = 28.721044428837228;
                                attribute Cy : Real = -76.81080126203597;
                                attribute sigma_Cy : Real = 28.23690002309109;
                                attribute Cz : Real = 6.381321884691715;
                                attribute sigma_Cz : Real = 29.057750463592832;
                                attribute Ixx : Real = 0.10038840498046217;
                                attribute sigma_Ixx : Real = 0.37074144170588635;
                                attribute Iyy : Real = 0.10288062559698441;
                                attribute sigma_Iyy : Real = 0.3723953238821935;
                                attribute Izz : Real = 0.10105545383956836;
                                attribute sigma_Izz : Real = 0.37017423652493897;
                                attribute Ixy : Real = -0.00052345651808272;
                                attribute sigma_Ixy : Real = 0.02351283871158888;
                                attribute Ixz : Real = 0.001621883754674607;
                                attribute sigma_Ixz : Real = 0.022566176940390956;
                                attribute Iyz : Real = -0.002887650154809425;
                                attribute sigma_Iyz : Real = 0.02209918015384651;
                            }
                            part <'C.1.1.4.4.1.2.4'> 'Part 632' {
                                attribute POIconv : String = "+";
                                attribute Ipoint : Boolean = false;
                                attribute mass : Real = 0.7189656034540385;
                                attribute sigma_mass : Real = 0.28909372274994966;
                                attribute Cx : Real = -77.27161380462348;
                                attribute sigma_Cx : Real = 28.721044428837228;
                                attribute Cy : Real = -21.555351465940475;
                                attribute sigma_Cy : Real = 28.23690002309109;
                                attribute Cz : Real = 83.10190890915692;
                                attribute sigma_Cz : Real = 29.057750463592832;
                                attribute Ixx : Real = 0.8998275937366682;
                                attribute sigma_Ixx : Real = 0.37074144170588635;
                                attribute Iyy : Real = 0.8781170989823803;
                                attribute sigma_Iyy : Real = 0.3723953238821935;
                                attribute Izz : Real = 0.8928099108972033;
                                attribute sigma_Izz : Real = 0.37017423652493897;
                                attribute Ixy : Real = -0.1133287122914308;
                                attribute sigma_Ixy : Real = 0.02351283871158888;
                                attribute Ixz : Real = 0.019949234854670192;
                                attribute sigma_Ixz : Real = 0.022566176940390956;
                                attribute Iyz : Real = 0.002908574202194272;
                                attribute sigma_Iyz : Real = 0.02209918015384651;
                            }
                            part <'C.1.1.4.4.1.2.5'> 'Part 633' {
                                attribute POIconv : String = "-";
                                attribute Ipoint : Boolean = false;
                                attribute mass : Real = 0.45745119171915577;
                                attribute sigma_mass : Real = 0.28909372274994966;
                                attribute Cx : Real = 61.73730925656855;
                                attribute sigma_Cx : Real = 28.721044428837228;
                                attribute Cy : Real = -13.850621040910482;
                                attribute sigma_Cy : Real = 28.23690002309109;
                                attribute Cz : Real = -58.137682639062405;
                                attribute sigma_Cz : Real = 29.057750463592832;
                                attribute Ixx : Real = 0.5902970737033577;
                                attribute sigma_Ixx : Real = 0.37074144170588635;
                                attribute Iyy : Real = 0.6866288310140553;
                                attribute sigma_Iyy : Real = 0.3723953238821935;
                                attribute Izz : Real = 0.65671479826207;
                                attribute sigma_Izz : Real = 0.37017423652493897;
                                attribute Ixy : Real = -0.008924095188379094;
                                attribute sigma_Ixy : Real = 0.02351283871158888;
                                attribute Ixz : Real = -0.011028995694243936;
                                attribute sigma_Ixz : Real = 0.022566176940390956;
                                attribute Iyz : Real = 0.022484405377679366;
                                attribute sigma_Iyz : Real = 0.02209918015384651;
                            }
                        }
                        part <'C.1.1.4.4.1.3'> 'Subassembly 182' {
                            attribute POIconv : String = "-";
                            attribute Ipoint : Boolean = false;
                            attribute mass : Real = 2.1339941113628447;
                            attribute sigma_mass : Real = 0.5007250159521434;
                            attribute Cx : Real = -22.01416991471624;
                            attribute sigma_Cx : Real = 20.45185639506904;
                            attribute Cy : Real = 14.359894507324672;
                            attribute sigma_Cy : Real = 21.014122245372654;
                            attribute Cz : Real = -78.48093724767986;
                            attribute sigma_Cz : Real = 17.126051853151893;
                            attribute Ixx : Real = 6344.332572333707;
                            attribute sigma_Ixx : Real = 4217.866858857178;
                            attribute Iyy : Real = 6158.437691055546;
                            attribute sigma_Iyy : Real = 4258.286911017142;
                            attribute Izz : Real = 11822.231243981241;
                            attribute sigma_Izz : Real = 5956.84902727842;
                            attribute Ixy : Real = -376.9132930457331;
                            attribute sigma_Ixy : Real = 2755.422453759303;
                            attribute Ixz : Real = 1296.1565837166613;
                            attribute sigma_Ixz : Real = 2025.1298736147057;
                            attribute Iyz : Real = -462.3658576213259;
                            attribute sigma_Iyz : Real = 1880.5852646970943;
                            part <'C.1.1.4.4.1.3.1'> 'Part 634' {
                                attribute POIconv : String = "-";
                                attribute Ipoint : Boolean = false;
                                attribute mass : Real = 0.7445031916454901;
                                attribute sigma_mass : Real = 0.28909372274994966;
                                attribute Cx : Real = -77.09335209801793;
                                attribute sigma_Cx : Real = 28.721044428837228;
                                attribute Cy : Real = 56.73170727677643;
                                attribute sigma_Cy : Real = 28.23690002309109;
                                attribute Cz : Real = -62.00810060836375;
                                attribute sigma_Cz : Real = 29.057750463592832;
                                attribute Ixx : Real = 1.0505947686101482;
                                attribute sigma_Ixx : Real = 0.37074144170588635;
                                attribute Iyy : Real = 1.0911259668615945;
                                attribute sigma_Iyy : Real = 0.3723953238821935;
                                attribute Izz : Real = 1.0419452762255526;
                                attribute sigma_Izz : Real = 0.37017423652493897;
                                attribute Ixy : Real = 0.002777205497951083;
                                attribute sigma_Ixy : Real = 0.02351283871158888;
                                attribute Ixz : Real = 0.04384984317939566;
                                attribute sigma_Ixz : Real = 0.022566176940390956;
                                attribute Iyz : Real = 0.005179359757764826;
                                attribute sigma_Iyz : Real = 0.02209918015384651;
                            }
                            part <'C.1.1.4.4.1.3.2'> 'Part 635' {
                                attribute POIconv : String = "+";
                                attribute Ipoint : Boolean = false;
                                attribute mass : Real = 0.7894681825775187;
                                attribute sigma_mass : Real = 0.28909372274994966;
                                attribute Cx : Real = 43.335770489647985;
                                attribute sigma_Cx : Real = 28.721044428837228;
                                attribute Cy : Real = 38.13791209831834;
                                attribute sigma_Cy : Real = 28.23690002309109;
                                attribute Cz : Real = -91.25747540965676;
                                attribute sigma_Cz : Real = 29.057750463592832;
                                attribute Ixx : Real = 1.0521098089407661;
                                attribute sigma_Ixx : Real = 0.37074144170588635;
                                attribute Iyy : Real = 0.9764479277985872;
                                attribute sigma_Iyy : Real = 0.3723953238821935;
                                attribute Izz : Real = 0.9844375028349654;
                                attribute sigma_Izz : Real = 0.37017423652493897;
                                attribute Ixy : Real = -0.002212063508913096;
                                attribute sigma_Ixy : Real = 0.02351283871158888;
                                attribute Ixz : Real = 0.13761180567479708;
                                attribute sigma_Ixz : Real = 0.022566176940390956;
                                attribute Iyz : Real = -0.06166974936489115;
                                attribute sigma_Iyz : Real = 0.02209918015384651;
                            }
                            part <'C.1.1.4.4.1.3.3'> 'Part 636' {
                                attribute POIconv : String = "+";
                                attribute Ipoint : Boolean = false;
                                attribute mass : Real = 0.600022737139836;
                                attribute sigma_mass : Real = 0.28909372274994966;
                                attribute Cx : Real = -39.65528765693307;
                                attribute sigma_Cx : Real = 28.721044428837228;
                                attribute Cy : Real = -69.50015788897872;
                                attribute sigma_Cy : Real = 28.23690002309109;
                                attribute Cz : Real = -82.10981488227844;
                                attribute sigma_Cz : Real = 29.057750463592832;
                                attribute Ixx : Real = 0.7467293868149234;
                                attribute sigma_Ixx : Real = 0.37074144170588635;
                                attribute Iyy : Real = 0.7132531140447513;
                                attribute sigma_Iyy : Real = 0.3723953238821935;
                                attribute Izz : Real = 0.6617734497211627;
                                attribute sigma_Izz : Real = 0.37017423652493897;
                                attribute Ixy : Real = 0.030410120387099393;
                                attribute sigma_Ixy : Real = 0.02351283871158888;
                                attribute Ixz : Real = -0.0035022425268600196;
                                attribute sigma_Ixz : Real = 0.022566176940390956;
                                attribute Iyz : Real = 0.024813186905203406;
                                attribute sigma_Iyz : Real = 0.02209918015384651;
                            }
                        }
                    }
                    part <'C.1.1.4.4.2'> 'Assembly 51' {
                        attribute POIconv : String = "-";
                        attribute Ipoint : Boolean = false;
                        attribute mass : Real = 4.568352677763206;
                        attribute sigma_mass : Real = 0.8176805270198123;
                        attribute Cx : Real = -21.919590069459424;
                        attribute sigma_Cx : Real = 16.77639314329424;
                        attribute Cy : Real = 0.7271381464421238;
                        attribute sigma_Cy : Real = 14.883631410018593;
                        attribute Cz : Real = -29.038585751720436;
                        attribute sigma_Cz : Real = 15.675294533034414;
                        attribute Ixx : Real = 31972.67955301983;
                        attribute sigma_Ixx : Real = 10431.209617671806;
                        attribute Iyy : Real = 39571.35016369488;
                        attribute sigma_Iyy : Real = 12922.346020576497;
                        attribute Izz : Real = 34537.4716594608;
                        attribute sigma_Izz : Real = 11520.249573647057;
                        attribute Ixy : Real = 6475.898535363342;
                        attribute sigma_Ixy : Real = 5478.485109343416;
                        attribute Ixz : Real = 7528.424693199555;
                        attribute sigma_Ixz : Real = 6178.421542438105;
                        attribute Iyz : Real = 1968.0453216035403;
                        attribute sigma_Iyz : Real = 4985.834741463299;
                        part <'C.1.1.4.4.2.1'> 'Subassembly 183' {
                            attribute POIconv : String = "-";
                            attribute Ipoint : Boolean = false;
                            attribute mass : Real = 2.163085727279773;
                            attribute sigma_mass : Real = 0.5781874454998993;
                            attribute Cx : Real = -16.469906777222285;
                            attribute sigma_Cx : Real = 24.031590308518346;
                            attribute Cy : Real = -31.299271077151555;
                            attribute sigma_Cy : Real = 19.243158274402163;
                            attribute Cz : Real = -26.544798699169924;
                            attribute sigma_Cz : Real = 24.425518748036605;
                            attribute Ixx : Real = 17170.649166329753;
                            attribute sigma_Ixx : Real = 7629.106433132176;
                            attribute Iyy : Real = 25517.05860887665;
                            attribute sigma_Iyy : Real = 10377.09930664061;
                            attribute Izz : Real = 16585.33273618116;
                            attribute sigma_Izz : Real = 7747.069258371712;
                            attribute Ixy : Real = 4202.411324329854;
                            attribute sigma_Ixy : Real = 3515.41408978465;
                            attribute Ixz : Real = 10809.336011647027;
                            attribute sigma_Ixz : Real = 5023.283094045038;
                            attribute Iyz : Real = -1915.073096531729;
                            attribute sigma_Iyz : Real = 3365.2597994062653;
                            part <'C.1.1.4.4.2.1.1'> 'Part 637' {
                                attribute POIconv : String = "+";
                                attribute Ipoint : Boolean = false;
                                attribute mass : Real = 0.5850285754469223;
                                attribute sigma_mass : Real = 0.28909372274994966;
                                attribute Cx : Real = 92.03333049081266;
                                attribute sigma_Cx : Real = 28.721044428837228;
                                attribute Cy : Real = -95.03411869518459;
                                attribute sigma_Cy : Real = 28.23690002309109;
                                attribute Cz : Real = -94.54090013168752;
                                attribute sigma_Cz : Real = 29.057750463592832;
                                attribute Ixx : Real = 0.7385547623937166;
                                attribute sigma_Ixx : Real = 0.37074144170588635;
                                attribute Iyy : Real = 0.7691384008707457;
                                attribute sigma_Iyy : Real = 0.3723953238821935;
                                attribute Izz : Real = 0.7587495995937851;
                                attribute sigma_Izz : Real = 0.37017423652493897;
                                attribute Ixy : Real = -0.0568511866849163;
                                attribute sigma_Ixy : Real = 0.02351283871158888;
                                attribute Ixz : Real = 0.03762691444175087;
                                attribute sigma_Ixz : Real = 0.022566176940390956;
                                attribute Iyz : Real = 0.06051961046485135;
                                attribute sigma_Iyz : Real = 0.02209918015384651;
                            }
                            part <'C.1.1.4.4.2.1.2'> 'Part 638' {
                                attribute POIconv : String = "-";
                                attribute Ipoint : Boolean = false;
                                attribute mass : Real = 0.7281634239251725;
                                attribute sigma_mass : Real = 0.28909372274994966;
                                attribute Cx : Real = -99.07150059007108;
                                attribute sigma_Cx : Real = 28.721044428837228;
                                attribute Cy : Real = -20.29116591438651;
                                attribute sigma_Cy : Real = 28.23690002309109;
                                attribute Cz : Real = 81.64410474710166;
                                attribute sigma_Cz : Real = 29.057750463592832;
                                attribute Ixx : Real = 0.7946678896161208;
                                attribute sigma_Ixx : Real = 0.37074144170588635;
                                attribute Iyy : Real = 0.8027839388925051;
                                attribute sigma_Iyy : Real = 0.3723953238821935;
                                attribute Izz : Real = 0.6680983673206855;
                                attribute sigma_Izz : Real = 0.37017423652493897;
                                attribute Ixy : Real = 0.0015691527312515765;
                                attribute sigma_Ixy : Real = 0.02351283871158888;
                                attribute Ixz : Real = 0.01387978728029793;
                                attribute sigma_Ixz : Real = 0.022566176940390956;
                                attribute Iyz : Real = 0.005223915830027655;
                                attribute sigma_Iyz : Real = 0.02209918015384651;
                            }
                            part <'C.1.1.4.4.2.1.3'> 'Part 639' {
                                attribute POIconv : String = "-";
                                attribute Ipoint : Boolean = false;
                                attribute mass : Real = 0.34984703476168216;
                                attribute sigma_mass : Real = 0.28909372274994966;
                                attribute Cx : Real = 11.26664848998189;
                                attribute sigma_Cx : Real = 28.721044428837228;
                                attribute Cy : Real = 36.090205470100045;
                                attribute sigma_Cy : Real = 28.23690002309109;
                                attribute Cz : Real = -79.79898378252983;
                                attribute sigma_Cz : Real = 29.057750463592832;
                                attribute Ixx : Real = 0.34705694331724224;
                                attribute sigma_Ixx : Real = 0.37074144170588635;
                                attribute Iyy : Real = 0.34520902025967787;
                                attribute sigma_Iyy : Real = 0.3723953238821935;
                                attribute Izz : Real = 0.29848930728677286;
                                attribute sigma_Izz : Real = 0.37017423652493897;
                                attribute Ixy : Real = 0.001732562027179664;
                                attribute sigma_Ixy : Real = 0.02351283871158888;
                                attribute Ixz : Real = 0.004111237649007722;
                                attribute sigma_Ixz : Real = 0.022566176940390956;
                                attribute Iyz : Real = -0.003352189099066421;
                                attribute sigma_Iyz : Real = 0.02209918015384651;
                            }
                            part <'C.1.1.4.4.2.1.4'> 'Part 640' {
                                attribute POIconv : String = "+";
                                attribute Ipoint : Boolean = false;
                                attribute mass : Real = 0.5000466931459959;
                                attribute sigma_mass : Real = 0.28909372274994966;
                                attribute Cx : Real = -42.53464583307505;
                                attribute sigma_Cx : Real = 28.721044428837228;
                                attribute Cy : Real = -19.910336611792445;
                                attribute sigma_Cy : Real = 28.23690002309109;
                                attribute Cz : Real = -67.27843726985157;
                                attribute sigma_Cz : Real = 29.057750463592832;
                                attribute Ixx : Real = 0.675107583124659;
                                attribute sigma_Ixx : Real = 0.37074144170588635;
                                attribute Iyy : Real = 0.7330380267268488;
                                attribute sigma_Iyy : Real = 0.3723953238821935;
                                attribute Izz : Real = 0.6225290764573047;
                                attribute sigma_Izz : Real = 0.37017423652493897;
                                attribute Ixy : Real = 0.00821429025942937;
                                attribute sigma_Ixy : Real = 0.02351283871158888;
                                attribute Ixz : Real = 0.003499141306068416;
                                attribute sigma_Ixz : Real = 0.022566176940390956;
                                attribute Iyz : Real = -0.046860042677496855;
                                attribute sigma_Iyz : Real = 0.02209918015384651;
                            }
                        }
                        part <'C.1.1.4.4.2.2'> 'Subassembly 184' {
                            attribute POIconv : String = "-";
                            attribute Ipoint : Boolean = false;
                            attribute mass : Real = 2.405266950483434;
                            attribute sigma_mass : Real = 0.5781874454998993;
                            attribute Cx : Real = -26.820556319905716;
                            attribute sigma_Cx : Real = 23.347614582544605;
                            attribute Cy : Real = 29.528876212835556;
                            attribute sigma_Cy : Real = 19.809840986744174;
                            attribute Cz : Real = -31.281278679905764;
                            attribute sigma_Cz : Real = 20.08048972411907;
                            attribute Ixx : Real = 10562.557766118529;
                            attribute sigma_Ixx : Real = 5938.0036148911295;
                            attribute Iyy : Real = 13906.72685379341;
                            attribute sigma_Iyy : Real = 7652.564795176426;
                            attribute Izz : Real = 13616.201354486922;
                            attribute sigma_Izz : Real = 7537.72885855515;
                            attribute Ixy : Real = 1556.4369724834244;
                            attribute sigma_Ixy : Real = 3484.9923649540992;
                            attribute Ixz : Real = -3225.0770665199384;
                            attribute sigma_Ixz : Real = 3573.2078571840443;
                            attribute Iyz : Real = 3554.9946529484773;
                            attribute sigma_Iyz : Real = 2951.188471556781;
                            part <'C.1.1.4.4.2.2.1'> 'Part 641' {
                                attribute POIconv : String = "+";
                                attribute Ipoint : Boolean = false;
                                attribute mass : Real = 0.8178395064359065;
                                attribute sigma_mass : Real = 0.28909372274994966;
                                attribute Cx : Real = -99.41334365867078;
                                attribute sigma_Cx : Real = 28.721044428837228;
                                attribute Cy : Real = 66.0095114260912;
                                attribute sigma_Cy : Real = 28.23690002309109;
                                attribute Cz : Real = -86.4141988568008;
                                attribute sigma_Cz : Real = 29.057750463592832;
                                attribute Ixx : Real = 1.1799980484867147;
                                attribute sigma_Ixx : Real = 0.37074144170588635;
                                attribute Iyy : Real = 1.2723315048634494;
                                attribute sigma_Iyy : Real = 0.3723953238821935;
                                attribute Izz : Real = 1.2490540993734833;
                                attribute sigma_Izz : Real = 0.37017423652493897;
                                attribute Ixy : Real = -0.007872232966019563;
                                attribute sigma_Ixy : Real = 0.02351283871158888;
                                attribute Ixz : Real = -0.0038526707459050394;
                                attribute sigma_Ixz : Real = 0.022566176940390956;
                                attribute Iyz : Real = -0.018515835467333753;
                                attribute sigma_Iyz : Real = 0.02209918015384651;
                            }
                            part <'C.1.1.4.4.2.2.2'> 'Part 642' {
                                attribute POIconv : String = "+";
                                attribute Ipoint : Boolean = false;
                                attribute mass : Real = 0.7008634718770627;
                                attribute sigma_mass : Real = 0.28909372274994966;
                                attribute Cx : Real = -26.6862197779119;
                                attribute sigma_Cx : Real = 28.721044428837228;
                                attribute Cy : Real = -35.09652717038989;
                                attribute sigma_Cy : Real = 28.23690002309109;
                                attribute Cz : Real = 27.19354876317084;
                                attribute sigma_Cz : Real = 29.057750463592832;
                                attribute Ixx : Real = 0.8581735090661876;
                                attribute sigma_Ixx : Real = 0.37074144170588635;
                                attribute Iyy : Real = 0.7990625431995491;
                                attribute sigma_Iyy : Real = 0.3723953238821935;
                                attribute Izz : Real = 0.8340933780478439;
                                attribute sigma_Izz : Real = 0.37017423652493897;
                                attribute Ixy : Real = -0.053903288222560616;
                                attribute sigma_Ixy : Real = 0.02351283871158888;
                                attribute Ixz : Real = 0.026856863933016447;
                                attribute sigma_Ixz : Real = 0.022566176940390956;
                                attribute Iyz : Real = 0.014718945302150503;
                                attribute sigma_Iyz : Real = 0.02209918015384651;
                            }
                            part <'C.1.1.4.4.2.2.3'> 'Part 643' {
                                attribute POIconv : String = "-";
                                attribute Ipoint : Boolean = false;
                                attribute mass : Real = 0.11524255599244498;
                                attribute sigma_mass : Real = 0.28909372274994966;
                                attribute Cx : Real = 79.45131273008883;
                                attribute sigma_Cx : Real = 28.721044428837228;
                                attribute Cy : Real = -33.110162895172834;
                                attribute sigma_Cy : Real = 28.23690002309109;
                                attribute Cz : Real = -89.52125748619437;
                                attribute sigma_Cz : Real = 29.057750463592832;
                                attribute Ixx : Real = 0.13369376134203798;
                                attribute sigma_Ixx : Real = 0.37074144170588635;
                                attribute Iyy : Real = 0.1109909330288093;
                                attribute sigma_Iyy : Real = 0.3723953238821935;
                                attribute Izz : Real = 0.13577337908492074;
                                attribute sigma_Izz : Real = 0.37017423652493897;
                                attribute Ixy : Real = -0.016250548696400337;
                                attribute sigma_Ixy : Real = 0.02351283871158888;
                                attribute Ixz : Real = 0.0018443793115279277;
                                attribute sigma_Ixz : Real = 0.022566176940390956;
                                attribute Iyz : Real = 0.004216570133306237;
                                attribute sigma_Iyz : Real = 0.02209918015384651;
                            }
                            part <'C.1.1.4.4.2.2.4'> 'Part 644' {
                                attribute POIconv : String = "+";
                                attribute Ipoint : Boolean = false;
                                attribute mass : Real = 0.7713214161780197;
                                attribute sigma_mass : Real = 0.28909372274994966;
                                attribute Cx : Real = 34.15020760148764;
                                attribute sigma_Cx : Real = 28.721044428837228;
                                attribute Cy : Real = 58.92902300693095;
                                attribute sigma_Cy : Real = 28.23690002309109;
                                attribute Cz : Real = -17.255045985803008;
                                attribute sigma_Cz : Real = 29.057750463592832;
                                attribute Ixx : Real = 0.9416641897622688;
                                attribute sigma_Ixx : Real = 0.37074144170588635;
                                attribute Iyy : Real = 0.8602111167660398;
                                attribute sigma_Iyy : Real = 0.3723953238821935;
                                attribute Izz : Real = 0.9335252373162685;
                                attribute sigma_Izz : Real = 0.37017423652493897;
                                attribute Ixy : Real = 0.03224752135352436;
                                attribute sigma_Ixy : Real = 0.02351283871158888;
                                attribute Ixz : Real = -0.00867700382084487;
                                attribute sigma_Ixz : Real = 0.022566176940390956;
                                attribute Iyz : Real = -0.032925345619652005;
                                attribute sigma_Iyz : Real = 0.02209918015384651;
                            }
                        }
                    }
                    part <'C.1.1.4.4.3'> 'Assembly 52' {
                        attribute POIconv : String = "-";
                        attribute Ipoint : Boolean = false;
                        attribute mass : Real = 8.629122503633145;
                        attribute sigma_mass : Real = 1.2265207905297186;
                        attribute Cx : Real = 15.924352572100098;
                        attribute sigma_Cx : Real = 12.177984389202807;
                        attribute Cy : Real = -1.2159553085875485;
                        attribute sigma_Cy : Real = 11.14401308671958;
                        attribute Cz : Real = 1.772283067161325;
                        attribute sigma_Cz : Real = 11.948431547352309;
                        attribute Ixx : Real = 44214.053579354004;
                        attribute sigma_Ixx : Real = 13846.128894100208;
                        attribute Iyy : Real = 47959.92599931497;
                        attribute sigma_Iyy : Real = 16921.418445181665;
                        attribute Izz : Real = 49388.71236521364;
                        attribute sigma_Izz : Real = 15018.7728610704;
                        attribute Ixy : Real = -6781.296841247373;
                        attribute sigma_Ixy : Real = 6644.275130384153;
                        attribute Ixz : Real = -4752.707282607646;
                        attribute sigma_Ixz : Real = 8035.831623501373;
                        attribute Iyz : Real = 5763.619449714652;
                        attribute sigma_Iyz : Real = 6043.621314987049;
                        part <'C.1.1.4.4.3.1'> 'Subassembly 185' {
                            attribute POIconv : String = "-";
                            attribute Ipoint : Boolean = false;
                            attribute mass : Real = 0.926858893287601;
                            attribute sigma_mass : Real = 0.40884026350990615;
                            attribute Cx : Real = 21.21140581137241;
                            attribute sigma_Cx : Real = 34.6096552348212;
                            attribute Cy : Real = -18.22771113483078;
                            attribute sigma_Cy : Real = 36.55785119441237;
                            attribute Cz : Real = 35.99914794264251;
                            attribute sigma_Cz : Real = 23.486892690066963;
                            attribute Ixx : Real = 4551.437308628235;
                            attribute sigma_Ixx : Real = 3452.684573729556;
                            attribute Iyy : Real = 3878.683889737632;
                            attribute sigma_Iyy : Real = 3105.9645189038088;
                            attribute Izz : Real = 7438.042563847515;
                            attribute sigma_Izz : Real = 5020.372996438215;
                            attribute Ixy : Real = -3703.0919739782867;
                            attribute sigma_Ixy : Real = 2505.922611029074;
                            attribute Ixz : Real = 1294.3303580523482;
                            attribute sigma_Ixz : Real = 1375.1972894832663;
                            attribute Iyz : Real = 1417.1960834213364;
                            attribute sigma_Iyz : Real = 1491.7036456907745;
                            part <'C.1.1.4.4.3.1.1'> 'Part 645' {
                                attribute POIconv : String = "-";
                                attribute Ipoint : Boolean = false;
                                attribute mass : Real = 0.3708922187909484;
                                attribute sigma_mass : Real = 0.28909372274994966;
                                attribute Cx : Real = 95.16847915947437;
                                attribute sigma_Cx : Real = 28.721044428837228;
                                attribute Cy : Real = 62.7530378755182;
                                attribute sigma_Cy : Real = 28.23690002309109;
                                attribute Cz : Real = 7.694865297526121;
                                attribute sigma_Cz : Real = 29.057750463592832;
                                attribute Ixx : Real = 0.48991264372612714;
                                attribute sigma_Ixx : Real = 0.37074144170588635;
                                attribute Iyy : Real = 0.4995432845810946;
                                attribute sigma_Iyy : Real = 0.3723953238821935;
                                attribute Izz : Real = 0.4629455816568369;
                                attribute sigma_Izz : Real = 0.37017423652493897;
                                attribute Ixy : Real = 0.034515841272272085;
                                attribute sigma_Ixy : Real = 0.02351283871158888;
                                attribute Ixz : Real = -0.0019665326911897036;
                                attribute sigma_Ixz : Real = 0.022566176940390956;
                                attribute Iyz : Real = -0.002147191810277855;
                                attribute sigma_Iyz : Real = 0.02209918015384651;
                            }
                            part <'C.1.1.4.4.3.1.2'> 'Part 646' {
                                attribute POIconv : String = "-";
                                attribute Ipoint : Boolean = false;
                                attribute mass : Real = 0.5559666744966526;
                                attribute sigma_mass : Real = 0.28909372274994966;
                                attribute Cx : Real = -28.1262690667063;
                                attribute sigma_Cx : Real = 28.721044428837228;
                                attribute Cy : Real = -72.25096658803523;
                                attribute sigma_Cy : Real = 28.23690002309109;
                                attribute Cz : Real = 54.88128364086151;
                                attribute sigma_Cz : Real = 29.057750463592832;
                                attribute Ixx : Real = 0.7292300228806227;
                                attribute sigma_Ixx : Real = 0.37074144170588635;
                                attribute Iyy : Real = 0.841315023274269;
                                attribute sigma_Iyy : Real = 0.3723953238821935;
                                attribute Izz : Real = 0.7291900871263225;
                                attribute sigma_Izz : Real = 0.37017423652493897;
                                attribute Ixy : Real = 0.047261992220689095;
                                attribute sigma_Ixy : Real = 0.02351283871158888;
                                attribute Ixz : Real = 0.0040078407510839254;
                                attribute sigma_Ixz : Real = 0.022566176940390956;
                                attribute Iyz : Real = -0.05196345428313482;
                                attribute sigma_Iyz : Real = 0.02209918015384651;
                            }
                        }
                        part <'C.1.1.4.4.3.2'> 'Subassembly 186' {
                            attribute POIconv : String = "-";
                            attribute Ipoint : Boolean = false;
                            attribute mass : Real = 1.8870062813637778;
                            attribute sigma_mass : Real = 0.6464332159373649;
                            attribute Cx : Real = 28.54804223121892;
                            attribute sigma_Cx : Real = 25.58407256950963;
                            attribute Cy : Real = -41.54090027884227;
                            attribute sigma_Cy : Real = 22.507677596194895;
                            attribute Cz : Real = 49.25923244912354;
                            attribute sigma_Cz : Real = 29.57945885161729;
                            attribute Ixx : Real = 12796.514328913969;
                            attribute sigma_Ixx : Real = 7796.123695562876;
                            attribute Iyy : Real = 11093.56430829282;
                            attribute sigma_Iyy : Real = 9497.323366660692;
                            attribute Izz : Real = 11622.91404684919;
                            attribute sigma_Izz : Real = 6418.532678992061;
                            attribute Ixy : Real = -4197.9184501690615;
                            attribute sigma_Ixy : Real = 2811.7566122714366;
                            attribute Ixz : Real = -5073.942525876878;
                            attribute sigma_Ixz : Real = 4574.876038072825;
                            attribute Iyz : Real = -2594.6007754306215;
                            attribute sigma_Iyz : Real = 2731.471332167237;
                            part <'C.1.1.4.4.3.2.1'> 'Part 647' {
                                attribute POIconv : String = "-";
                                attribute Ipoint : Boolean = false;
                                attribute mass : Real = 0.5929015871589072;
                                attribute sigma_mass : Real = 0.28909372274994966;
                                attribute Cx : Real = 90.22030089981854;
                                attribute sigma_Cx : Real = 28.721044428837228;
                                attribute Cy : Real = 43.91450327821076;
                                attribute sigma_Cy : Real = 28.23690002309109;
                                attribute Cz : Real = 93.74375697225332;
                                attribute sigma_Cz : Real = 29.057750463592832;
                                attribute Ixx : Real = 0.7132659420359875;
                                attribute sigma_Ixx : Real = 0.37074144170588635;
                                attribute Iyy : Real = 0.8145055400847724;
                                attribute sigma_Iyy : Real = 0.3723953238821935;
                                attribute Izz : Real = 0.798426913221992;
                                attribute sigma_Izz : Real = 0.37017423652493897;
                                attribute Ixy : Real = -0.028204504287408484;
                                attribute sigma_Ixy : Real = 0.02351283871158888;
                                attribute Ixz : Real = -0.01351279316801711;
                                attribute sigma_Ixz : Real = 0.022566176940390956;
                                attribute Iyz : Real = 0.0895824291515327;
                                attribute sigma_Iyz : Real = 0.02209918015384651;
                            }
                            part <'C.1.1.4.4.3.2.2'> 'Part 648' {
                                attribute POIconv : String = "-";
                                attribute Ipoint : Boolean = false;
                                attribute mass : Real = 0.11944463109923527;
                                attribute sigma_mass : Real = 0.28909372274994966;
                                attribute Cx : Real = -70.27734313160181;
                                attribute sigma_Cx : Real = 28.721044428837228;
                                attribute Cy : Real = -54.88735265098512;
                                attribute sigma_Cy : Real = 28.23690002309109;
                                attribute Cz : Real = -85.39182115346193;
                                attribute sigma_Cz : Real = 29.057750463592832;
                                attribute Ixx : Real = 0.15561112986551978;
                                attribute sigma_Ixx : Real = 0.37074144170588635;
                                attribute Iyy : Real = 0.13392965961057846;
                                attribute sigma_Iyy : Real = 0.3723953238821935;
                                attribute Izz : Real = 0.14201765980254955;
                                attribute sigma_Izz : Real = 0.37017423652493897;
                                attribute Ixy : Real = -0.006894970837519226;
                                attribute sigma_Ixy : Real = 0.02351283871158888;
                                attribute Ixz : Real = -0.010849575401658864;
                                attribute sigma_Ixz : Real = 0.022566176940390956;
                                attribute Iyz : Real = -0.002121634058788813;
                                attribute sigma_Iyz : Real = 0.02209918015384651;
                            }
                            part <'C.1.1.4.4.3.2.3'> 'Part 649' {
                                attribute POIconv : String = "+";
                                attribute Ipoint : Boolean = false;
                                attribute mass : Real = 0.7270542142656632;
                                attribute sigma_mass : Real = 0.28909372274994966;
                                attribute Cx : Real = 27.828036528080702;
                                attribute sigma_Cx : Real = 28.721044428837228;
                                attribute Cy : Real = -91.04517088271677;
                                attribute sigma_Cy : Real = 28.23690002309109;
                                attribute Cz : Real = 75.82955206744373;
                                attribute sigma_Cz : Real = 29.057750463592832;
                                attribute Ixx : Real = 1.0071645506733111;
                                attribute sigma_Ixx : Real = 0.37074144170588635;
                                attribute Iyy : Real = 0.89517000135824;
                                attribute sigma_Iyy : Real = 0.3723953238821935;
                                attribute Izz : Real = 0.837896063840597;
                                attribute sigma_Izz : Real = 0.37017423652493897;
                                attribute Ixy : Real = -0.004771443169109581;
                                attribute sigma_Ixy : Real = 0.02351283871158888;
                                attribute Ixz : Real = -0.07115226375479916;
                                attribute sigma_Ixz : Real = 0.022566176940390956;
                                attribute Iyz : Real = 0.06062610864754969;
                                attribute sigma_Iyz : Real = 0.02209918015384651;
                            }
                            part <'C.1.1.4.4.3.2.4'> 'Part 650' {
                                attribute POIconv : String = "-";
                                attribute Ipoint : Boolean = false;
                                attribute mass : Real = 0.39043298179726116;
                                attribute sigma_mass : Real = 0.28909372274994966;
                                attribute Cx : Real = -34.16824992746115;
                                attribute sigma_Cx : Real = 28.721044428837228;
                                attribute Cy : Real = -77.69201076589525;
                                attribute sigma_Cy : Real = 28.23690002309109;
                                attribute Cz : Real = -27.146129868924618;
                                attribute sigma_Cz : Real = 29.057750463592832;
                                attribute Ixx : Real = 0.4736410963161003;
                                attribute sigma_Ixx : Real = 0.37074144170588635;
                                attribute Iyy : Real = 0.5272370345692045;
                                attribute sigma_Iyy : Real = 0.3723953238821935;
                                attribute Izz : Real = 0.5095622791079157;
                                attribute sigma_Izz : Real = 0.37017423652493897;
                                attribute Ixy : Real = 0.005098307148937808;
                                attribute sigma_Ixy : Real = 0.02351283871158888;
                                attribute Ixz : Real = 0.010748909107348673;
                                attribute sigma_Ixz : Real = 0.022566176940390956;
                                attribute Iyz : Real = 0.020505577586772107;
                                attribute sigma_Iyz : Real = 0.02209918015384651;
                            }
                            part <'C.1.1.4.4.3.2.5'> 'Part 651' {
                                attribute POIconv : String = "-";
                                attribute Ipoint : Boolean = false;
                                attribute mass : Real = 0.057172867042711004;
                                attribute sigma_mass : Real = 0.28909372274994966;
                                attribute Cx : Real = 32.895800145342946;
                                attribute sigma_Cx : Real = 28.721044428837228;
                                attribute Cy : Real = -23.44853999093175;
                                attribute sigma_Cy : Real = 28.23690002309109;
                                attribute Cz : Real = 53.1336369458586;
                                attribute sigma_Cz : Real = 29.057750463592832;
                                attribute Ixx : Real = 0.08190849231471198;
                                attribute sigma_Ixx : Real = 0.37074144170588635;
                                attribute Iyy : Real = 0.07678246082938343;
                                attribute sigma_Iyy : Real = 0.3723953238821935;
                                attribute Izz : Real = 0.07321211261888941;
                                attribute sigma_Izz : Real = 0.37017423652493897;
                                attribute Ixy : Real = 0.0032909567413494647;
                                attribute sigma_Ixy : Real = 0.02351283871158888;
                                attribute Ixz : Real = -0.0002642453420887582;
                                attribute sigma_Ixz : Real = 0.022566176940390956;
                                attribute Iyz : Real = 0.00016256916490882265;
                                attribute sigma_Iyz : Real = 0.02209918015384651;
                            }
                        }
                        part <'C.1.1.4.4.3.3'> 'Subassembly 187' {
                            attribute POIconv : String = "-";
                            attribute Ipoint : Boolean = false;
                            attribute mass : Real = 0.6222719662049785;
                            attribute sigma_mass : Real = 0.40884026350990615;
                            attribute Cx : Real = 63.91563268635035;
                            attribute sigma_Cx : Real = 66.88554097947093;
                            attribute Cy : Real = -15.454342798890089;
                            attribute sigma_Cy : Real = 34.48530865823268;
                            attribute Cz : Real = -72.45147303496678;
                            attribute sigma_Cz : Real = 39.63101618138562;
                            attribute Ixx : Real = 251.22941686693358;
                            attribute sigma_Ixx : Real = 1764.5557981436216;
                            attribute Iyy : Real = 874.264609114297;
                            attribute sigma_Iyy : Real = 6112.101652527694;
                            attribute Izz : Real = 809.2905867459872;
                            attribute sigma_Izz : Real = 5658.750722755179;
                            attribute Ixy : Real = -257.63521375386046;
                            attribute sigma_Ixy : Real = 1810.8069896801703;
                            attribute Ixz : Real = 335.9662898318973;
                            attribute sigma_Ixz : Real = 2355.621164009638;
                            attribute Iyz : Real = 120.88844603244254;
                            attribute sigma_Iyz : Real = 852.5502417719199;
                            part <'C.1.1.4.4.3.3.1'> 'Part 652' {
                                attribute POIconv : String = "+";
                                attribute Ipoint : Boolean = false;
                                attribute mass : Real = 0.5834298036796972;
                                attribute sigma_mass : Real = 0.28909372274994966;
                                attribute Cx : Real = 72.66629724763334;
                                attribute sigma_Cx : Real = 28.721044428837228;
                                attribute Cy : Real = -12.304610526189208;
                                attribute sigma_Cy : Real = 28.23690002309109;
                                attribute Cz : Real = -76.55869051814079;
                                attribute sigma_Cz : Real = 29.057750463592832;
                                attribute Ixx : Real = 0.7744401753220163;
                                attribute sigma_Ixx : Real = 0.37074144170588635;
                                attribute Iyy : Real = 0.8091303297473567;
                                attribute sigma_Iyy : Real = 0.3723953238821935;
                                attribute Izz : Real = 0.7752726147253572;
                                attribute sigma_Izz : Real = 0.37017423652493897;
                                attribute Ixy : Real = 0.014912444861162326;
                                attribute sigma_Ixy : Real = 0.02351283871158888;
                                attribute Ixz : Real = -0.03203726823482057;
                                attribute sigma_Ixz : Real = 0.022566176940390956;
                                attribute Iyz : Real = 0.025091479071070885;
                                attribute sigma_Iyz : Real = 0.02209918015384651;
                            }
                            part <'C.1.1.4.4.3.3.2'> 'Part 653' {
                                attribute POIconv : String = "+";
                                attribute Ipoint : Boolean = false;
                                attribute mass : Real = 0.03884216252528131;
                                attribute sigma_mass : Real = 0.28909372274994966;
                                attribute Cx : Real = -67.52397250384092;
                                attribute sigma_Cx : Real = 28.721044428837228;
                                attribute Cy : Real = -62.76498571969569;
                                attribute sigma_Cy : Real = 28.23690002309109;
                                attribute Cz : Real = -10.758896358311176;
                                attribute sigma_Cz : Real = 29.057750463592832;
                                attribute Ixx : Real = 0.05230914465404922;
                                attribute sigma_Ixx : Real = 0.37074144170588635;
                                attribute Iyy : Real = 0.054008826850562894;
                                attribute sigma_Iyy : Real = 0.3723953238821935;
                                attribute Izz : Real = 0.05972875603266172;
                                attribute sigma_Izz : Real = 0.37017423652493897;
                                attribute Ixy : Real = -2.286942533325464e-05;
                                attribute sigma_Ixy : Real = 0.02351283871158888;
                                attribute Ixz : Real = -8.16954618559898e-05;
                                attribute sigma_Ixz : Real = 0.022566176940390956;
                                attribute Iyz : Real = 0.0033016698351556743;
                                attribute sigma_Iyz : Real = 0.02209918015384651;
                            }
                        }
                        part <'C.1.1.4.4.3.4'> 'Subassembly 188' {
                            attribute POIconv : String = "-";
                            attribute Ipoint : Boolean = false;
                            attribute mass : Real = 2.598564336190233;
                            attribute sigma_mass : Real = 0.5781874454998993;
                            attribute Cx : Real = -3.546627086402233;
                            attribute sigma_Cx : Real = 21.79494456979627;
                            attribute Cy : Real = 21.61000668461704;
                            attribute sigma_Cy : Real = 18.81471160307881;
                            attribute Cz : Real = 6.376054738511495;
                            attribute sigma_Cz : Real = 17.779185326175188;
                            attribute Ixx : Real = 3393.96430951213;
                            attribute sigma_Ixx : Real = 3654.729823687077;
                            attribute Iyy : Real = 13923.251788526952;
                            attribute sigma_Iyy : Real = 7142.3254066434265;
                            attribute Izz : Real = 14818.978183492827;
                            attribute sigma_Izz : Real = 7559.266917731297;
                            attribute Ixy : Real = -2720.196943410532;
                            attribute sigma_Ixy : Real = 3463.3569036123836;
                            attribute Ixz : Real = -1778.5560306209295;
                            attribute sigma_Ixz : Real = 3297.4564284919747;
                            attribute Iyz : Real = 199.9857436918777;
                            attribute sigma_Iyz : Real = 1760.7676069355357;
                            part <'C.1.1.4.4.3.4.1'> 'Part 654' {
                                attribute POIconv : String = "-";
                                attribute Ipoint : Boolean = false;
                                attribute mass : Real = 0.7294995150738396;
                                attribute sigma_mass : Real = 0.28909372274994966;
                                attribute Cx : Real = 20.80776821821928;
                                attribute sigma_Cx : Real = 28.721044428837228;
                                attribute Cy : Real = 56.439983658492565;
                                attribute sigma_Cy : Real = 28.23690002309109;
                                attribute Cz : Real = -18.41131648980081;
                                attribute sigma_Cz : Real = 29.057750463592832;
                                attribute Ixx : Real = 1.0885855727211162;
                                attribute sigma_Ixx : Real = 0.37074144170588635;
                                attribute Iyy : Real = 1.0362376835868075;
                                attribute sigma_Iyy : Real = 0.3723953238821935;
                                attribute Izz : Real = 1.1099342308146714;
                                attribute sigma_Izz : Real = 0.37017423652493897;
                                attribute Ixy : Real = -0.02262375998969255;
                                attribute sigma_Ixy : Real = 0.02351283871158888;
                                attribute Ixz : Real = -0.04306735791686042;
                                attribute sigma_Ixz : Real = 0.022566176940390956;
                                attribute Iyz : Real = -0.0007850062816412658;
                                attribute sigma_Iyz : Real = 0.02209918015384651;
                            }
                            part <'C.1.1.4.4.3.4.2'> 'Part 655' {
                                attribute POIconv : String = "+";
                                attribute Ipoint : Boolean = false;
                                attribute mass : Real = 0.06647569054015912;
                                attribute sigma_mass : Real = 0.28909372274994966;
                                attribute Cx : Real = -54.38962164334953;
                                attribute sigma_Cx : Real = 28.721044428837228;
                                attribute Cy : Real = 96.47902818396688;
                                attribute sigma_Cy : Real = 28.23690002309109;
                                attribute Cz : Real = 54.403184819966555;
                                attribute sigma_Cz : Real = 29.057750463592832;
                                attribute Ixx : Real = 0.07493053501695036;
                                attribute sigma_Ixx : Real = 0.37074144170588635;
                                attribute Iyy : Real = 0.0696320207792127;
                                attribute sigma_Iyy : Real = 0.3723953238821935;
                                attribute Izz : Real = 0.07371307851929684;
                                attribute sigma_Izz : Real = 0.37017423652493897;
                                attribute Ixy : Real = -0.0013140496659008374;
                                attribute sigma_Ixy : Real = 0.02351283871158888;
                                attribute Ixz : Real = -0.0023899330591866884;
                                attribute sigma_Ixz : Real = 0.022566176940390956;
                                attribute Iyz : Real = 0.006571556739064629;
                                attribute sigma_Iyz : Real = 0.02209918015384651;
                            }
                            part <'C.1.1.4.4.3.4.3'> 'Part 656' {
                                attribute POIconv : String = "+";
                                attribute Ipoint : Boolean = false;
                                attribute mass : Real = 0.8293648636750877;
                                attribute sigma_mass : Real = 0.28909372274994966;
                                attribute Cx : Real = -99.7387720271945;
                                attribute sigma_Cx : Real = 28.721044428837228;
                                attribute Cy : Real = -10.832154704257846;
                                attribute sigma_Cy : Real = 28.23690002309109;
                                attribute Cz : Real = -3.8142846431583166;
                                attribute sigma_Cz : Real = 29.057750463592832;
                                attribute Ixx : Real = 1.1332402498766572;
                                attribute sigma_Ixx : Real = 0.37074144170588635;
                                attribute Iyy : Real = 1.0960864846989586;
                                attribute sigma_Iyy : Real = 0.3723953238821935;
                                attribute Izz : Real = 1.300113932983362;
                                attribute sigma_Izz : Real = 0.37017423652493897;
                                attribute Ixy : Real = -0.005475115002864709;
                                attribute sigma_Ixy : Real = 0.02351283871158888;
                                attribute Ixz : Real = -0.06413935635584692;
                                attribute sigma_Ixz : Real = 0.022566176940390956;
                                attribute Iyz : Real = 0.03647391340973194;
                                attribute sigma_Iyz : Real = 0.02209918015384651;
                            }
                            part <'C.1.1.4.4.3.4.4'> 'Part 657' {
                                attribute POIconv : String = "-";
                                attribute Ipoint : Boolean = false;
                                attribute mass : Real = 0.9732242669011466;
                                attribute sigma_mass : Real = 0.28909372274994966;
                                attribute Cx : Real = 63.64414384588599;
                                attribute sigma_Cx : Real = 28.721044428837228;
                                attribute Cy : Real = 18.035257700830698;
                                attribute sigma_Cy : Real = 28.23690002309109;
                                attribute Cz : Real = 30.359476525336504;
                                attribute sigma_Cz : Real = 29.057750463592832;
                                attribute Ixx : Real = 1.2583666517712888;
                                attribute sigma_Ixx : Real = 0.37074144170588635;
                                attribute Iyy : Real = 1.2702173104602115;
                                attribute sigma_Iyy : Real = 0.3723953238821935;
                                attribute Izz : Real = 1.254563463701605;
                                attribute sigma_Izz : Real = 0.37017423652493897;
                                attribute Ixy : Real = 0.006678955725010968;
                                attribute sigma_Ixy : Real = 0.02351283871158888;
                                attribute Ixz : Real = -0.0027418875649944715;
                                attribute sigma_Ixz : Real = 0.022566176940390956;
                                attribute Iyz : Real = -0.0034297498091773533;
                                attribute sigma_Iyz : Real = 0.02209918015384651;
                            }
                        }
                        part <'C.1.1.4.4.3.5'> 'Subassembly 189' {
                            attribute POIconv : String = "-";
                            attribute Ipoint : Boolean = false;
                            attribute mass : Real = 2.594421026586555;
                            attribute sigma_mass : Real = 0.6464332159373649;
                            attribute Cx : Real = 12.845296081613014;
                            attribute sigma_Cx : Real = 17.898712972085487;
                            attribute Cy : Real = 14.743805968629497;
                            attribute sigma_Cy : Real = 18.89096449566928;
                            attribute Cz : Real = -31.802637580436414;
                            attribute sigma_Cz : Real = 16.1764773712452;
                            attribute Ixx : Real = 5994.391036433018;
                            attribute sigma_Ixx : Real = 4102.482891316973;
                            attribute Iyy : Real = 3671.672795969429;
                            attribute sigma_Iyy : Real = 3208.180771477382;
                            attribute Izz : Real = 6452.312952326113;
                            attribute sigma_Izz : Real = 4891.684715091998;
                            attribute Ixy : Real = 1345.9840798915466;
                            attribute sigma_Ixy : Real = 2337.431183568691;
                            attribute Ixz : Real = -412.9128959029742;
                            attribute sigma_Ixz : Real = 1344.6584121900742;
                            attribute Iyz : Real = 2007.5238173135292;
                            attribute sigma_Iyz : Real = 1875.430687277647;
                            part <'C.1.1.4.4.3.5.1'> 'Part 658' {
                                attribute POIconv : String = "-";
                                attribute Ipoint : Boolean = false;
                                attribute mass : Real = 0.10381324536819012;
                                attribute sigma_mass : Real = 0.28909372274994966;
                                attribute Cx : Real = -64.93578017689288;
                                attribute sigma_Cx : Real = 28.721044428837228;
                                attribute Cy : Real = 77.90709142573178;
                                attribute sigma_Cy : Real = 28.23690002309109;
                                attribute Cz : Real = -41.95287162438035;
                                attribute sigma_Cz : Real = 29.057750463592832;
                                attribute Ixx : Real = 0.12236136238449359;
                                attribute sigma_Ixx : Real = 0.37074144170588635;
                                attribute Iyy : Real = 0.12755863882373125;
                                attribute sigma_Iyy : Real = 0.3723953238821935;
                                attribute Izz : Real = 0.1249036453282957;
                                attribute sigma_Izz : Real = 0.37017423652493897;
                                attribute Ixy : Real = 0.006525911589655946;
                                attribute sigma_Ixy : Real = 0.02351283871158888;
                                attribute Ixz : Real = 0.004752255211857944;
                                attribute sigma_Ixz : Real = 0.022566176940390956;
                                attribute Iyz : Real = 0.00027050919682382237;
                                attribute sigma_Iyz : Real = 0.02209918015384651;
                            }
                            part <'C.1.1.4.4.3.5.2'> 'Part 659' {
                                attribute POIconv : String = "-";
                                attribute Ipoint : Boolean = false;
                                attribute mass : Real = 0.6908058856886345;
                                attribute sigma_mass : Real = 0.28909372274994966;
                                attribute Cx : Real = 18.802362075075507;
                                attribute sigma_Cx : Real = 28.721044428837228;
                                attribute Cy : Real = 58.91342908143997;
                                attribute sigma_Cy : Real = 28.23690002309109;
                                attribute Cz : Real = -39.664994925260544;
                                attribute sigma_Cz : Real = 29.057750463592832;
                                attribute Ixx : Real = 0.760993359139941;
                                attribute sigma_Ixx : Real = 0.37074144170588635;
                                attribute Iyy : Real = 0.8961084879110146;
                                attribute sigma_Iyy : Real = 0.3723953238821935;
                                attribute Izz : Real = 0.8189816995968294;
                                attribute sigma_Izz : Real = 0.37017423652493897;
                                attribute Ixy : Real = -0.04462630736215295;
                                attribute sigma_Ixy : Real = 0.02351283871158888;
                                attribute Ixz : Real = 0.00923851624049183;
                                attribute sigma_Ixz : Real = 0.022566176940390956;
                                attribute Iyz : Real = -0.02284500772779672;
                                attribute sigma_Iyz : Real = 0.02209918015384651;
                            }
                            part <'C.1.1.4.4.3.5.3'> 'Part 660' {
                                attribute POIconv : String = "-";
                                attribute Ipoint : Boolean = false;
                                attribute mass : Real = 0.39716463511041367;
                                attribute sigma_mass : Real = 0.28909372274994966;
                                attribute Cx : Real = 56.3727430999279;
                                attribute sigma_Cx : Real = 28.721044428837228;
                                attribute Cy : Real = -63.765452057123184;
                                attribute sigma_Cy : Real = 28.23690002309109;
                                attribute Cz : Real = 14.837637869641185;
                                attribute sigma_Cz : Real = 29.057750463592832;
                                attribute Ixx : Real = 0.466276944649842;
                                attribute sigma_Ixx : Real = 0.37074144170588635;
                                attribute Iyy : Real = 0.47371364254354675;
                                attribute sigma_Iyy : Real = 0.3723953238821935;
                                attribute Izz : Real = 0.4521836449404636;
                                attribute sigma_Izz : Real = 0.37017423652493897;
                                attribute Ixy : Real = -0.020137304849106787;
                                attribute sigma_Ixy : Real = 0.02351283871158888;
                                attribute Ixz : Real = -0.03105040290991145;
                                attribute sigma_Ixz : Real = 0.022566176940390956;
                                attribute Iyz : Real = -0.03066280443231116;
                                attribute sigma_Iyz : Real = 0.02209918015384651;
                            }
                            part <'C.1.1.4.4.3.5.4'> 'Part 661' {
                                attribute POIconv : String = "-";
                                attribute Ipoint : Boolean = false;
                                attribute mass : Real = 0.9128130629851948;
                                attribute sigma_mass : Real = 0.28909372274994966;
                                attribute Cx : Real = -10.915799252688885;
                                attribute sigma_Cx : Real = 28.721044428837228;
                                attribute Cy : Real = 2.938470523804426;
                                attribute sigma_Cy : Real = 28.23690002309109;
                                attribute Cz : Real = -25.43125026859343;
                                attribute sigma_Cz : Real = 29.057750463592832;
                                attribute Ixx : Real = 1.3367298630637854;
                                attribute sigma_Ixx : Real = 0.37074144170588635;
                                attribute Iyy : Real = 1.2886982065698867;
                                attribute sigma_Iyy : Real = 0.3723953238821935;
                                attribute Izz : Real = 1.2776388207537794;
                                attribute sigma_Izz : Real = 0.37017423652493897;
                                attribute Ixy : Real = 0.004874802984346142;
                                attribute sigma_Ixy : Real = 0.02351283871158888;
                                attribute Ixz : Real = -0.008465364977057556;
                                attribute sigma_Ixz : Real = 0.022566176940390956;
                                attribute Iyz : Real = 0.040751973122049374;
                                attribute sigma_Iyz : Real = 0.02209918015384651;
                            }
                            part <'C.1.1.4.4.3.5.5'> 'Part 662' {
                                attribute POIconv : String = "-";
                                attribute Ipoint : Boolean = false;
                                attribute mass : Real = 0.48982419743412176;
                                attribute sigma_mass : Real = 0.28909372274994966;
                                attribute Cx : Real = 29.91551300510764;
                                attribute sigma_Cx : Real = 28.721044428837228;
                                attribute Cy : Real = 24.721557134762406;
                                attribute sigma_Cy : Real = 28.23690002309109;
                                attribute Cz : Real = -68.25380143709481;
                                attribute sigma_Cz : Real = 29.057750463592832;
                                attribute Ixx : Real = 0.579138393087451;
                                attribute sigma_Ixx : Real = 0.37074144170588635;
                                attribute Iyy : Real = 0.49805813778701313;
                                attribute sigma_Iyy : Real = 0.3723953238821935;
                                attribute Izz : Real = 0.5964203878052231;
                                attribute sigma_Izz : Real = 0.37017423652493897;
                                attribute Ixy : Real = 0.02367105169573768;
                                attribute sigma_Ixy : Real = 0.02351283871158888;
                                attribute Ixz : Real = 0.039714001707232674;
                                attribute sigma_Ixz : Real = 0.022566176940390956;
                                attribute Iyz : Real = -0.024897487731116177;
                                attribute sigma_Iyz : Real = 0.02209918015384651;
                            }
                        }
                    }
                    part <'C.1.1.4.4.4'> 'Assembly 53' {
                        attribute POIconv : String = "-";
                        attribute Ipoint : Boolean = false;
                        attribute mass : Real = 8.387579951894702;
                        attribute sigma_mass : Real = 1.1563748909997986;
                        attribute Cx : Real = 1.1906613055516855;
                        attribute sigma_Cx : Real = 11.112235970813387;
                        attribute Cy : Real = 5.246794004545063;
                        attribute sigma_Cy : Real = 11.690441210918092;
                        attribute Cz : Real = 9.358274692618975;
                        attribute sigma_Cz : Real = 11.250997543404639;
                        attribute Ixx : Real = 51391.51538580838;
                        attribute sigma_Ixx : Real = 13546.986915479582;
                        attribute Iyy : Real = 41775.448509256305;
                        attribute sigma_Iyy : Real = 12589.146055501542;
                        attribute Izz : Real = 46277.61890914175;
                        attribute sigma_Izz : Real = 13288.850245200985;
                        attribute Ixy : Real = 3553.4930096801845;
                        attribute sigma_Ixy : Real = 5955.039026491258;
                        attribute Ixz : Real = 5406.348523321369;
                        attribute sigma_Ixz : Real = 6006.246005805896;
                        attribute Iyz : Real = 961.238724806668;
                        attribute sigma_Iyz : Real = 6213.90302750749;
                        part <'C.1.1.4.4.4.1'> 'Subassembly 190' {
                            attribute POIconv : String = "-";
                            attribute Ipoint : Boolean = false;
                            attribute mass : Real = 2.4554188300801907;
                            attribute sigma_mass : Real = 0.5781874454998993;
                            attribute Cx : Real = 36.56454611712282;
                            attribute sigma_Cx : Real = 20.48146922549101;
                            attribute Cy : Real = -31.05225759795076;
                            attribute sigma_Cy : Real = 16.307715522488657;
                            attribute Cz : Real = 11.668065426785367;
                            attribute sigma_Cz : Real = 18.736883839675425;
                            attribute Ixx : Real = 2932.9816011134876;
                            attribute sigma_Ixx : Real = 2790.1746891037046;
                            attribute Iyy : Real = 3880.091535066438;
                            attribute sigma_Iyy : Real = 4651.943549942527;
                            attribute Izz : Real = 1754.3327906321688;
                            attribute sigma_Izz : Real = 3431.4421712083026;
                            attribute Ixy : Real = 304.0351934129984;
                            attribute sigma_Ixy : Real = 794.0278835141401;
                            attribute Ixz : Real = 414.72686845116766;
                            attribute sigma_Ixz : Real = 1950.9447855128342;
                            attribute Iyz : Real = -493.9848432932715;
                            attribute sigma_Iyz : Real = 1277.676556773551;
                            part <'C.1.1.4.4.4.1.1'> 'Part 663' {
                                attribute POIconv : String = "+";
                                attribute Ipoint : Boolean = false;
                                attribute mass : Real = 0.7460370842069387;
                                attribute sigma_mass : Real = 0.28909372274994966;
                                attribute Cx : Real = 44.681803649291396;
                                attribute sigma_Cx : Real = 28.721044428837228;
                                attribute Cy : Real = -49.046736769378185;
                                attribute sigma_Cy : Real = 28.23690002309109;
                                attribute Cz : Real = 3.6335147451609373;
                                attribute sigma_Cz : Real = 29.057750463592832;
                                attribute Ixx : Real = 0.8206288609790491;
                                attribute sigma_Ixx : Real = 0.37074144170588635;
                                attribute Iyy : Real = 0.8240987708061448;
                                attribute sigma_Iyy : Real = 0.3723953238821935;
                                attribute Izz : Real = 0.9662463239274194;
                                attribute sigma_Izz : Real = 0.37017423652493897;
                                attribute Ixy : Real = -0.036969133585519925;
                                attribute sigma_Ixy : Real = 0.02351283871158888;
                                attribute Ixz : Real = -0.05189924401597873;
                                attribute sigma_Ixz : Real = 0.022566176940390956;
                                attribute Iyz : Real = -0.02170383463928574;
                                attribute sigma_Iyz : Real = 0.02209918015384651;
                            }
                            part <'C.1.1.4.4.4.1.2'> 'Part 664' {
                                attribute POIconv : String = "-";
                                attribute Ipoint : Boolean = false;
                                attribute mass : Real = 0.9950239433427341;
                                attribute sigma_mass : Real = 0.28909372274994966;
                                attribute Cx : Real = 49.79861541651189;
                                attribute sigma_Cx : Real = 28.721044428837228;
                                attribute Cy : Real = -27.88475281558931;
                                attribute sigma_Cy : Real = 28.23690002309109;
                                attribute Cz : Real = -11.094320099800825;
                                attribute sigma_Cz : Real = 29.057750463592832;
                                attribute Ixx : Real = 1.1398798164841484;
                                attribute sigma_Ixx : Real = 0.37074144170588635;
                                attribute Iyy : Real = 1.0205937981087359;
                                attribute sigma_Iyy : Real = 0.3723953238821935;
                                attribute Izz : Real = 1.262935207341279;
                                attribute sigma_Izz : Real = 0.37017423652493897;
                                attribute Ixy : Real = 0.04350959382729905;
                                attribute sigma_Ixy : Real = 0.02351283871158888;
                                attribute Ixz : Real = -0.01999228933925175;
                                attribute sigma_Ixz : Real = 0.022566176940390956;
                                attribute Iyz : Real = 0.05508174998057035;
                                attribute sigma_Iyz : Real = 0.02209918015384651;
                            }
                            part <'C.1.1.4.4.4.1.3'> 'Part 665' {
                                attribute POIconv : String = "+";
                                attribute Ipoint : Boolean = false;
                                attribute mass : Real = 0.6226469260763843;
                                attribute sigma_mass : Real = 0.28909372274994966;
                                attribute Cx : Real = 20.853755017742515;
                                attribute sigma_Cx : Real = 28.721044428837228;
                                attribute Cy : Real = -15.939851617440581;
                                attribute sigma_Cy : Real = 28.23690002309109;
                                attribute Cz : Real = 64.73429212346673;
                                attribute sigma_Cz : Real = 29.057750463592832;
                                attribute Ixx : Real = 0.975527632148426;
                                attribute sigma_Ixx : Real = 0.37074144170588635;
                                attribute Iyy : Real = 0.9603041646391267;
                                attribute sigma_Iyy : Real = 0.3723953238821935;
                                attribute Izz : Real = 0.9593930517425237;
                                attribute sigma_Izz : Real = 0.37017423652493897;
                                attribute Ixy : Real = -0.004335460860332886;
                                attribute sigma_Ixy : Real = 0.02351283871158888;
                                attribute Ixz : Real = -0.004265222686083687;
                                attribute sigma_Ixz : Real = 0.022566176940390956;
                                attribute Iyz : Real = -0.0009275286369879559;
                                attribute sigma_Iyz : Real = 0.02209918015384651;
                            }
                            part <'C.1.1.4.4.4.1.4'> 'Part 666' {
                                attribute POIconv : String = "-";
                                attribute Ipoint : Boolean = false;
                                attribute mass : Real = 0.09171087645413355;
                                attribute sigma_mass : Real = 0.28909372274994966;
                                attribute Cx : Real = -66.38633105903864;
                                attribute sigma_Cx : Real = 28.721044428837228;
                                attribute Cy : Real = -21.641023317351937;
                                attribute sigma_Cy : Real = 28.23690002309109;
                                attribute Cz : Real = -36.29060350358486;
                                attribute sigma_Cz : Real = 29.057750463592832;
                                attribute Ixx : Real = 0.13385867241431623;
                                attribute sigma_Ixx : Real = 0.37074144170588635;
                                attribute Iyy : Real = 0.10629591196262331;
                                attribute sigma_Iyy : Real = 0.3723953238821935;
                                attribute Izz : Real = 0.12171634469903274;
                                attribute sigma_Izz : Real = 0.37017423652493897;
                                attribute Ixy : Real = -0.0016704420589676394;
                                attribute sigma_Ixy : Real = 0.02351283871158888;
                                attribute Ixz : Real = -0.0011132647127876506;
                                attribute sigma_Ixz : Real = 0.022566176940390956;
                                attribute Iyz : Real = -0.00035043140685179694;
                                attribute sigma_Iyz : Real = 0.02209918015384651;
                            }
                        }
                        part <'C.1.1.4.4.4.2'> 'Subassembly 191' {
                            attribute POIconv : String = "-";
                            attribute Ipoint : Boolean = false;
                            attribute mass : Real = 2.2626211789138617;
                            attribute sigma_mass : Real = 0.5781874454998993;
                            attribute Cx : Real = -4.449863220281455;
                            attribute sigma_Cx : Real = 21.090621509461023;
                            attribute Cy : Real = -32.844342274219684;
                            attribute sigma_Cy : Real = 17.563118425539795;
                            attribute Cz : Real = 4.099451954283284;
                            attribute sigma_Cz : Real = 20.881400089689887;
                            attribute Ixx : Real = 8052.078145132491;
                            attribute sigma_Ixx : Real = 4867.304429114193;
                            attribute Iyy : Real = 12015.469944820472;
                            attribute sigma_Iyy : Real = 6392.558025571144;
                            attribute Izz : Real = 6997.743275625113;
                            attribute sigma_Izz : Real = 4382.352839551211;
                            attribute Ixy : Real = 585.6629557310794;
                            attribute sigma_Ixy : Real = 2017.6096517879805;
                            attribute Ixz : Real = 5458.033110364166;
                            attribute sigma_Ixz : Real = 3165.7820203336382;
                            attribute Iyz : Real = 390.8385021640329;
                            attribute sigma_Iyz : Real = 2233.6073353633706;
                            part <'C.1.1.4.4.4.2.1'> 'Part 667' {
                                attribute POIconv : String = "-";
                                attribute Ipoint : Boolean = false;
                                attribute mass : Real = 0.41442017414723525;
                                attribute sigma_mass : Real = 0.28909372274994966;
                                attribute Cx : Real = -41.24772152863443;
                                attribute sigma_Cx : Real = 28.721044428837228;
                                attribute Cy : Real = 16.03273069486022;
                                attribute sigma_Cy : Real = 28.23690002309109;
                                attribute Cz : Real = -1.5365771483629942;
                                attribute sigma_Cz : Real = 29.057750463592832;
                                attribute Ixx : Real = 0.463646018585574;
                                attribute sigma_Ixx : Real = 0.37074144170588635;
                                attribute Iyy : Real = 0.48390182259333736;
                                attribute sigma_Iyy : Real = 0.3723953238821935;
                                attribute Izz : Real = 0.4555758053168145;
                                attribute sigma_Izz : Real = 0.37017423652493897;
                                attribute Ixy : Real = 0.006764826690762742;
                                attribute sigma_Ixy : Real = 0.02351283871158888;
                                attribute Ixz : Real = -0.0028519594962106007;
                                attribute sigma_Ixz : Real = 0.022566176940390956;
                                attribute Iyz : Real = -0.007359256057349441;
                                attribute sigma_Iyz : Real = 0.02209918015384651;
                            }
                            part <'C.1.1.4.4.4.2.2'> 'Part 668' {
                                attribute POIconv : String = "-";
                                attribute Ipoint : Boolean = false;
                                attribute mass : Real = 0.9810561304318253;
                                attribute sigma_mass : Real = 0.28909372274994966;
                                attribute Cx : Real = -44.00698612444103;
                                attribute sigma_Cx : Real = 28.721044428837228;
                                attribute Cy : Real = -46.46273930557072;
                                attribute sigma_Cy : Real = 28.23690002309109;
                                attribute Cz : Real = 61.14027970470488;
                                attribute sigma_Cz : Real = 29.057750463592832;
                                attribute Ixx : Real = 1.2464724267746063;
                                attribute sigma_Ixx : Real = 0.37074144170588635;
                                attribute Iyy : Real = 1.3615500195266517;
                                attribute sigma_Iyy : Real = 0.3723953238821935;
                                attribute Izz : Real = 1.3210414589125157;
                                attribute sigma_Izz : Real = 0.37017423652493897;
                                attribute Ixy : Real = -0.008427737691065963;
                                attribute sigma_Ixy : Real = 0.02351283871158888;
                                attribute Ixz : Real = -0.07381658708078295;
                                attribute sigma_Ixz : Real = 0.022566176940390956;
                                attribute Iyz : Real = 0.04457754242755761;
                                attribute sigma_Iyz : Real = 0.02209918015384651;
                            }
                            part <'C.1.1.4.4.4.2.3'> 'Part 669' {
                                attribute POIconv : String = "+";
                                attribute Ipoint : Boolean = false;
                                attribute mass : Real = 0.2073239594688639;
                                attribute sigma_mass : Real = 0.28909372274994966;
                                attribute Cx : Real = 64.76589371450245;
                                attribute sigma_Cx : Real = 28.721044428837228;
                                attribute Cy : Real = -8.22969856671989;
                                attribute sigma_Cy : Real = 28.23690002309109;
                                attribute Cz : Real = -51.083578588441014;
                                attribute sigma_Cz : Real = 29.057750463592832;
                                attribute Ixx : Real = 0.2919851755944372;
                                attribute sigma_Ixx : Real = 0.37074144170588635;
                                attribute Iyy : Real = 0.24887200044581698;
                                attribute sigma_Iyy : Real = 0.3723953238821935;
                                attribute Izz : Real = 0.25149728812355837;
                                attribute sigma_Izz : Real = 0.37017423652493897;
                                attribute Ixy : Real = 0.0028152252170847198;
                                attribute sigma_Ixy : Real = 0.02351283871158888;
                                attribute Ixz : Real = 0.020272005236701897;
                                attribute sigma_Ixz : Real = 0.022566176940390956;
                                attribute Iyz : Real = -0.009147478898857185;
                                attribute sigma_Iyz : Real = 0.02209918015384651;
                            }
                            part <'C.1.1.4.4.4.2.4'> 'Part 670' {
                                attribute POIconv : String = "+";
                                attribute Ipoint : Boolean = false;
                                attribute mass : Real = 0.6598209148659371;
                                attribute sigma_mass : Real = 0.28909372274994966;
                                attribute Cx : Real = 55.72926583699882;
                                attribute sigma_Cx : Real = 28.721044428837228;
                                attribute Cy : Real = -51.02872885763645;
                                attribute sigma_Cy : Real = 28.23690002309109;
                                attribute Cz : Real = -59.8327518440783;
                                attribute sigma_Cz : Real = 29.057750463592832;
                                attribute Ixx : Real = 0.8713158024680474;
                                attribute sigma_Ixx : Real = 0.37074144170588635;
                                attribute Iyy : Real = 0.8588387056584211;
                                attribute sigma_Iyy : Real = 0.3723953238821935;
                                attribute Izz : Real = 0.8393741958348306;
                                attribute sigma_Izz : Real = 0.37017423652493897;
                                attribute Ixy : Real = 0.030829142776857887;
                                attribute sigma_Ixy : Real = 0.02351283871158888;
                                attribute Ixz : Real = 0.014233781497328632;
                                attribute sigma_Ixz : Real = 0.022566176940390956;
                                attribute Iyz : Real = -0.018059801260491077;
                                attribute sigma_Iyz : Real = 0.02209918015384651;
                            }
                        }
                        part <'C.1.1.4.4.4.3'> 'Subassembly 192' {
                            attribute POIconv : String = "-";
                            attribute Ipoint : Boolean = false;
                            attribute mass : Real = 2.2067520453059113;
                            attribute sigma_mass : Real = 0.5781874454998993;
                            attribute Cx : Real = -15.777166214226773;
                            attribute sigma_Cx : Real = 19.013811020084795;
                            attribute Cy : Real = 71.4568396910071;
                            attribute sigma_Cy : Real = 21.24449471130994;
                            attribute Cz : Real = 15.28055427962881;
                            attribute sigma_Cz : Real = 22.22824749909941;
                            attribute Ixx : Real = 11321.319506490254;
                            attribute sigma_Ixx : Real = 6615.854696534671;
                            attribute Iyy : Real = 11321.329419559412;
                            attribute sigma_Iyy : Real = 6048.418338907845;
                            attribute Izz : Real = 6009.901006956008;
                            attribute sigma_Izz : Real = 5349.786857033957;
                            attribute Ixy : Real = -1991.328719779819;
                            attribute sigma_Ixy : Real = 2400.3984678752654;
                            attribute Ixz : Real = 4326.740899974342;
                            attribute sigma_Ixz : Real = 2872.8103933650623;
                            attribute Iyz : Real = 2121.014274409262;
                            attribute sigma_Iyz : Real = 2804.4504990333016;
                            part <'C.1.1.4.4.4.3.1'> 'Part 671' {
                                attribute POIconv : String = "-";
                                attribute Ipoint : Boolean = false;
                                attribute mass : Real = 0.9395295278353151;
                                attribute sigma_mass : Real = 0.28909372274994966;
                                attribute Cx : Real = 24.310704972594976;
                                attribute sigma_Cx : Real = 28.721044428837228;
                                attribute Cy : Real = 89.07412635162473;
                                attribute sigma_Cy : Real = 28.23690002309109;
                                attribute Cz : Real = -39.38687336631119;
                                attribute sigma_Cz : Real = 29.057750463592832;
                                attribute Ixx : Real = 1.1011973142032485;
                                attribute sigma_Ixx : Real = 0.37074144170588635;
                                attribute Iyy : Real = 1.014959160470996;
                                attribute sigma_Iyy : Real = 0.3723953238821935;
                                attribute Izz : Real = 1.0358922164723334;
                                attribute sigma_Izz : Real = 0.37017423652493897;
                                attribute Ixy : Real = -0.016391674255517817;
                                attribute sigma_Ixy : Real = 0.02351283871158888;
                                attribute Ixz : Real = 0.07970686107997438;
                                attribute sigma_Ixz : Real = 0.022566176940390956;
                                attribute Iyz : Real = -0.01540563887548016;
                                attribute sigma_Iyz : Real = 0.02209918015384651;
                            }
                            part <'C.1.1.4.4.4.3.2'> 'Part 672' {
                                attribute POIconv : String = "-";
                                attribute Ipoint : Boolean = false;
                                attribute mass : Real = 0.22989934752346017;
                                attribute sigma_mass : Real = 0.28909372274994966;
                                attribute Cx : Real = -74.94536084122956;
                                attribute sigma_Cx : Real = 28.721044428837228;
                                attribute Cy : Real = -35.33804030157626;
                                attribute sigma_Cy : Real = 28.23690002309109;
                                attribute Cz : Real = 64.7656999528408;
                                attribute sigma_Cz : Real = 29.057750463592832;
                                attribute Ixx : Real = 0.31644585538757936;
                                attribute sigma_Ixx : Real = 0.37074144170588635;
                                attribute Iyy : Real = 0.2935569695992459;
                                attribute sigma_Iyy : Real = 0.3723953238821935;
                                attribute Izz : Real = 0.2854106723993982;
                                attribute sigma_Izz : Real = 0.37017423652493897;
                                attribute Ixy : Real = 0.008772669929748275;
                                attribute sigma_Ixy : Real = 0.02351283871158888;
                                attribute Ixz : Real = 0.007897311757948057;
                                attribute sigma_Ixz : Real = 0.022566176940390956;
                                attribute Iyz : Real = 0.012721215288910126;
                                attribute sigma_Iyz : Real = 0.02209918015384651;
                            }
                            part <'C.1.1.4.4.4.3.3'> 'Part 673' {
                                attribute POIconv : String = "+";
                                attribute Ipoint : Boolean = false;
                                attribute mass : Real = 0.6448374005705119;
                                attribute sigma_mass : Real = 0.28909372274994966;
                                attribute Cx : Real = -47.73186882957816;
                                attribute sigma_Cx : Real = 28.721044428837228;
                                attribute Cy : Real = 75.10412405245006;
                                attribute sigma_Cy : Real = 28.23690002309109;
                                attribute Cz : Real = 98.51210243068635;
                                attribute sigma_Cz : Real = 29.057750463592832;
                                attribute Ixx : Real = 0.768810610390486;
                                attribute sigma_Ixx : Real = 0.37074144170588635;
                                attribute Iyy : Real = 0.7855635358213313;
                                attribute sigma_Iyy : Real = 0.3723953238821935;
                                attribute Izz : Real = 0.9019277139768106;
                                attribute sigma_Izz : Real = 0.37017423652493897;
                                attribute Ixy : Real = -0.039190964060222155;
                                attribute sigma_Ixy : Real = 0.02351283871158888;
                                attribute Ixz : Real = 0.0047140026305167206;
                                attribute sigma_Ixz : Real = 0.022566176940390956;
                                attribute Iyz : Real = 0.006334708608366373;
                                attribute sigma_Iyz : Real = 0.02209918015384651;
                            }
                            part <'C.1.1.4.4.4.3.4'> 'Part 674' {
                                attribute POIconv : String = "+";
                                attribute Ipoint : Boolean = false;
                                attribute mass : Real = 0.3924857693766244;
                                attribute sigma_mass : Real = 0.28909372274994966;
                                attribute Cx : Real = -24.58110828883946;
                                attribute sigma_Cx : Real = 28.721044428837228;
                                attribute Cy : Real = 85.84769736044109;
                                attribute sigma_Cy : Real = 28.23690002309109;
                                attribute Cz : Real = -19.588876515626907;
                                attribute sigma_Cz : Real = 29.057750463592832;
                                attribute Ixx : Real = 0.5337427465100959;
                                attribute sigma_Ixx : Real = 0.37074144170588635;
                                attribute Iyy : Real = 0.5582009971030575;
                                attribute sigma_Iyy : Real = 0.3723953238821935;
                                attribute Izz : Real = 0.6060182738584219;
                                attribute sigma_Izz : Real = 0.37017423652493897;
                                attribute Ixy : Real = 0.006485700900252028;
                                attribute sigma_Ixy : Real = 0.02351283871158888;
                                attribute Ixz : Real = 0.0010825429017011516;
                                attribute sigma_Ixz : Real = 0.022566176940390956;
                                attribute Iyz : Real = -0.010208972786856608;
                                attribute sigma_Iyz : Real = 0.02209918015384651;
                            }
                        }
                        part <'C.1.1.4.4.4.4'> 'Subassembly 193' {
                            attribute POIconv : String = "-";
                            attribute Ipoint : Boolean = false;
                            attribute mass : Real = 1.4627878975947386;
                            attribute sigma_mass : Real = 0.5781874454998993;
                            attribute Cx : Real = -23.86529149777912;
                            attribute sigma_Cx : Real = 25.443098010147466;
                            attribute Cy : Real = 25.212800560706455;
                            attribute sigma_Cy : Real = 28.269302167202188;
                            attribute Cz : Real = 4.681053503503237;
                            attribute sigma_Cz : Real = 31.479234372290126;
                            attribute Ixx : Real = 12124.815190853598;
                            attribute sigma_Ixx : Real = 6377.751294262311;
                            attribute Iyy : Real = 9675.325580845747;
                            attribute sigma_Iyy : Real = 6278.762687568681;
                            attribute Izz : Real = 10042.233030670988;
                            attribute sigma_Izz : Real = 5391.424956101639;
                            attribute Ixy : Real = -1222.5353712726348;
                            attribute sigma_Ixy : Real = 2292.978109439845;
                            attribute Ixz : Real = -4575.739396504103;
                            attribute sigma_Ixz : Real = 3011.823234366014;
                            attribute Iyz : Real = -80.56732300801036;
                            attribute sigma_Iyz : Real = 2543.3181886547964;
                            part <'C.1.1.4.4.4.4.1'> 'Part 675' {
                                attribute POIconv : String = "-";
                                attribute Ipoint : Boolean = false;
                                attribute mass : Real = 0.10299141077185049;
                                attribute sigma_mass : Real = 0.28909372274994966;
                                attribute Cx : Real = -76.77513929083943;
                                attribute sigma_Cx : Real = 28.721044428837228;
                                attribute Cy : Real = 52.76911025866866;
                                attribute sigma_Cy : Real = 28.23690002309109;
                                attribute Cz : Real = -85.07573287934065;
                                attribute sigma_Cz : Real = 29.057750463592832;
                                attribute Ixx : Real = 0.1406659143728044;
                                attribute sigma_Ixx : Real = 0.37074144170588635;
                                attribute Iyy : Real = 0.13552328218473658;
                                attribute sigma_Iyy : Real = 0.3723953238821935;
                                attribute Izz : Real = 0.15570786129877726;
                                attribute sigma_Izz : Real = 0.37017423652493897;
                                attribute Ixy : Real = -0.001132016907031185;
                                attribute sigma_Ixy : Real = 0.02351283871158888;
                                attribute Ixz : Real = -0.0035682786936119615;
                                attribute sigma_Ixz : Real = 0.022566176940390956;
                                attribute Iyz : Real = 0.003297623686421914;
                                attribute sigma_Iyz : Real = 0.02209918015384651;
                            }
                            part <'C.1.1.4.4.4.4.2'> 'Part 676' {
                                attribute POIconv : String = "-";
                                attribute Ipoint : Boolean = false;
                                attribute mass : Real = 0.43510476969531736;
                                attribute sigma_mass : Real = 0.28909372274994966;
                                attribute Cx : Real = -55.80467330291867;
                                attribute sigma_Cx : Real = 28.721044428837228;
                                attribute Cy : Real = 90.63829854130745;
                                attribute sigma_Cy : Real = 28.23690002309109;
                                attribute Cz : Real = -48.55994042009115;
                                attribute sigma_Cz : Real = 29.057750463592832;
                                attribute Ixx : Real = 0.6700441178951808;
                                attribute sigma_Ixx : Real = 0.37074144170588635;
                                attribute Iyy : Real = 0.608833254600094;
                                attribute sigma_Iyy : Real = 0.3723953238821935;
                                attribute Izz : Real = 0.5718316124111003;
                                attribute sigma_Izz : Real = 0.37017423652493897;
                                attribute Ixy : Real = 0.014189034826263084;
                                attribute sigma_Ixy : Real = 0.02351283871158888;
                                attribute Ixz : Real = 0.00031911920674320034;
                                attribute sigma_Ixz : Real = 0.022566176940390956;
                                attribute Iyz : Real = 0.00031245873823186523;
                                attribute sigma_Iyz : Real = 0.02209918015384651;
                            }
                            part <'C.1.1.4.4.4.4.3'> 'Part 677' {
                                attribute POIconv : String = "+";
                                attribute Ipoint : Boolean = false;
                                attribute mass : Real = 0.46932102445862256;
                                attribute sigma_mass : Real = 0.28909372274994966;
                                attribute Cx : Real = 49.872670974582434;
                                attribute sigma_Cx : Real = 28.721044428837228;
                                attribute Cy : Real = 49.70479113981128;
                                attribute sigma_Cy : Real = 28.23690002309109;
                                attribute Cz : Real = 92.74870436638594;
                                attribute sigma_Cz : Real = 29.057750463592832;
                                attribute Ixx : Real = 0.6086401932176692;
                                attribute sigma_Ixx : Real = 0.37074144170588635;
                                attribute Iyy : Real = 0.6293695796310088;
                                attribute sigma_Iyy : Real = 0.3723953238821935;
                                attribute Izz : Real = 0.5882568806472014;
                                attribute sigma_Izz : Real = 0.37017423652493897;
                                attribute Ixy : Real = 0.023473516841990366;
                                attribute sigma_Ixy : Real = 0.02351283871158888;
                                attribute Ixz : Real = -0.016705590820211773;
                                attribute sigma_Ixz : Real = 0.022566176940390956;
                                attribute Iyz : Real = 0.006308390406972531;
                                attribute sigma_Iyz : Real = 0.02209918015384651;
                            }
                            part <'C.1.1.4.4.4.4.4'> 'Part 678' {
                                attribute POIconv : String = "-";
                                attribute Ipoint : Boolean = false;
                                attribute mass : Real = 0.4553706926689483;
                                attribute sigma_mass : Real = 0.28909372274994966;
                                attribute Cx : Real = -57.37763452343643;
                                attribute sigma_Cx : Real = 28.721044428837228;
                                attribute Cy : Real = -68.77571525983512;
                                attribute sigma_Cy : Real = 28.23690002309109;
                                attribute Cz : Real = -14.912679279223084;
                                attribute sigma_Cz : Real = 29.057750463592832;
                                attribute Ixx : Real = 0.614334864629171;
                                attribute sigma_Ixx : Real = 0.37074144170588635;
                                attribute Iyy : Real = 0.609213258947741;
                                attribute sigma_Iyy : Real = 0.3723953238821935;
                                attribute Izz : Real = 0.618478745264341;
                                attribute sigma_Izz : Real = 0.37017423652493897;
                                attribute Ixy : Real = 0.0011198755793584724;
                                attribute sigma_Ixy : Real = 0.02351283871158888;
                                attribute Ixz : Real = -0.007517029843743193;
                                attribute sigma_Ixz : Real = 0.022566176940390956;
                                attribute Iyz : Real = -0.0013814228023789456;
                                attribute sigma_Iyz : Real = 0.02209918015384651;
                            }
                        }
                    }
                }
                part <'C.1.1.4.5'> 'Subsystem 15' {
                    attribute POIconv : String = "-";
                    attribute Ipoint : Boolean = false;
                    attribute mass : Real = 25.6566409030722;
                    attribute sigma_mass : Real = 2.0846844815794277;
                    attribute Cx : Real = -4.908875950482082;
                    attribute sigma_Cx : Real = 7.3501702389741395;
                    attribute Cy : Real = -12.655455031927337;
                    attribute sigma_Cy : Real = 6.836558956933618;
                    attribute Cz : Real = -8.132761066545578;
                    attribute sigma_Cz : Real = 6.817959187544644;
                    attribute Ixx : Real = 155078.54860240017;
                    attribute sigma_Ixx : Real = 26478.62432275875;
                    attribute Iyy : Real = 172073.77082100871;
                    attribute sigma_Iyy : Real = 28744.491765709543;
                    attribute Izz : Real = 173585.08383660056;
                    attribute sigma_Izz : Real = 29635.836168792852;
                    attribute Ixy : Real = -15079.336049990268;
                    attribute sigma_Ixy : Real = 13453.710162668243;
                    attribute Ixz : Real = -8666.568198590105;
                    attribute sigma_Ixz : Real = 12591.723274507554;
                    attribute Iyz : Real = -29701.266236276388;
                    attribute sigma_Iyz : Real = 12521.845041522427;
                    part <'C.1.1.4.5.1'> 'Assembly 54' {
                        attribute POIconv : String = "-";
                        attribute Ipoint : Boolean = false;
                        attribute mass : Real = 2.9915554821889385;
                        attribute sigma_mass : Real = 0.9141946211470771;
                        attribute Cx : Real = 24.887584423472052;
                        attribute sigma_Cx : Real = 19.742474598433297;
                        attribute Cy : Real = -33.39921799335833;
                        attribute sigma_Cy : Real = 19.405422352393995;
                        attribute Cz : Real = -8.380197700234685;
                        attribute sigma_Cz : Real = 20.63849804757253;
                        attribute Ixx : Real = 11683.665621220307;
                        attribute sigma_Ixx : Real = 7196.383121118784;
                        attribute Iyy : Real = 15987.705300966274;
                        attribute sigma_Iyy : Real = 7796.90293469389;
                        attribute Izz : Real = 15313.47535125555;
                        attribute sigma_Izz : Real = 7574.530830083124;
                        attribute Ixy : Real = -1514.1678695937742;
                        attribute sigma_Ixy : Real = 3435.121193222487;
                        attribute Ixz : Real = -1732.8036310897992;
                        attribute sigma_Ixz : Real = 3293.8894032496255;
                        attribute Iyz : Real = -1214.7439978764144;
                        attribute sigma_Iyz : Real = 2757.2940133652855;
                        part <'C.1.1.4.5.1.1'> 'Subassembly 194' {
                            attribute POIconv : String = "-";
                            attribute Ipoint : Boolean = false;
                            attribute mass : Real = 1.897704235614976;
                            attribute sigma_mass : Real = 0.6464332159373649;
                            attribute Cx : Real = 18.103515552294386;
                            attribute sigma_Cx : Real = 23.562942692667317;
                            attribute Cy : Real = -20.973372134427624;
                            attribute sigma_Cy : Real = 23.79821228578079;
                            attribute Cz : Real = 5.144128930109264;
                            attribute sigma_Cz : Real = 25.42839941268859;
                            attribute Ixx : Real = 8061.871844982807;
                            attribute sigma_Ixx : Real = 5613.171410989859;
                            attribute Iyy : Real = 11332.585957237936;
                            attribute sigma_Iyy : Real = 6343.521038436811;
                            attribute Izz : Real = 10541.675870723258;
                            attribute sigma_Izz : Real = 5925.3985008023255;
                            attribute Ixy : Real = -2098.7587730306095;
                            attribute sigma_Ixy : Real = 2527.5661127897515;
                            attribute Ixz : Real = -1703.489399847324;
                            attribute sigma_Ixz : Real = 2841.869343813472;
                            attribute Iyz : Real = -152.50323625393523;
                            attribute sigma_Iyz : Real = 2104.4861536799044;
                            part <'C.1.1.4.5.1.1.1'> 'Part 679' {
                                attribute POIconv : String = "-";
                                attribute Ipoint : Boolean = false;
                                attribute mass : Real = 0.5458585424774792;
                                attribute sigma_mass : Real = 0.28909372274994966;
                                attribute Cx : Real = 85.50647832453251;
                                attribute sigma_Cx : Real = 28.721044428837228;
                                attribute Cy : Real = -29.775803722441196;
                                attribute sigma_Cy : Real = 28.23690002309109;
                                attribute Cz : Real = 63.13854418694973;
                                attribute sigma_Cz : Real = 29.057750463592832;
                                attribute Ixx : Real = 0.4978284865589333;
                                attribute sigma_Ixx : Real = 0.37074144170588635;
                                attribute Iyy : Real = 0.68768193544253;
                                attribute sigma_Iyy : Real = 0.3723953238821935;
                                attribute Izz : Real = 0.6788463951038252;
                                attribute sigma_Izz : Real = 0.37017423652493897;
                                attribute Ixy : Real = 0.0262114329089291;
                                attribute sigma_Ixy : Real = 0.02351283871158888;
                                attribute Ixz : Real = -0.045881555638085866;
                                attribute sigma_Ixz : Real = 0.022566176940390956;
                                attribute Iyz : Real = 0.00793722402940337;
                                attribute sigma_Iyz : Real = 0.02209918015384651;
                            }
                            part <'C.1.1.4.5.1.1.2'> 'Part 680' {
                                attribute POIconv : String = "-";
                                attribute Ipoint : Boolean = false;
                                attribute mass : Real = 0.21352396419341677;
                                attribute sigma_mass : Real = 0.28909372274994966;
                                attribute Cx : Real = 16.390314605087042;
                                attribute sigma_Cx : Real = 28.721044428837228;
                                attribute Cy : Real = 72.85699057392776;
                                attribute sigma_Cy : Real = 28.23690002309109;
                                attribute Cz : Real = 35.691239358857274;
                                attribute sigma_Cz : Real = 29.057750463592832;
                                attribute Ixx : Real = 0.29291505594957146;
                                attribute sigma_Ixx : Real = 0.37074144170588635;
                                attribute Iyy : Real = 0.2901555971237649;
                                attribute sigma_Iyy : Real = 0.3723953238821935;
                                attribute Izz : Real = 0.3034414030770064;
                                attribute sigma_Izz : Real = 0.37017423652493897;
                                attribute Ixy : Real = -0.005479785696470594;
                                attribute sigma_Ixy : Real = 0.02351283871158888;
                                attribute Ixz : Real = 0.0028228698849508942;
                                attribute sigma_Ixz : Real = 0.022566176940390956;
                                attribute Iyz : Real = -0.0007937649056078236;
                                attribute sigma_Iyz : Real = 0.02209918015384651;
                            }
                            part <'C.1.1.4.5.1.1.3'> 'Part 681' {
                                attribute POIconv : String = "+";
                                attribute Ipoint : Boolean = false;
                                attribute mass : Real = 0.18561021326552146;
                                attribute sigma_mass : Real = 0.28909372274994966;
                                attribute Cx : Real = 80.37407421506941;
                                attribute sigma_Cx : Real = 28.721044428837228;
                                attribute Cy : Real = 46.43285432830453;
                                attribute sigma_Cy : Real = 28.23690002309109;
                                attribute Cz : Real = -53.399051539599895;
                                attribute sigma_Cz : Real = 29.057750463592832;
                                attribute Ixx : Real = 0.20761213110324594;
                                attribute sigma_Ixx : Real = 0.37074144170588635;
                                attribute Iyy : Real = 0.23129726548037075;
                                attribute sigma_Iyy : Real = 0.3723953238821935;
                                attribute Izz : Real = 0.233063851590576;
                                attribute sigma_Izz : Real = 0.37017423652493897;
                                attribute Ixy : Real = -0.015489894223154296;
                                attribute sigma_Ixy : Real = 0.02351283871158888;
                                attribute Ixz : Real = -0.021740293077604673;
                                attribute sigma_Ixz : Real = 0.022566176940390956;
                                attribute Iyz : Real = 0.011055316450912936;
                                attribute sigma_Iyz : Real = 0.02209918015384651;
                            }
                            part <'C.1.1.4.5.1.1.4'> 'Part 682' {
                                attribute POIconv : String = "+";
                                attribute Ipoint : Boolean = false;
                                attribute mass : Real = 0.16669526490941644;
                                attribute sigma_mass : Real = 0.28909372274994966;
                                attribute Cx : Real = 47.57193187251687;
                                attribute sigma_Cx : Real = 28.721044428837228;
                                attribute Cy : Real = -32.69286481663585;
                                attribute sigma_Cy : Real = 28.23690002309109;
                                attribute Cz : Real = -92.84564526751637;
                                attribute sigma_Cz : Real = 29.057750463592832;
                                attribute Ixx : Real = 0.23316409424887946;
                                attribute sigma_Ixx : Real = 0.37074144170588635;
                                attribute Iyy : Real = 0.24638327040536862;
                                attribute sigma_Iyy : Real = 0.3723953238821935;
                                attribute Izz : Real = 0.2407007462312049;
                                attribute sigma_Izz : Real = 0.37017423652493897;
                                attribute Ixy : Real = -7.4615259516791e-05;
                                attribute sigma_Ixy : Real = 0.02351283871158888;
                                attribute Ixz : Real = -0.008670388867699982;
                                attribute sigma_Ixz : Real = 0.022566176940390956;
                                attribute Iyz : Real = -7.968590087718936e-05;
                                attribute sigma_Iyz : Real = 0.02209918015384651;
                            }
                            part <'C.1.1.4.5.1.1.5'> 'Part 683' {
                                attribute POIconv : String = "+";
                                attribute Ipoint : Boolean = false;
                                attribute mass : Real = 0.786016250769142;
                                attribute sigma_mass : Real = 0.28909372274994966;
                                attribute Cx : Real = -49.19403796084225;
                                attribute sigma_Cx : Real = 28.721044428837228;
                                attribute Cy : Real = -53.781661577522755;
                                attribute sigma_Cy : Real = 28.23690002309109;
                                attribute Cz : Real = -8.823322132229805;
                                attribute sigma_Cz : Real = 29.057750463592832;
                                attribute Ixx : Real = 0.9099732314839822;
                                attribute sigma_Ixx : Real = 0.37074144170588635;
                                attribute Iyy : Real = 1.0094120574261891;
                                attribute sigma_Iyy : Real = 0.3723953238821935;
                                attribute Izz : Real = 0.8740660846495787;
                                attribute sigma_Izz : Real = 0.37017423652493897;
                                attribute Ixy : Real = 0.0076688710440139;
                                attribute sigma_Ixy : Real = 0.02351283871158888;
                                attribute Ixz : Real = 0.051714639174203436;
                                attribute sigma_Ixz : Real = 0.022566176940390956;
                                attribute Iyz : Real = -0.027952824305149584;
                                attribute sigma_Iyz : Real = 0.02209918015384651;
                            }
                        }
                        part <'C.1.1.4.5.1.2'> 'Subassembly 195' {
                            attribute POIconv : String = "-";
                            attribute Ipoint : Boolean = false;
                            attribute mass : Real = 1.0938512465739623;
                            attribute sigma_mass : Real = 0.6464332159373649;
                            attribute Cx : Real = 36.65715206062614;
                            attribute sigma_Cx : Real = 34.3473779032705;
                            attribute Cy : Real = -54.956610181234;
                            attribute sigma_Cy : Real = 29.928896698254594;
                            attribute Cz : Real = -31.8433258089512;
                            attribute sigma_Cz : Real = 31.36249635463145;
                            attribute Ixx : Real = 1871.159916882838;
                            attribute sigma_Ixx : Real = 3500.6780307178833;
                            attribute Iyy : Real = 3466.9675435168056;
                            attribute sigma_Iyy : Real = 3858.1888970418004;
                            attribute Izz : Real = 3731.5925912463176;
                            attribute sigma_Izz : Real = 4206.201642075111;
                            attribute Ixy : Real = 147.08538756871866;
                            attribute sigma_Ixy : Real = 2043.17236668929;
                            attribute Ixz : Real = -505.49650216006427;
                            attribute sigma_Ixz : Real = 1151.1245182048563;
                            attribute Iyz : Real = -190.05511440477972;
                            attribute sigma_Iyz : Real = 1088.8287350789706;
                            part <'C.1.1.4.5.1.2.1'> 'Part 684' {
                                attribute POIconv : String = "+";
                                attribute Ipoint : Boolean = false;
                                attribute mass : Real = 0.11510431311046705;
                                attribute sigma_mass : Real = 0.28909372274994966;
                                attribute Cx : Real = -38.319445541128516;
                                attribute sigma_Cx : Real = 28.721044428837228;
                                attribute Cy : Real = 21.279124030843377;
                                attribute sigma_Cy : Real = 28.23690002309109;
                                attribute Cz : Real = -53.52545413188636;
                                attribute sigma_Cz : Real = 29.057750463592832;
                                attribute Ixx : Real = 0.1634008557308538;
                                attribute sigma_Ixx : Real = 0.37074144170588635;
                                attribute Iyy : Real = 0.17583565297390666;
                                attribute sigma_Iyy : Real = 0.3723953238821935;
                                attribute Izz : Real = 0.1487024348348355;
                                attribute sigma_Izz : Real = 0.37017423652493897;
                                attribute Ixy : Real = 0.01227083893178895;
                                attribute sigma_Ixy : Real = 0.02351283871158888;
                                attribute Ixz : Real = -0.00015273900575365985;
                                attribute sigma_Ixz : Real = 0.022566176940390956;
                                attribute Iyz : Real = -0.0005596919559221888;
                                attribute sigma_Iyz : Real = 0.02209918015384651;
                            }
                            part <'C.1.1.4.5.1.2.2'> 'Part 685' {
                                attribute POIconv : String = "-";
                                attribute Ipoint : Boolean = false;
                                attribute mass : Real = 0.48765380095737054;
                                attribute sigma_mass : Real = 0.28909372274994966;
                                attribute Cx : Real = 88.75530292280018;
                                attribute sigma_Cx : Real = 28.721044428837228;
                                attribute Cy : Real = -53.729676781222224;
                                attribute sigma_Cy : Real = 28.23690002309109;
                                attribute Cz : Real = -29.083979642018676;
                                attribute sigma_Cz : Real = 29.057750463592832;
                                attribute Ixx : Real = 0.6681893971636667;
                                attribute sigma_Ixx : Real = 0.37074144170588635;
                                attribute Iyy : Real = 0.6474488050827316;
                                attribute sigma_Iyy : Real = 0.3723953238821935;
                                attribute Izz : Real = 0.7384423955373283;
                                attribute sigma_Izz : Real = 0.37017423652493897;
                                attribute Ixy : Real = 0.0016882295500983567;
                                attribute sigma_Ixy : Real = 0.02351283871158888;
                                attribute Ixz : Real = -0.03123287271292473;
                                attribute sigma_Ixz : Real = 0.022566176940390956;
                                attribute Iyz : Real = 0.011094145601315178;
                                attribute sigma_Iyz : Real = 0.02209918015384651;
                            }
                            part <'C.1.1.4.5.1.2.3'> 'Part 686' {
                                attribute POIconv : String = "-";
                                attribute Ipoint : Boolean = false;
                                attribute mass : Real = 0.07498787941411138;
                                attribute sigma_mass : Real = 0.28909372274994966;
                                attribute Cx : Real = 36.137044010683894;
                                attribute sigma_Cx : Real = 28.721044428837228;
                                attribute Cy : Real = -25.958018703386188;
                                attribute sigma_Cy : Real = 28.23690002309109;
                                attribute Cz : Real = 61.00114309228957;
                                attribute sigma_Cz : Real = 29.057750463592832;
                                attribute Ixx : Real = 0.08171020163059381;
                                attribute sigma_Ixx : Real = 0.37074144170588635;
                                attribute Iyy : Real = 0.08785904546882935;
                                attribute sigma_Iyy : Real = 0.3723953238821935;
                                attribute Izz : Real = 0.07613759001625761;
                                attribute sigma_Izz : Real = 0.37017423652493897;
                                attribute Ixy : Real = -0.0013674459016115273;
                                attribute sigma_Ixy : Real = 0.02351283871158888;
                                attribute Ixz : Real = 0.005853186686075328;
                                attribute sigma_Ixz : Real = 0.022566176940390956;
                                attribute Iyz : Real = 0.007034409904021212;
                                attribute sigma_Iyz : Real = 0.02209918015384651;
                            }
                            part <'C.1.1.4.5.1.2.4'> 'Part 687' {
                                attribute POIconv : String = "+";
                                attribute Ipoint : Boolean = false;
                                attribute mass : Real = 0.3603147188061848;
                                attribute sigma_mass : Real = 0.28909372274994966;
                                attribute Cx : Real = -0.9015227667987347;
                                attribute sigma_Cx : Real = 28.721044428837228;
                                attribute Cy : Real = -80.43021969497204;
                                attribute sigma_Cy : Real = 28.23690002309109;
                                attribute Cz : Real = -43.28553429804742;
                                attribute sigma_Cz : Real = 29.057750463592832;
                                attribute Ixx : Real = 0.42328771570847906;
                                attribute sigma_Ixx : Real = 0.37074144170588635;
                                attribute Iyy : Real = 0.49628968896180703;
                                attribute sigma_Iyy : Real = 0.3723953238821935;
                                attribute Izz : Real = 0.4152256140762518;
                                attribute sigma_Izz : Real = 0.37017423652493897;
                                attribute Ixy : Real = -0.00422843924200126;
                                attribute sigma_Ixy : Real = 0.02351283871158888;
                                attribute Ixz : Real = 0.017556848456288375;
                                attribute sigma_Ixz : Real = 0.022566176940390956;
                                attribute Iyz : Real = 0.02201346237109579;
                                attribute sigma_Iyz : Real = 0.02209918015384651;
                            }
                            part <'C.1.1.4.5.1.2.5'> 'Part 688' {
                                attribute POIconv : String = "-";
                                attribute Ipoint : Boolean = false;
                                attribute mass : Real = 0.055790534285828475;
                                attribute sigma_mass : Real = 0.28909372274994966;
                                attribute Cx : Real = -20.768115622922778;
                                attribute sigma_Cx : Real = 28.721044428837228;
                                attribute Cy : Real = -97.4263054318726;
                                attribute sigma_Cy : Real = 28.23690002309109;
                                attribute Cz : Real = -62.12288639508188;
                                attribute sigma_Cz : Real = 29.057750463592832;
                                attribute Ixx : Real = 0.06589443743307816;
                                attribute sigma_Ixx : Real = 0.37074144170588635;
                                attribute Iyy : Real = 0.07251637448648951;
                                attribute sigma_Iyy : Real = 0.3723953238821935;
                                attribute Izz : Real = 0.07593302708954004;
                                attribute sigma_Izz : Real = 0.37017423652493897;
                                attribute Ixy : Real = 0.005877918236308498;
                                attribute sigma_Ixy : Real = 0.02351283871158888;
                                attribute Ixz : Real = 0.0043300084157293205;
                                attribute sigma_Ixz : Real = 0.022566176940390956;
                                attribute Iyz : Real = -0.0014569351338486751;
                                attribute sigma_Iyz : Real = 0.02209918015384651;
                            }
                        }
                    }
                    part <'C.1.1.4.5.2'> 'Assembly 55' {
                        attribute POIconv : String = "-";
                        attribute Ipoint : Boolean = false;
                        attribute mass : Real = 9.042771630625706;
                        attribute sigma_mass : Real = 1.1196551737036593;
                        attribute Cx : Real = -18.718656673266985;
                        attribute sigma_Cx : Real = 11.54721690710864;
                        attribute Cy : Real = -3.420792668482136;
                        attribute sigma_Cy : Real = 10.321602505614912;
                        attribute Cz : Real = -8.304962163507389;
                        attribute sigma_Cz : Real = 11.293375894286438;
                        attribute Ixx : Real = 61646.30346616947;
                        attribute sigma_Ixx : Real = 14933.582315620686;
                        attribute Iyy : Real = 69123.10443033713;
                        attribute sigma_Iyy : Real = 16523.437769905417;
                        attribute Izz : Real = 59052.935681909235;
                        attribute sigma_Izz : Real = 15328.744252063418;
                        attribute Ixy : Real = 2713.4880832666927;
                        attribute sigma_Ixy : Real = 6904.710736190281;
                        attribute Ixz : Real = -7549.796155527147;
                        attribute sigma_Ixz : Real = 7503.487725857415;
                        attribute Iyz : Real = -22181.27297042733;
                        attribute sigma_Iyz : Real = 7277.0927044746695;
                        part <'C.1.1.4.5.2.1'> 'Subassembly 196' {
                            attribute POIconv : String = "-";
                            attribute Ipoint : Boolean = false;
                            attribute mass : Real = 2.6659425663568546;
                            attribute sigma_mass : Real = 0.5781874454998993;
                            attribute Cx : Real = 7.834570906649998;
                            attribute sigma_Cx : Real = 20.198432118777628;
                            attribute Cy : Real = 8.419542615356958;
                            attribute sigma_Cy : Real = 18.193150440042213;
                            attribute Cz : Real = 5.866785467139913;
                            attribute sigma_Cz : Real = 22.210191558518737;
                            attribute Ixx : Real = 17984.462357671175;
                            attribute sigma_Ixx : Real = 7991.9894191678295;
                            attribute Iyy : Real = 22033.487708698223;
                            attribute sigma_Iyy : Real = 9018.899280889682;
                            attribute Izz : Real = 15432.342166208588;
                            attribute sigma_Izz : Real = 7086.031262227182;
                            attribute Ixy : Real = 85.38370041125563;
                            attribute sigma_Ixy : Real = 3423.1785377438523;
                            attribute Ixz : Real = -2870.663928219602;
                            attribute sigma_Ixz : Real = 4325.399401295953;
                            attribute Iyz : Real = -7234.213206013152;
                            attribute sigma_Iyz : Real = 3768.896176913372;
                            part <'C.1.1.4.5.2.1.1'> 'Part 689' {
                                attribute POIconv : String = "+";
                                attribute Ipoint : Boolean = false;
                                attribute mass : Real = 0.778733261555899;
                                attribute sigma_mass : Real = 0.28909372274994966;
                                attribute Cx : Real = 82.77139770798385;
                                attribute sigma_Cx : Real = 28.721044428837228;
                                attribute Cy : Real = 14.387979498133063;
                                attribute sigma_Cy : Real = 28.23690002309109;
                                attribute Cz : Real = 63.029924081638455;
                                attribute sigma_Cz : Real = 29.057750463592832;
                                attribute Ixx : Real = 0.9637121102912828;
                                attribute sigma_Ixx : Real = 0.37074144170588635;
                                attribute Iyy : Real = 0.9234867828364582;
                                attribute sigma_Iyy : Real = 0.3723953238821935;
                                attribute Izz : Real = 0.9462326990280726;
                                attribute sigma_Izz : Real = 0.37017423652493897;
                                attribute Ixy : Real = 0.014949304684276212;
                                attribute sigma_Ixy : Real = 0.02351283871158888;
                                attribute Ixz : Real = 0.01339002780609833;
                                attribute sigma_Ixz : Real = 0.022566176940390956;
                                attribute Iyz : Real = 0.034313812118543674;
                                attribute sigma_Iyz : Real = 0.02209918015384651;
                            }
                            part <'C.1.1.4.5.2.1.2'> 'Part 690' {
                                attribute POIconv : String = "+";
                                attribute Ipoint : Boolean = false;
                                attribute mass : Real = 0.9568621058263816;
                                attribute sigma_mass : Real = 0.28909372274994966;
                                attribute Cx : Real = -33.973609656095505;
                                attribute sigma_Cx : Real = 28.721044428837228;
                                attribute Cy : Real = 59.473318979144096;
                                attribute sigma_Cy : Real = 28.23690002309109;
                                attribute Cz : Real = 48.99963201023638;
                                attribute sigma_Cz : Real = 29.057750463592832;
                                attribute Ixx : Real = 1.1343299166749816;
                                attribute sigma_Ixx : Real = 0.37074144170588635;
                                attribute Iyy : Real = 1.2186767709521567;
                                attribute sigma_Iyy : Real = 0.3723953238821935;
                                attribute Izz : Real = 1.1159097953459405;
                                attribute sigma_Izz : Real = 0.37017423652493897;
                                attribute Ixy : Real = 0.013858432866820255;
                                attribute sigma_Ixy : Real = 0.02351283871158888;
                                attribute Ixz : Real = -0.08543633398883976;
                                attribute sigma_Ixz : Real = 0.022566176940390956;
                                attribute Iyz : Real = 0.00432979193668491;
                                attribute sigma_Iyz : Real = 0.02209918015384651;
                            }
                            part <'C.1.1.4.5.2.1.3'> 'Part 691' {
                                attribute POIconv : String = "+";
                                attribute Ipoint : Boolean = false;
                                attribute mass : Real = 0.4740491446400993;
                                attribute sigma_mass : Real = 0.28909372274994966;
                                attribute Cx : Real = 46.819713711738586;
                                attribute sigma_Cx : Real = 28.721044428837228;
                                attribute Cy : Real = -39.33364422991872;
                                attribute sigma_Cy : Real = 28.23690002309109;
                                attribute Cz : Real = -93.95119771361351;
                                attribute sigma_Cz : Real = 29.057750463592832;
                                attribute Ixx : Real = 0.5342479957281323;
                                attribute sigma_Ixx : Real = 0.37074144170588635;
                                attribute Iyy : Real = 0.5216757153673918;
                                attribute sigma_Iyy : Real = 0.3723953238821935;
                                attribute Izz : Real = 0.48682968142480904;
                                attribute sigma_Izz : Real = 0.37017423652493897;
                                attribute Ixy : Real = -0.003303742435147597;
                                attribute sigma_Ixy : Real = 0.02351283871158888;
                                attribute Ixz : Real = 0.03916557439190065;
                                attribute sigma_Ixz : Real = 0.022566176940390956;
                                attribute Iyz : Real = -0.0246545484429605;
                                attribute sigma_Iyz : Real = 0.02209918015384651;
                            }
                            part <'C.1.1.4.5.2.1.4'> 'Part 692' {
                                attribute POIconv : String = "-";
                                attribute Ipoint : Boolean = false;
                                attribute mass : Real = 0.45629805433447473;
                                attribute sigma_mass : Real = 0.28909372274994966;
                                attribute Cx : Real = -72.88461932912469;
                                attribute sigma_Cx : Real = 28.721044428837228;
                                attribute Cy : Real = -59.215825563296676;
                                attribute sigma_Cy : Real = 28.23690002309109;
                                attribute Cz : Real = -78.43862376175821;
                                attribute sigma_Cz : Real = 29.057750463592832;
                                attribute Ixx : Real = 0.5405471609747734;
                                attribute sigma_Ixx : Real = 0.37074144170588635;
                                attribute Iyy : Real = 0.6351644818589913;
                                attribute sigma_Iyy : Real = 0.3723953238821935;
                                attribute Izz : Real = 0.5921371356326721;
                                attribute sigma_Izz : Real = 0.37017423652493897;
                                attribute Ixy : Real = -0.061133062137915146;
                                attribute sigma_Ixy : Real = 0.02351283871158888;
                                attribute Ixz : Real = 0.0029286774257625105;
                                attribute sigma_Ixz : Real = 0.022566176940390956;
                                attribute Iyz : Real = 0.025116439907442695;
                                attribute sigma_Iyz : Real = 0.02209918015384651;
                            }
                        }
                        part <'C.1.1.4.5.2.2'> 'Subassembly 197' {
                            attribute POIconv : String = "-";
                            attribute Ipoint : Boolean = false;
                            attribute mass : Real = 0.9616291496527847;
                            attribute sigma_mass : Real = 0.5007250159521434;
                            attribute Cx : Real = -42.05834270900924;
                            attribute sigma_Cx : Real = 47.65996855078619;
                            attribute Cy : Real = -3.530261643557246;
                            attribute sigma_Cy : Real = 28.666133305848682;
                            attribute Cz : Real = -25.774358342464563;
                            attribute sigma_Cz : Real = 20.81883391048723;
                            attribute Ixx : Real = 992.6765598733474;
                            attribute sigma_Ixx : Real = 1472.4289461316025;
                            attribute Iyy : Real = 4726.758932039553;
                            attribute sigma_Iyy : Real = 5589.536659193709;
                            attribute Izz : Real = 5570.230044796901;
                            attribute sigma_Izz : Real = 6715.861295060976;
                            attribute Ixy : Real = 1639.402090381253;
                            attribute sigma_Ixy : Real = 2706.347863225208;
                            attribute Ixz : Real = -53.56786554237995;
                            attribute sigma_Ixz : Real = 1140.4176846676555;
                            attribute Iyz : Real = -139.0350399432104;
                            attribute sigma_Iyz : Real = 458.2957853153155;
                            part <'C.1.1.4.5.2.2.1'> 'Part 693' {
                                attribute POIconv : String = "-";
                                attribute Ipoint : Boolean = false;
                                attribute mass : Real = 0.176639727151487;
                                attribute sigma_mass : Real = 0.28909372274994966;
                                attribute Cx : Real = 90.512166172266;
                                attribute sigma_Cx : Real = 28.721044428837228;
                                attribute Cy : Real = -67.1765451785177;
                                attribute sigma_Cy : Real = 28.23690002309109;
                                attribute Cz : Real = -32.116163754835725;
                                attribute sigma_Cz : Real = 29.057750463592832;
                                attribute Ixx : Real = 0.1964134101628636;
                                attribute sigma_Ixx : Real = 0.37074144170588635;
                                attribute Iyy : Real = 0.18249680480064884;
                                attribute sigma_Iyy : Real = 0.3723953238821935;
                                attribute Izz : Real = 0.21192236259477626;
                                attribute sigma_Izz : Real = 0.37017423652493897;
                                attribute Ixy : Real = -0.006972638532967788;
                                attribute sigma_Ixy : Real = 0.02351283871158888;
                                attribute Ixz : Real = -0.0007993330649466419;
                                attribute sigma_Ixz : Real = 0.022566176940390956;
                                attribute Iyz : Real = 0.014203366189068386;
                                attribute sigma_Iyz : Real = 0.02209918015384651;
                            }
                            part <'C.1.1.4.5.2.2.2'> 'Part 694' {
                                attribute POIconv : String = "-";
                                attribute Ipoint : Boolean = false;
                                attribute mass : Real = 0.1732897980902344;
                                attribute sigma_mass : Real = 0.28909372274994966;
                                attribute Cx : Real = -10.115628223866224;
                                attribute sigma_Cx : Real = 28.721044428837228;
                                attribute Cy : Real = 24.359602946788073;
                                attribute sigma_Cy : Real = 28.23690002309109;
                                attribute Cz : Real = -7.20491842366755;
                                attribute sigma_Cz : Real = 29.057750463592832;
                                attribute Ixx : Real = 0.19225071350698547;
                                attribute sigma_Ixx : Real = 0.37074144170588635;
                                attribute Iyy : Real = 0.18519781290997242;
                                attribute sigma_Iyy : Real = 0.3723953238821935;
                                attribute Izz : Real = 0.22102352453135873;
                                attribute sigma_Izz : Real = 0.37017423652493897;
                                attribute Ixy : Real = 0.0038856935081703872;
                                attribute sigma_Ixy : Real = 0.02351283871158888;
                                attribute Ixz : Real = -0.0019131659232851856;
                                attribute sigma_Ixz : Real = 0.022566176940390956;
                                attribute Iyz : Real = -0.011870926596134954;
                                attribute sigma_Iyz : Real = 0.02209918015384651;
                            }
                            part <'C.1.1.4.5.2.2.3'> 'Part 695' {
                                attribute POIconv : String = "-";
                                attribute Ipoint : Boolean = false;
                                attribute mass : Real = 0.6116996244110633;
                                attribute sigma_mass : Real = 0.28909372274994966;
                                attribute Cx : Real = -89.3896862398833;
                                attribute sigma_Cx : Real = 28.721044428837228;
                                attribute Cy : Real = 6.947811087593436;
                                attribute sigma_Cy : Real = 28.23690002309109;
                                attribute Cz : Real = -29.203622695058584;
                                attribute sigma_Cz : Real = 29.057750463592832;
                                attribute Ixx : Real = 0.7437495047419891;
                                attribute sigma_Ixx : Real = 0.37074144170588635;
                                attribute Iyy : Real = 0.7286839268660732;
                                attribute sigma_Iyy : Real = 0.3723953238821935;
                                attribute Izz : Real = 0.6947609493181452;
                                attribute sigma_Izz : Real = 0.37017423652493897;
                                attribute Ixy : Real = -0.0007689128615830149;
                                attribute sigma_Ixy : Real = 0.02351283871158888;
                                attribute Ixz : Real = 0.001688171696741651;
                                attribute sigma_Ixz : Real = 0.022566176940390956;
                                attribute Iyz : Real = 0.02713605064301431;
                                attribute sigma_Iyz : Real = 0.02209918015384651;
                            }
                        }
                        part <'C.1.1.4.5.2.3'> 'Subassembly 198' {
                            attribute POIconv : String = "-";
                            attribute Ipoint : Boolean = false;
                            attribute mass : Real = 3.676936066599796;
                            attribute sigma_mass : Real = 0.6464332159373649;
                            attribute Cx : Real = -30.77021013101756;
                            attribute sigma_Cx : Real = 16.668161878971315;
                            attribute Cy : Real = -33.293401418272154;
                            attribute sigma_Cy : Real = 15.585080906763707;
                            attribute Cz : Real = -48.76709547104983;
                            attribute sigma_Cz : Real = 14.955257553405929;
                            attribute Ixx : Real = 15174.659455284687;
                            attribute sigma_Ixx : Real = 7341.4915189901785;
                            attribute Iyy : Real = 20160.056014089736;
                            attribute sigma_Iyy : Real = 8541.96121145246;
                            attribute Izz : Real = 23060.939172149825;
                            attribute sigma_Izz : Real = 9164.458434907858;
                            attribute Ixy : Real = 3375.5087640308084;
                            attribute sigma_Ixy : Real = 4059.1372417869848;
                            attribute Ixz : Real = -2824.899868763395;
                            attribute sigma_Ixz : Real = 3747.509873759252;
                            attribute Iyz : Real = -5559.970587795742;
                            attribute sigma_Iyz : Real = 3641.2254992678363;
                            part <'C.1.1.4.5.2.3.1'> 'Part 696' {
                                attribute POIconv : String = "+";
                                attribute Ipoint : Boolean = false;
                                attribute mass : Real = 0.6614907957387622;
                                attribute sigma_mass : Real = 0.28909372274994966;
                                attribute Cx : Real = -43.55907682329416;
                                attribute sigma_Cx : Real = 28.721044428837228;
                                attribute Cy : Real = -15.579560492187738;
                                attribute sigma_Cy : Real = 28.23690002309109;
                                attribute Cz : Real = -65.22868028841913;
                                attribute sigma_Cz : Real = 29.057750463592832;
                                attribute Ixx : Real = 0.9727921600997239;
                                attribute sigma_Ixx : Real = 0.37074144170588635;
                                attribute Iyy : Real = 0.924180403152381;
                                attribute sigma_Iyy : Real = 0.3723953238821935;
                                attribute Izz : Real = 0.8204448402397868;
                                attribute sigma_Izz : Real = 0.37017423652493897;
                                attribute Ixy : Real = -0.11269090499769062;
                                attribute sigma_Ixy : Real = 0.02351283871158888;
                                attribute Ixz : Real = -0.009794734069918251;
                                attribute sigma_Ixz : Real = 0.022566176940390956;
                                attribute Iyz : Real = -0.010126621874253807;
                                attribute sigma_Iyz : Real = 0.02209918015384651;
                            }
                            part <'C.1.1.4.5.2.3.2'> 'Part 697' {
                                attribute POIconv : String = "+";
                                attribute Ipoint : Boolean = false;
                                attribute mass : Real = 0.7561861641407013;
                                attribute sigma_mass : Real = 0.28909372274994966;
                                attribute Cx : Real = 83.52324776351452;
                                attribute sigma_Cx : Real = 28.721044428837228;
                                attribute Cy : Real = -76.49587052874267;
                                attribute sigma_Cy : Real = 28.23690002309109;
                                attribute Cz : Real = -39.48756381869316;
                                attribute sigma_Cz : Real = 29.057750463592832;
                                attribute Ixx : Real = 0.8969279359394727;
                                attribute sigma_Ixx : Real = 0.37074144170588635;
                                attribute Iyy : Real = 0.9597142287606878;
                                attribute sigma_Iyy : Real = 0.3723953238821935;
                                attribute Izz : Real = 1.1408890955432698;
                                attribute sigma_Izz : Real = 0.37017423652493897;
                                attribute Ixy : Real = -0.022682979675318883;
                                attribute sigma_Ixy : Real = 0.02351283871158888;
                                attribute Ixz : Real = -0.011863204884777661;
                                attribute sigma_Ixz : Real = 0.022566176940390956;
                                attribute Iyz : Real = 0.02362798455896486;
                                attribute sigma_Iyz : Real = 0.02209918015384651;
                            }
                            part <'C.1.1.4.5.2.3.3'> 'Part 698' {
                                attribute POIconv : String = "+";
                                attribute Ipoint : Boolean = false;
                                attribute mass : Real = 0.6198430245679337;
                                attribute sigma_mass : Real = 0.28909372274994966;
                                attribute Cx : Real = -46.22788834385574;
                                attribute sigma_Cx : Real = 28.721044428837228;
                                attribute Cy : Real = -80.63847618177533;
                                attribute sigma_Cy : Real = 28.23690002309109;
                                attribute Cz : Real = -69.16550188325346;
                                attribute sigma_Cz : Real = 29.057750463592832;
                                attribute Ixx : Real = 0.8143033547565512;
                                attribute sigma_Ixx : Real = 0.37074144170588635;
                                attribute Iyy : Real = 0.8159492862870545;
                                attribute sigma_Iyy : Real = 0.3723953238821935;
                                attribute Izz : Real = 0.7647472353363632;
                                attribute sigma_Izz : Real = 0.37017423652493897;
                                attribute Ixy : Real = -0.036055034929605496;
                                attribute sigma_Ixy : Real = 0.02351283871158888;
                                attribute Ixz : Real = -0.0017598684973048487;
                                attribute sigma_Ixz : Real = 0.022566176940390956;
                                attribute Iyz : Real = -0.0053525253364198385;
                                attribute sigma_Iyz : Real = 0.02209918015384651;
                            }
                            part <'C.1.1.4.5.2.3.4'> 'Part 699' {
                                attribute POIconv : String = "-";
                                attribute Ipoint : Boolean = false;
                                attribute mass : Real = 0.9360021412963979;
                                attribute sigma_mass : Real = 0.28909372274994966;
                                attribute Cx : Real = -94.25285863690078;
                                attribute sigma_Cx : Real = 28.721044428837228;
                                attribute Cy : Real = -47.94981596060097;
                                attribute sigma_Cy : Real = 28.23690002309109;
                                attribute Cz : Real = -88.74891842715442;
                                attribute sigma_Cz : Real = 29.057750463592832;
                                attribute Ixx : Real = 1.034879848746387;
                                attribute sigma_Ixx : Real = 0.37074144170588635;
                                attribute Iyy : Real = 1.053463114362619;
                                attribute sigma_Iyy : Real = 0.3723953238821935;
                                attribute Izz : Real = 1.1720665682033824;
                                attribute sigma_Izz : Real = 0.37017423652493897;
                                attribute Ixy : Real = 0.11517385564587376;
                                attribute sigma_Ixy : Real = 0.02351283871158888;
                                attribute Ixz : Real = -0.03666029813430868;
                                attribute sigma_Ixz : Real = 0.022566176940390956;
                                attribute Iyz : Real = 0.02651653028966892;
                                attribute sigma_Iyz : Real = 0.02209918015384651;
                            }
                            part <'C.1.1.4.5.2.3.5'> 'Part 700' {
                                attribute POIconv : String = "-";
                                attribute Ipoint : Boolean = false;
                                attribute mass : Real = 0.7034139408560004;
                                attribute sigma_mass : Real = 0.28909372274994966;
                                attribute Cx : Real = -43.51687952876091;
                                attribute sigma_Cx : Real = 28.721044428837228;
                                attribute Cy : Real = 57.71491201594472;
                                attribute sigma_Cy : Real = 28.23690002309109;
                                attribute Cz : Real = 27.91465916670859;
                                attribute sigma_Cz : Real = 29.057750463592832;
                                attribute Ixx : Real = 0.817711499665778;
                                attribute sigma_Ixx : Real = 0.37074144170588635;
                                attribute Iyy : Real = 0.8675304354241302;
                                attribute sigma_Iyy : Real = 0.3723953238821935;
                                attribute Izz : Real = 0.8085704785353787;
                                attribute sigma_Izz : Real = 0.37017423652493897;
                                attribute Ixy : Real = 0.016806881986910507;
                                attribute sigma_Ixy : Real = 0.02351283871158888;
                                attribute Ixz : Real = -0.006094909929318314;
                                attribute sigma_Ixz : Real = 0.022566176940390956;
                                attribute Iyz : Real = -0.023328592166564986;
                                attribute sigma_Iyz : Real = 0.02209918015384651;
                            }
                        }
                        part <'C.1.1.4.5.2.4'> 'Subassembly 199' {
                            attribute POIconv : String = "-";
                            attribute Ipoint : Boolean = false;
                            attribute mass : Real = 1.7382638480162713;
                            attribute sigma_mass : Real = 0.5007250159521434;
                            attribute Cx : Real = -21.03848037609035;
                            attribute sigma_Cx : Real = 23.808000692493174;
                            attribute Cy : Real = 41.66976555101154;
                            attribute sigma_Cy : Real = 21.415986144484187;
                            attribute Cz : Real = 65.21361948347402;
                            attribute sigma_Cz : Real = 20.866552394712034;
                            attribute Ixx : Real = 4061.382457827249;
                            attribute sigma_Ixx : Real = 3256.277007631926;
                            attribute Iyy : Real = 3011.8840994660586;
                            attribute sigma_Iyy : Real = 3439.112265662882;
                            attribute Izz : Real = 4853.38360776387;
                            attribute sigma_Izz : Real = 3818.1456769551455;
                            attribute Ixy : Real = -404.266989783952;
                            attribute sigma_Ixy : Real = 1506.1239210868425;
                            attribute Ixz : Real = 1091.1589200236785;
                            attribute sigma_Ixz : Real = 1512.1685249441923;
                            attribute Iyz : Real = 1407.8068215317528;
                            attribute sigma_Iyz : Real = 1572.2260222099812;
                            part <'C.1.1.4.5.2.4.1'> 'Part 701' {
                                attribute POIconv : String = "+";
                                attribute Ipoint : Boolean = false;
                                attribute mass : Real = 0.21574145847093315;
                                attribute sigma_mass : Real = 0.28909372274994966;
                                attribute Cx : Real = 66.00678227841854;
                                attribute sigma_Cx : Real = 28.721044428837228;
                                attribute Cy : Real = 45.6171250436455;
                                attribute sigma_Cy : Real = 28.23690002309109;
                                attribute Cz : Real = 21.227593533694744;
                                attribute sigma_Cz : Real = 29.057750463592832;
                                attribute Ixx : Real = 0.31183894636364573;
                                attribute sigma_Ixx : Real = 0.37074144170588635;
                                attribute Iyy : Real = 0.3431571151566759;
                                attribute sigma_Iyy : Real = 0.3723953238821935;
                                attribute Izz : Real = 0.3032670903373876;
                                attribute sigma_Izz : Real = 0.37017423652493897;
                                attribute Ixy : Real = 0.021770134391957525;
                                attribute sigma_Ixy : Real = 0.02351283871158888;
                                attribute Ixz : Real = 0.00259655354499567;
                                attribute sigma_Ixz : Real = 0.022566176940390956;
                                attribute Iyz : Real = -0.0007534296556114815;
                                attribute sigma_Iyz : Real = 0.02209918015384651;
                            }
                            part <'C.1.1.4.5.2.4.2'> 'Part 702' {
                                attribute POIconv : String = "-";
                                attribute Ipoint : Boolean = false;
                                attribute mass : Real = 0.952474264848046;
                                attribute sigma_mass : Real = 0.28909372274994966;
                                attribute Cx : Real = -37.06433824263513;
                                attribute sigma_Cx : Real = 28.721044428837228;
                                attribute Cy : Real = 7.076812628656626;
                                attribute sigma_Cy : Real = 28.23690002309109;
                                attribute Cz : Real = 87.21284228377044;
                                attribute sigma_Cz : Real = 29.057750463592832;
                                attribute Ixx : Real = 0.891986830749284;
                                attribute sigma_Ixx : Real = 0.37074144170588635;
                                attribute Iyy : Real = 0.8684200016430845;
                                attribute sigma_Iyy : Real = 0.3723953238821935;
                                attribute Izz : Real = 0.8690985685725223;
                                attribute sigma_Izz : Real = 0.37017423652493897;
                                attribute Ixy : Real = 0.0016582478297530044;
                                attribute sigma_Ixy : Real = 0.02351283871158888;
                                attribute Ixz : Real = 0.004895732437623076;
                                attribute sigma_Ixz : Real = 0.022566176940390956;
                                attribute Iyz : Real = 0.000360654029876336;
                                attribute sigma_Iyz : Real = 0.02209918015384651;
                            }
                            part <'C.1.1.4.5.2.4.3'> 'Part 703' {
                                attribute POIconv : String = "-";
                                attribute Ipoint : Boolean = false;
                                attribute mass : Real = 0.5700481246972923;
                                attribute sigma_mass : Real = 0.28909372274994966;
                                attribute Cx : Real = -27.204722445458174;
                                attribute sigma_Cx : Real = 28.721044428837228;
                                attribute Cy : Real = 97.97604377381504;
                                attribute sigma_Cy : Real = 28.23690002309109;
                                attribute Cz : Real = 45.102889044210315;
                                attribute sigma_Cz : Real = 29.057750463592832;
                                attribute Ixx : Real = 0.8122376664768497;
                                attribute sigma_Ixx : Real = 0.37074144170588635;
                                attribute Iyy : Real = 0.8027276521243892;
                                attribute sigma_Iyy : Real = 0.3723953238821935;
                                attribute Izz : Real = 0.8276223382317585;
                                attribute sigma_Izz : Real = 0.37017423652493897;
                                attribute Ixy : Real = -0.00364346393596255;
                                attribute sigma_Ixy : Real = 0.02351283871158888;
                                attribute Ixz : Real = 0.020482219314112825;
                                attribute sigma_Ixz : Real = 0.022566176940390956;
                                attribute Iyz : Real = -0.003240294290503124;
                                attribute sigma_Iyz : Real = 0.02209918015384651;
                            }
                        }
                    }
                    part <'C.1.1.4.5.3'> 'Assembly 56' {
                        attribute POIconv : String = "-";
                        attribute Ipoint : Boolean = false;
                        attribute mass : Real = 5.030240003043786;
                        attribute sigma_mass : Real = 1.0014500319042867;
                        attribute Cx : Real = 0.731550634975887;
                        attribute sigma_Cx : Real = 16.602085691926177;
                        attribute Cy : Real = -42.75093589825313;
                        attribute sigma_Cy : Real = 14.537065688258783;
                        attribute Cz : Real = -6.191969492272626;
                        attribute sigma_Cz : Real = 15.960728850667424;
                        attribute Ixx : Real = 20228.069636625474;
                        attribute sigma_Ixx : Real = 10889.456527700853;
                        attribute Iyy : Real = 29430.486212730233;
                        attribute sigma_Iyy : Real = 12630.216847317955;
                        attribute Izz : Real = 28537.739380113453;
                        attribute sigma_Izz : Real = 11854.130788247676;
                        attribute Ixy : Real = -3559.71267695613;
                        attribute sigma_Ixy : Real = 5543.3274736730355;
                        attribute Ixz : Real = 2552.1631708239397;
                        attribute sigma_Ixz : Real = 5756.720247428165;
                        attribute Iyz : Real = -3352.1535690822966;
                        attribute sigma_Iyz : Real = 4808.388329145172;
                        part <'C.1.1.4.5.3.1'> 'Subassembly 200' {
                            attribute POIconv : String = "-";
                            attribute Ipoint : Boolean = false;
                            attribute mass : Real = 1.8694034173726104;
                            attribute sigma_mass : Real = 0.5781874454998993;
                            attribute Cx : Real = -53.00946301330481;
                            attribute sigma_Cx : Real = 19.795396702684943;
                            attribute Cy : Real = -57.35936087499651;
                            attribute sigma_Cy : Real = 22.05034951880619;
                            attribute Cz : Real = -22.974008309060974;
                            attribute sigma_Cz : Real = 22.300060722953585;
                            attribute Ixx : Real = 1779.0852201621321;
                            attribute sigma_Ixx : Real = 3456.2897502622027;
                            attribute Iyy : Real = 2674.287684487019;
                            attribute sigma_Iyy : Real = 2845.752584427591;
                            attribute Izz : Real = 1424.1653623293241;
                            attribute sigma_Izz : Real = 2629.183146573623;
                            attribute Ixy : Real = 58.051823353989484;
                            attribute sigma_Ixy : Real = 1002.4974077308185;
                            attribute Ixz : Real = 807.4975417087376;
                            attribute sigma_Ixz : Real = 1335.9080829560864;
                            attribute Iyz : Real = 183.73310650368484;
                            attribute sigma_Iyz : Real = 1656.031796349026;
                            part <'C.1.1.4.5.3.1.1'> 'Part 704' {
                                attribute POIconv : String = "-";
                                attribute Ipoint : Boolean = false;
                                attribute mass : Real = 0.6181363071794622;
                                attribute sigma_mass : Real = 0.28909372274994966;
                                attribute Cx : Real = -88.38436212390661;
                                attribute sigma_Cx : Real = 28.721044428837228;
                                attribute Cy : Real = -54.767060512676835;
                                attribute sigma_Cy : Real = 28.23690002309109;
                                attribute Cz : Real = 0.7699199020862579;
                                attribute sigma_Cz : Real = 29.057750463592832;
                                attribute Ixx : Real = 0.7105811457485497;
                                attribute sigma_Ixx : Real = 0.37074144170588635;
                                attribute Iyy : Real = 0.7058748745836105;
                                attribute sigma_Iyy : Real = 0.3723953238821935;
                                attribute Izz : Real = 0.8218448367932933;
                                attribute sigma_Izz : Real = 0.37017423652493897;
                                attribute Ixy : Real = -0.0024425930359994723;
                                attribute sigma_Ixy : Real = 0.02351283871158888;
                                attribute Ixz : Real = 0.05619118465805949;
                                attribute sigma_Ixz : Real = 0.022566176940390956;
                                attribute Iyz : Real = 0.007311057667664491;
                                attribute sigma_Iyz : Real = 0.02209918015384651;
                            }
                            part <'C.1.1.4.5.3.1.2'> 'Part 705' {
                                attribute POIconv : String = "+";
                                attribute Ipoint : Boolean = false;
                                attribute mass : Real = 0.01861351730534807;
                                attribute sigma_mass : Real = 0.28909372274994966;
                                attribute Cx : Real = -28.513810643926263;
                                attribute sigma_Cx : Real = 28.721044428837228;
                                attribute Cy : Real = 21.655534906312823;
                                attribute sigma_Cy : Real = 28.23690002309109;
                                attribute Cz : Real = 36.31605035625398;
                                attribute sigma_Cz : Real = 29.057750463592832;
                                attribute Ixx : Real = 0.022980722775626284;
                                attribute sigma_Ixx : Real = 0.37074144170588635;
                                attribute Iyy : Real = 0.023646280808303666;
                                attribute sigma_Iyy : Real = 0.3723953238821935;
                                attribute Izz : Real = 0.020702241025586227;
                                attribute sigma_Izz : Real = 0.37017423652493897;
                                attribute Ixy : Real = 0.001743042595745284;
                                attribute sigma_Ixy : Real = 0.02351283871158888;
                                attribute Ixz : Real = -0.0009144028456923883;
                                attribute sigma_Ixz : Real = 0.022566176940390956;
                                attribute Iyz : Real = -5.6003885499551e-05;
                                attribute sigma_Iyz : Real = 0.02209918015384651;
                            }
                            part <'C.1.1.4.5.3.1.3'> 'Part 706' {
                                attribute POIconv : String = "-";
                                attribute Ipoint : Boolean = false;
                                attribute mass : Real = 0.24543188220774756;
                                attribute sigma_mass : Real = 0.28909372274994966;
                                attribute Cx : Real = -38.11907307244837;
                                attribute sigma_Cx : Real = 28.721044428837228;
                                attribute Cy : Real = -80.86219783872366;
                                attribute sigma_Cy : Real = 28.23690002309109;
                                attribute Cz : Real = 18.341547856107354;
                                attribute sigma_Cz : Real = 29.057750463592832;
                                attribute Ixx : Real = 0.2960881970694699;
                                attribute sigma_Ixx : Real = 0.37074144170588635;
                                attribute Iyy : Real = 0.2820275713494834;
                                attribute sigma_Iyy : Real = 0.3723953238821935;
                                attribute Izz : Real = 0.26660346410223534;
                                attribute sigma_Izz : Real = 0.37017423652493897;
                                attribute Ixy : Real = 0.0014772203017352108;
                                attribute sigma_Ixy : Real = 0.02351283871158888;
                                attribute Ixz : Real = 0.007203635064748598;
                                attribute sigma_Ixz : Real = 0.022566176940390956;
                                attribute Iyz : Real = 0.020799571811916773;
                                attribute sigma_Iyz : Real = 0.02209918015384651;
                            }
                            part <'C.1.1.4.5.3.1.4'> 'Part 707' {
                                attribute POIconv : String = "+";
                                attribute Ipoint : Boolean = false;
                                attribute mass : Real = 0.9872217106800526;
                                attribute sigma_mass : Real = 0.28909372274994966;
                                attribute Cx : Real = -35.02365229651332;
                                attribute sigma_Cx : Real = 28.721044428837228;
                                attribute Cy : Real = -54.62926956824958;
                                attribute sigma_Cy : Real = 28.23690002309109;
                                attribute Cz : Real = -49.230253556743264;
                                attribute sigma_Cz : Real = 29.057750463592832;
                                attribute Ixx : Real = 1.311390835126343;
                                attribute sigma_Ixx : Real = 0.37074144170588635;
                                attribute Iyy : Real = 1.3590790973440527;
                                attribute sigma_Iyy : Real = 0.3723953238821935;
                                attribute Izz : Real = 1.2927278947398129;
                                attribute sigma_Izz : Real = 0.37017423652493897;
                                attribute Ixy : Real = 0.020626965163901993;
                                attribute sigma_Ixy : Real = 0.02351283871158888;
                                attribute Ixz : Real = -0.05513576322599253;
                                attribute sigma_Ixz : Real = 0.022566176940390956;
                                attribute Iyz : Real = 0.13572115752784122;
                                attribute sigma_Iyz : Real = 0.02209918015384651;
                            }
                        }
                        part <'C.1.1.4.5.3.2'> 'Subassembly 201' {
                            attribute POIconv : String = "-";
                            attribute Ipoint : Boolean = false;
                            attribute mass : Real = 1.336515749156708;
                            attribute sigma_mass : Real = 0.5007250159521434;
                            attribute Cx : Real = 43.30089803403201;
                            attribute sigma_Cx : Real = 30.200268034889316;
                            attribute Cy : Real = -34.004127854517954;
                            attribute sigma_Cy : Real = 31.856381929411366;
                            attribute Cz : Real = -13.429492717362214;
                            attribute sigma_Cz : Real = 28.153431302501648;
                            attribute Ixx : Real = 4266.3686372244865;
                            attribute sigma_Ixx : Real = 6444.746122091879;
                            attribute Iyy : Real = 2879.4000472461785;
                            attribute sigma_Iyy : Real = 6108.695095236922;
                            attribute Izz : Real = 4641.645206333791;
                            attribute sigma_Izz : Real = 7160.611367853758;
                            attribute Ixy : Real = 1130.0621448940585;
                            attribute sigma_Ixy : Real = 3572.731410472714;
                            attribute Ixz : Real = 1243.733974176817;
                            attribute sigma_Ixz : Real = 3030.813718563388;
                            attribute Iyz : Real = -1681.908331715359;
                            attribute sigma_Iyz : Real = 3191.894777359033;
                            part <'C.1.1.4.5.3.2.1'> 'Part 708' {
                                attribute POIconv : String = "-";
                                attribute Ipoint : Boolean = false;
                                attribute mass : Real = 0.5766528496164829;
                                attribute sigma_mass : Real = 0.28909372274994966;
                                attribute Cx : Real = 63.95033188164234;
                                attribute sigma_Cx : Real = 28.721044428837228;
                                attribute Cy : Real = -8.190266601741314;
                                attribute sigma_Cy : Real = 28.23690002309109;
                                attribute Cz : Real = -14.481313759461045;
                                attribute sigma_Cz : Real = 29.057750463592832;
                                attribute Ixx : Real = 0.734019955825562;
                                attribute sigma_Ixx : Real = 0.37074144170588635;
                                attribute Iyy : Real = 0.7977772828222424;
                                attribute sigma_Iyy : Real = 0.3723953238821935;
                                attribute Izz : Real = 0.6566883170093378;
                                attribute sigma_Izz : Real = 0.37017423652493897;
                                attribute Ixy : Real = -0.050267614553132646;
                                attribute sigma_Ixy : Real = 0.02351283871158888;
                                attribute Ixz : Real = 0.020581594802523813;
                                attribute sigma_Ixz : Real = 0.022566176940390956;
                                attribute Iyz : Real = -0.020762292104751327;
                                attribute sigma_Iyz : Real = 0.02209918015384651;
                            }
                            part <'C.1.1.4.5.3.2.2'> 'Part 709' {
                                attribute POIconv : String = "-";
                                attribute Ipoint : Boolean = false;
                                attribute mass : Real = 0.11901163538405672;
                                attribute sigma_mass : Real = 0.28909372274994966;
                                attribute Cx : Real = -64.35482897795737;
                                attribute sigma_Cx : Real = 28.721044428837228;
                                attribute Cy : Real = 75.11381502263248;
                                attribute sigma_Cy : Real = 28.23690002309109;
                                attribute Cz : Real = 81.48970929905772;
                                attribute sigma_Cz : Real = 29.057750463592832;
                                attribute Ixx : Real = 0.1444977929943766;
                                attribute sigma_Ixx : Real = 0.37074144170588635;
                                attribute Iyy : Real = 0.15691711235480899;
                                attribute sigma_Iyy : Real = 0.3723953238821935;
                                attribute Izz : Real = 0.15886247791679445;
                                attribute sigma_Izz : Real = 0.37017423652493897;
                                attribute Ixy : Real = 0.004017344344703303;
                                attribute sigma_Ixy : Real = 0.02351283871158888;
                                attribute Ixz : Real = -0.002251255957500059;
                                attribute sigma_Ixz : Real = 0.022566176940390956;
                                attribute Iyz : Real = 0.0015117292708002733;
                                attribute sigma_Iyz : Real = 0.02209918015384651;
                            }
                            part <'C.1.1.4.5.3.2.3'> 'Part 710' {
                                attribute POIconv : String = "+";
                                attribute Ipoint : Boolean = false;
                                attribute mass : Real = 0.6408512641561683;
                                attribute sigma_mass : Real = 0.28909372274994966;
                                attribute Cx : Real = 44.71265971660614;
                                attribute sigma_Cx : Real = 28.721044428837228;
                                attribute Cy : Real = -77.49618762172759;
                                attribute sigma_Cy : Real = 28.23690002309109;
                                attribute Cz : Real = -30.110358400270343;
                                attribute sigma_Cz : Real = 29.057750463592832;
                                attribute Ixx : Real = 0.7779300632193954;
                                attribute sigma_Ixx : Real = 0.37074144170588635;
                                attribute Iyy : Real = 0.7586447735828574;
                                attribute sigma_Iyy : Real = 0.3723953238821935;
                                attribute Izz : Real = 0.8495913707678654;
                                attribute sigma_Izz : Real = 0.37017423652493897;
                                attribute Ixy : Real = -0.08973762475708297;
                                attribute sigma_Ixy : Real = 0.02351283871158888;
                                attribute Ixz : Real = 0.03242582577274904;
                                attribute sigma_Ixz : Real = 0.022566176940390956;
                                attribute Iyz : Real = -0.03169693861486331;
                                attribute sigma_Iyz : Real = 0.02209918015384651;
                            }
                        }
                        part <'C.1.1.4.5.3.3'> 'Subassembly 202' {
                            attribute POIconv : String = "-";
                            attribute Ipoint : Boolean = false;
                            attribute mass : Real = 1.8243208365144676;
                            attribute sigma_mass : Real = 0.6464332159373649;
                            attribute Cx : Real = 24.613880138071963;
                            attribute sigma_Cx : Real = 26.388422285526712;
                            attribute Cy : Real = -34.189507142939476;
                            attribute sigma_Cy : Real = 22.69475333032914;
                            attribute Cz : Real = 16.30706887217688;
                            attribute sigma_Cz : Real = 29.889819497661737;
                            attribute Ixx : Real = 12027.716846589996;
                            attribute sigma_Ixx : Real = 7354.614038578648;
                            attribute Iyy : Real = 13495.299481468315;
                            attribute sigma_Iyy : Real = 8258.417920277163;
                            attribute Izz : Real = 12975.501580356062;
                            attribute sigma_Izz : Real = 6528.841417766516;
                            attribute Ixy : Real = -2409.5518458303263;
                            attribute sigma_Ixy : Real = 2635.1413862762747;
                            attribute Ixz : Real = 2755.4015652127396;
                            attribute sigma_Ixz : Real = 3290.600609781414;
                            attribute Iyz : Real = -1128.8775937697371;
                            attribute sigma_Iyz : Real = 2831.0773773808296;
                            part <'C.1.1.4.5.3.3.1'> 'Part 711' {
                                attribute POIconv : String = "-";
                                attribute Ipoint : Boolean = false;
                                attribute mass : Real = 0.5243686088677496;
                                attribute sigma_mass : Real = 0.28909372274994966;
                                attribute Cx : Real = 77.82237767241895;
                                attribute sigma_Cx : Real = 28.721044428837228;
                                attribute Cy : Real = 50.653414241969585;
                                attribute sigma_Cy : Real = 28.23690002309109;
                                attribute Cz : Real = 24.862894974648952;
                                attribute sigma_Cz : Real = 29.057750463592832;
                                attribute Ixx : Real = 0.49970700822072517;
                                attribute sigma_Ixx : Real = 0.37074144170588635;
                                attribute Iyy : Real = 0.6667928010168054;
                                attribute sigma_Iyy : Real = 0.3723953238821935;
                                attribute Izz : Real = 0.6677517834265364;
                                attribute sigma_Izz : Real = 0.37017423652493897;
                                attribute Ixy : Real = 0.011275203244257423;
                                attribute sigma_Ixy : Real = 0.02351283871158888;
                                attribute Ixz : Real = -0.04956096849399768;
                                attribute sigma_Ixz : Real = 0.022566176940390956;
                                attribute Iyz : Real = 0.0037794841444387553;
                                attribute sigma_Iyz : Real = 0.02209918015384651;
                            }
                            part <'C.1.1.4.5.3.3.2'> 'Part 712' {
                                attribute POIconv : String = "+";
                                attribute Ipoint : Boolean = false;
                                attribute mass : Real = 0.48151264068833555;
                                attribute sigma_mass : Real = 0.28909372274994966;
                                attribute Cx : Real = 28.952090302482247;
                                attribute sigma_Cx : Real = 28.721044428837228;
                                attribute Cy : Real = -74.66428801417351;
                                attribute sigma_Cy : Real = 28.23690002309109;
                                attribute Cz : Real = 68.38612584397197;
                                attribute sigma_Cz : Real = 29.057750463592832;
                                attribute Ixx : Real = 0.6724347046816052;
                                attribute sigma_Ixx : Real = 0.37074144170588635;
                                attribute Iyy : Real = 0.6909920992351701;
                                attribute sigma_Iyy : Real = 0.3723953238821935;
                                attribute Izz : Real = 0.6457045914620532;
                                attribute sigma_Izz : Real = 0.37017423652493897;
                                attribute Ixy : Real = 0.03989488917460356;
                                attribute sigma_Ixy : Real = 0.02351283871158888;
                                attribute Ixz : Real = 0.01916526523264779;
                                attribute sigma_Ixz : Real = 0.022566176940390956;
                                attribute Iyz : Real = -0.021892412248756182;
                                attribute sigma_Iyz : Real = 0.02209918015384651;
                            }
                            part <'C.1.1.4.5.3.3.3'> 'Part 713' {
                                attribute POIconv : String = "+";
                                attribute Ipoint : Boolean = false;
                                attribute mass : Real = 0.4320334558309987;
                                attribute sigma_mass : Real = 0.28909372274994966;
                                attribute Cx : Real = -82.25429663434625;
                                attribute sigma_Cx : Real = 28.721044428837228;
                                attribute Cy : Real = -49.94864575564861;
                                attribute sigma_Cy : Real = 28.23690002309109;
                                attribute Cz : Real = 45.12386843562126;
                                attribute sigma_Cz : Real = 29.057750463592832;
                                attribute Ixx : Real = 0.5504236931337213;
                                attribute sigma_Ixx : Real = 0.37074144170588635;
                                attribute Iyy : Real = 0.5954264153655042;
                                attribute sigma_Iyy : Real = 0.3723953238821935;
                                attribute Izz : Real = 0.5897405377989049;
                                attribute sigma_Izz : Real = 0.37017423652493897;
                                attribute Ixy : Real = -0.02403321325698159;
                                attribute sigma_Ixy : Real = 0.02351283871158888;
                                attribute Ixz : Real = -0.022635029975796445;
                                attribute sigma_Ixz : Real = 0.022566176940390956;
                                attribute Iyz : Real = -0.05257036239153015;
                                attribute sigma_Iyz : Real = 0.02209918015384651;
                            }
                            part <'C.1.1.4.5.3.3.4'> 'Part 714' {
                                attribute POIconv : String = "-";
                                attribute Ipoint : Boolean = false;
                                attribute mass : Real = 0.11030147460312582;
                                attribute sigma_mass : Real = 0.28909372274994966;
                                attribute Cx : Real = 93.77060569822788;
                                attribute sigma_Cx : Real = 28.721044428837228;
                                attribute Cy : Real = -43.02244698628783;
                                attribute sigma_Cy : Real = 28.23690002309109;
                                attribute Cz : Real = -95.5415905918926;
                                attribute sigma_Cz : Real = 29.057750463592832;
                                attribute Ixx : Real = 0.13421399962043973;
                                attribute sigma_Ixx : Real = 0.37074144170588635;
                                attribute Iyy : Real = 0.13585396760505633;
                                attribute sigma_Iyy : Real = 0.3723953238821935;
                                attribute Izz : Real = 0.1324101159940624;
                                attribute sigma_Izz : Real = 0.37017423652493897;
                                attribute Ixy : Real = 0.002863968184362945;
                                attribute sigma_Ixy : Real = 0.02351283871158888;
                                attribute Ixz : Real = 0.004003239108246807;
                                attribute sigma_Ixz : Real = 0.022566176940390956;
                                attribute Iyz : Real = -0.0014841627506211623;
                                attribute sigma_Iyz : Real = 0.02209918015384651;
                            }
                            part <'C.1.1.4.5.3.3.5'> 'Part 715' {
                                attribute POIconv : String = "+";
                                attribute Ipoint : Boolean = false;
                                attribute mass : Real = 0.27610465652425775;
                                attribute sigma_mass : Real = 0.28909372274994966;
                                attribute Cx : Real = 55.59043143875897;
                                attribute sigma_Cx : Real = 28.721044428837228;
                                attribute Cy : Real = -96.5466033667326;
                                attribute sigma_Cy : Real = 28.23690002309109;
                                attribute Cz : Real = -91.17348100990057;
                                attribute sigma_Cz : Real = 29.057750463592832;
                                attribute Ixx : Real = 0.37362899423571533;
                                attribute sigma_Ixx : Real = 0.37074144170588635;
                                attribute Iyy : Real = 0.3594112917653221;
                                attribute sigma_Iyy : Real = 0.3723953238821935;
                                attribute Izz : Real = 0.30049652543813105;
                                attribute sigma_Izz : Real = 0.37017423652493897;
                                attribute Ixy : Real = 0.0020822286970982053;
                                attribute sigma_Ixy : Real = 0.02351283871158888;
                                attribute Ixz : Real = -0.009048158731498458;
                                attribute sigma_Ixz : Real = 0.022566176940390956;
                                attribute Iyz : Real = 0.013549022159672273;
                                attribute sigma_Iyz : Real = 0.02209918015384651;
                            }
                        }
                    }
                    part <'C.1.1.4.5.4'> 'Assembly 57' {
                        attribute POIconv : String = "-";
                        attribute Ipoint : Boolean = false;
                        attribute mass : Real = 8.592073787213769;
                        attribute sigma_mass : Real = 1.1196551737036593;
                        attribute Cx : Real = -4.051314702556611;
                        attribute sigma_Cx : Real = 13.363140186543205;
                        attribute Cy : Real = 2.4673977219587675;
                        attribute sigma_Cy : Real = 12.576042362513597;
                        attribute Cz : Real = -9.001614382634596;
                        attribute sigma_Cz : Real = 11.584510132882068;
                        attribute Ixx : Real = 52915.09684042675;
                        attribute sigma_Ixx : Real = 16362.231401656707;
                        attribute Iyy : Real = 52959.70002681116;
                        attribute sigma_Iyy : Real = 17619.34772276131;
                        attribute Izz : Real = 57554.51509030698;
                        attribute sigma_Izz : Real = 19556.73318211548;
                        attribute Ixy : Real = -16463.670194558992;
                        attribute sigma_Ixy : Real = 8592.738198592262;
                        attribute Ixz : Real = -1888.0196977994556;
                        attribute sigma_Ixz : Real = 7255.136480485335;
                        attribute Iyz : Real = -3358.828201401711;
                        attribute sigma_Iyz : Real = 7902.556671193797;
                        part <'C.1.1.4.5.4.1'> 'Subassembly 203' {
                            attribute POIconv : String = "-";
                            attribute Ipoint : Boolean = false;
                            attribute mass : Real = 1.9479303613349328;
                            attribute sigma_mass : Real = 0.5007250159521434;
                            attribute Cx : Real = -54.507058224005995;
                            attribute sigma_Cx : Real = 30.062527282741545;
                            attribute Cy : Real = -39.783735212006285;
                            attribute sigma_Cy : Real = 23.23423775307186;
                            attribute Cz : Real = -14.66707932478697;
                            attribute sigma_Cz : Real = 21.57375027980886;
                            attribute Ixx : Real = 1513.3203086318424;
                            attribute sigma_Ixx : Real = 3659.5979568523185;
                            attribute Iyy : Real = 3690.652230645854;
                            attribute sigma_Iyy : Real = 8201.28014506762;
                            attribute Izz : Real = 4210.776094309152;
                            attribute sigma_Izz : Real = 9435.672890679225;
                            attribute Ixy : Real = -1753.295208255212;
                            attribute sigma_Ixy : Real = 4147.325038427564;
                            attribute Ixz : Real = -1241.0547891495594;
                            attribute sigma_Ixz : Real = 2933.783948867018;
                            attribute Iyz : Real = -707.518146904729;
                            attribute sigma_Iyz : Real = 1721.9966813638534;
                            part <'C.1.1.4.5.4.1.1'> 'Part 716' {
                                attribute POIconv : String = "-";
                                attribute Ipoint : Boolean = false;
                                attribute mass : Real = 0.9259354616964701;
                                attribute sigma_mass : Real = 0.28909372274994966;
                                attribute Cx : Real = -51.72942406497896;
                                attribute sigma_Cx : Real = 28.721044428837228;
                                attribute Cy : Real = -43.71386934071779;
                                attribute sigma_Cy : Real = 28.23690002309109;
                                attribute Cz : Real = -16.282848082482815;
                                attribute sigma_Cz : Real = 29.057750463592832;
                                attribute Ixx : Real = 1.0924638848352082;
                                attribute sigma_Ixx : Real = 0.37074144170588635;
                                attribute Iyy : Real = 1.211918824464876;
                                attribute sigma_Iyy : Real = 0.3723953238821935;
                                attribute Izz : Real = 1.271129048401201;
                                attribute sigma_Izz : Real = 0.37017423652493897;
                                attribute Ixy : Real = 0.006718772955328196;
                                attribute sigma_Ixy : Real = 0.02351283871158888;
                                attribute Ixz : Real = 0.02603137210770866;
                                attribute sigma_Ixz : Real = 0.022566176940390956;
                                attribute Iyz : Real = 0.03153346825570205;
                                attribute sigma_Iyz : Real = 0.02209918015384651;
                            }
                            part <'C.1.1.4.5.4.1.2'> 'Part 717' {
                                attribute POIconv : String = "-";
                                attribute Ipoint : Boolean = false;
                                attribute mass : Real = 0.9072328777022194;
                                attribute sigma_mass : Real = 0.28909372274994966;
                                attribute Cx : Real = -76.86035190708935;
                                attribute sigma_Cx : Real = 28.721044428837228;
                                attribute Cy : Real = -47.28317493572831;
                                attribute sigma_Cy : Real = 28.23690002309109;
                                attribute Cz : Real = -20.996416732668877;
                                attribute sigma_Cz : Real = 29.057750463592832;
                                attribute Ixx : Real = 1.2367202334305931;
                                attribute sigma_Ixx : Real = 0.37074144170588635;
                                attribute Iyy : Real = 1.2286135826014641;
                                attribute sigma_Iyy : Real = 0.3723953238821935;
                                attribute Izz : Real = 1.034130595483409;
                                attribute sigma_Izz : Real = 0.37017423652493897;
                                attribute Ixy : Real = 0.0024152447610838717;
                                attribute sigma_Ixy : Real = 0.02351283871158888;
                                attribute Ixz : Real = -0.015981770434105085;
                                attribute sigma_Ixz : Real = 0.022566176940390956;
                                attribute Iyz : Real = 0.039729520205721056;
                                attribute sigma_Iyz : Real = 0.02209918015384651;
                            }
                            part <'C.1.1.4.5.4.1.3'> 'Part 718' {
                                attribute POIconv : String = "-";
                                attribute Ipoint : Boolean = false;
                                attribute mass : Real = 0.1147620219362434;
                                attribute sigma_mass : Real = 0.28909372274994966;
                                attribute Cx : Real = 99.79253225028515;
                                attribute sigma_Cx : Real = 28.721044428837228;
                                attribute Cy : Real = 51.211427338421345;
                                attribute sigma_Cy : Real = 28.23690002309109;
                                attribute Cz : Real = 48.40501071885228;
                                attribute sigma_Cz : Real = 29.057750463592832;
                                attribute Ixx : Real = 0.12662861052477048;
                                attribute sigma_Ixx : Real = 0.37074144170588635;
                                attribute Iyy : Real = 0.1600645038280774;
                                attribute sigma_Iyy : Real = 0.3723953238821935;
                                attribute Izz : Real = 0.14479687869142938;
                                attribute sigma_Izz : Real = 0.37017423652493897;
                                attribute Ixy : Real = -0.008291928043095746;
                                attribute sigma_Ixy : Real = 0.02351283871158888;
                                attribute Ixz : Real = -1.8345692514096145e-05;
                                attribute sigma_Ixz : Real = 0.022566176940390956;
                                attribute Iyz : Real = 0.0021275951646355174;
                                attribute sigma_Iyz : Real = 0.02209918015384651;
                            }
                        }
                        part <'C.1.1.4.5.4.2'> 'Subassembly 204' {
                            attribute POIconv : String = "-";
                            attribute Ipoint : Boolean = false;
                            attribute mass : Real = 2.942194352627732;
                            attribute sigma_mass : Real = 0.6464332159373649;
                            attribute Cx : Real = 5.242143091199958;
                            attribute sigma_Cx : Real = 16.76759741515106;
                            attribute Cy : Real = 59.48363924493132;
                            attribute sigma_Cy : Real = 20.499494590316594;
                            attribute Cz : Real = 19.8939121436059;
                            attribute sigma_Cz : Real = 21.525683931871722;
                            attribute Ixx : Real = 15659.58990661004;
                            attribute sigma_Ixx : Real = 10016.065363162095;
                            attribute Iyy : Real = 13947.409262756286;
                            attribute sigma_Iyy : Real = 7464.90178860099;
                            attribute Izz : Real = 5338.785813945078;
                            attribute sigma_Izz : Real = 6005.435557455286;
                            attribute Ixy : Real = -174.0462933182655;
                            attribute sigma_Ixy : Real = 2032.932021031025;
                            attribute Ixz : Real = -4061.0227727202932;
                            attribute sigma_Ixz : Real = 3395.052798445443;
                            attribute Iyz : Real = 1404.9050611423704;
                            attribute sigma_Iyz : Real = 4747.331018570032;
                            part <'C.1.1.4.5.4.2.1'> 'Part 719' {
                                attribute POIconv : String = "-";
                                attribute Ipoint : Boolean = false;
                                attribute mass : Real = 0.028702711908379572;
                                attribute sigma_mass : Real = 0.28909372274994966;
                                attribute Cx : Real = 24.50151718221605;
                                attribute sigma_Cx : Real = 28.721044428837228;
                                attribute Cy : Real = 79.14099269546568;
                                attribute sigma_Cy : Real = 28.23690002309109;
                                attribute Cz : Real = 50.49227578565478;
                                attribute sigma_Cz : Real = 29.057750463592832;
                                attribute Ixx : Real = 0.036951328468088664;
                                attribute sigma_Ixx : Real = 0.37074144170588635;
                                attribute Iyy : Real = 0.03882815193442854;
                                attribute sigma_Iyy : Real = 0.3723953238821935;
                                attribute Izz : Real = 0.0373987646627077;
                                attribute sigma_Izz : Real = 0.37017423652493897;
                                attribute Ixy : Real = -0.0028158179495523837;
                                attribute sigma_Ixy : Real = 0.02351283871158888;
                                attribute Ixz : Real = 0.0005120233063638329;
                                attribute sigma_Ixz : Real = 0.022566176940390956;
                                attribute Iyz : Real = -0.0005901302212767127;
                                attribute sigma_Iyz : Real = 0.02209918015384651;
                            }
                            part <'C.1.1.4.5.4.2.2'> 'Part 720' {
                                attribute POIconv : String = "-";
                                attribute Ipoint : Boolean = false;
                                attribute mass : Real = 0.928666933874134;
                                attribute sigma_mass : Real = 0.28909372274994966;
                                attribute Cx : Real = 8.624161453917623;
                                attribute sigma_Cx : Real = 28.721044428837228;
                                attribute Cy : Real = 30.25789698585868;
                                attribute sigma_Cy : Real = 28.23690002309109;
                                attribute Cz : Real = 74.44659322500229;
                                attribute sigma_Cz : Real = 29.057750463592832;
                                attribute Ixx : Real = 0.8939526394370166;
                                attribute sigma_Ixx : Real = 0.37074144170588635;
                                attribute Iyy : Real = 0.9895436094298773;
                                attribute sigma_Iyy : Real = 0.3723953238821935;
                                attribute Izz : Real = 1.058939498548267;
                                attribute sigma_Izz : Real = 0.37017423652493897;
                                attribute Ixy : Real = -0.06481420555728551;
                                attribute sigma_Ixy : Real = 0.02351283871158888;
                                attribute Ixz : Real = 0.023580854704829582;
                                attribute sigma_Ixz : Real = 0.022566176940390956;
                                attribute Iyz : Real = 0.04182024600706466;
                                attribute sigma_Iyz : Real = 0.02209918015384651;
                            }
                            part <'C.1.1.4.5.4.2.3'> 'Part 721' {
                                attribute POIconv : String = "+";
                                attribute Ipoint : Boolean = false;
                                attribute mass : Real = 0.9005303944807965;
                                attribute sigma_mass : Real = 0.28909372274994966;
                                attribute Cx : Real = 36.270047817379236;
                                attribute sigma_Cx : Real = 28.721044428837228;
                                attribute Cy : Real = 77.9579265974462;
                                attribute sigma_Cy : Real = 28.23690002309109;
                                attribute Cz : Real = 63.555475417524576;
                                attribute sigma_Cz : Real = 29.057750463592832;
                                attribute Ixx : Real = 1.0151262404443149;
                                attribute sigma_Ixx : Real = 0.37074144170588635;
                                attribute Iyy : Real = 1.19067801315242;
                                attribute sigma_Iyy : Real = 0.3723953238821935;
                                attribute Izz : Real = 1.0297584526064287;
                                attribute sigma_Izz : Real = 0.37017423652493897;
                                attribute Ixy : Real = -0.02691426775585533;
                                attribute sigma_Ixy : Real = 0.02351283871158888;
                                attribute Ixz : Real = -0.007695531168624236;
                                attribute sigma_Ixz : Real = 0.022566176940390956;
                                attribute Iyz : Real = -0.05802696207369526;
                                attribute sigma_Iyz : Real = 0.02209918015384651;
                            }
                            part <'C.1.1.4.5.4.2.4'> 'Part 722' {
                                attribute POIconv : String = "+";
                                attribute Ipoint : Boolean = false;
                                attribute mass : Real = 0.9725461800792254;
                                attribute sigma_mass : Real = 0.28909372274994966;
                                attribute Cx : Real = -23.739759856835008;
                                attribute sigma_Cx : Real = 28.721044428837228;
                                attribute Cy : Real = 84.33448066934943;
                                attribute sigma_Cy : Real = 28.23690002309109;
                                attribute Cz : Real = -62.785498797893524;
                                attribute sigma_Cz : Real = 29.057750463592832;
                                attribute Ixx : Real = 1.135198949647473;
                                attribute sigma_Ixx : Real = 0.37074144170588635;
                                attribute Iyy : Real = 1.0366610196989163;
                                attribute sigma_Iyy : Real = 0.3723953238821935;
                                attribute Izz : Real = 1.034243141762496;
                                attribute sigma_Izz : Real = 0.37017423652493897;
                                attribute Ixy : Real = 0.04517955457035574;
                                attribute sigma_Ixy : Real = 0.02351283871158888;
                                attribute Ixz : Real = -0.052405426816877675;
                                attribute sigma_Ixz : Real = 0.022566176940390956;
                                attribute Iyz : Real = 0.02511730996482605;
                                attribute sigma_Iyz : Real = 0.02209918015384651;
                            }
                            part <'C.1.1.4.5.4.2.5'> 'Part 723' {
                                attribute POIconv : String = "-";
                                attribute Ipoint : Boolean = false;
                                attribute mass : Real = 0.11174813228519634;
                                attribute sigma_mass : Real = 0.28909372274994966;
                                attribute Cx : Real = -25.62098721973598;
                                attribute sigma_Cx : Real = 28.721044428837228;
                                attribute Cy : Real = -67.84275793470442;
                                attribute sigma_Cy : Real = 28.23690002309109;
                                attribute Cz : Real = -73.60694906674325;
                                attribute sigma_Cz : Real = 29.057750463592832;
                                attribute Ixx : Real = 0.1268050948982667;
                                attribute sigma_Ixx : Real = 0.37074144170588635;
                                attribute Iyy : Real = 0.1285769699437629;
                                attribute sigma_Iyy : Real = 0.3723953238821935;
                                attribute Izz : Real = 0.12524686835849153;
                                attribute sigma_Izz : Real = 0.37017423652493897;
                                attribute Ixy : Real = -0.0006688257820647342;
                                attribute sigma_Ixy : Real = 0.02351283871158888;
                                attribute Ixz : Real = 0.014219180141157113;
                                attribute sigma_Ixz : Real = 0.022566176940390956;
                                attribute Iyz : Real = -0.004739797753517275;
                                attribute sigma_Iyz : Real = 0.02209918015384651;
                            }
                        }
                        part <'C.1.1.4.5.4.3'> 'Subassembly 205' {
                            attribute POIconv : String = "-";
                            attribute Ipoint : Boolean = false;
                            attribute mass : Real = 1.4516685543609784;
                            attribute sigma_mass : Real = 0.5007250159521434;
                            attribute Cx : Real = 44.929616552389945;
                            attribute sigma_Cx : Real = 34.781952032180754;
                            attribute Cy : Real = -20.225508124202058;
                            attribute sigma_Cy : Real = 28.844735519315964;
                            attribute Cz : Real = -7.5116079556919795;
                            attribute sigma_Cz : Real = 23.73258667804116;
                            attribute Ixx : Real = 4724.532412570125;
                            attribute sigma_Ixx : Real = 3851.6616322776003;
                            attribute Iyy : Real = 4284.660487020742;
                            attribute sigma_Iyy : Real = 5447.681403824892;
                            attribute Izz : Real = 6888.362927793647;
                            attribute sigma_Izz : Real = 6783.1456683379465;
                            attribute Ixy : Real = -2548.230205613605;
                            attribute sigma_Ixy : Real = 2907.7301847647154;
                            attribute Ixz : Real = -1745.7181266039615;
                            attribute sigma_Ixz : Real = 1798.6324588135908;
                            attribute Iyz : Real = -1813.5807200689105;
                            attribute sigma_Iyz : Real = 1794.9947393601608;
                            part <'C.1.1.4.5.4.3.1'> 'Part 724' {
                                attribute POIconv : String = "+";
                                attribute Ipoint : Boolean = false;
                                attribute mass : Real = 0.4168300075104926;
                                attribute sigma_mass : Real = 0.28909372274994966;
                                attribute Cx : Real = -14.283385733142495;
                                attribute sigma_Cx : Real = 28.721044428837228;
                                attribute Cy : Real = -99.07091353088617;
                                attribute sigma_Cy : Real = 28.23690002309109;
                                attribute Cz : Real = -48.003824427723885;
                                attribute sigma_Cz : Real = 29.057750463592832;
                                attribute Ixx : Real = 0.5497097266084952;
                                attribute sigma_Ixx : Real = 0.37074144170588635;
                                attribute Iyy : Real = 0.4692175753310004;
                                attribute sigma_Iyy : Real = 0.3723953238821935;
                                attribute Izz : Real = 0.5430888928451009;
                                attribute sigma_Izz : Real = 0.37017423652493897;
                                attribute Ixy : Real = 0.03498809085352045;
                                attribute sigma_Ixy : Real = 0.02351283871158888;
                                attribute Ixz : Real = -0.014878268435043179;
                                attribute sigma_Ixz : Real = 0.022566176940390956;
                                attribute Iyz : Real = -0.04478471650908063;
                                attribute sigma_Iyz : Real = 0.02209918015384651;
                            }
                            part <'C.1.1.4.5.4.3.2'> 'Part 725' {
                                attribute POIconv : String = "+";
                                attribute Ipoint : Boolean = false;
                                attribute mass : Real = 0.05277869777567685;
                                attribute sigma_mass : Real = 0.28909372274994966;
                                attribute Cx : Real = -76.45711689256132;
                                attribute sigma_Cx : Real = 28.721044428837228;
                                attribute Cy : Real = 34.03611145913601;
                                attribute sigma_Cy : Real = 28.23690002309109;
                                attribute Cz : Real = -33.76581915654242;
                                attribute sigma_Cz : Real = 29.057750463592832;
                                attribute Ixx : Real = 0.07567515528552089;
                                attribute sigma_Ixx : Real = 0.37074144170588635;
                                attribute Iyy : Real = 0.07567744386322818;
                                attribute sigma_Iyy : Real = 0.3723953238821935;
                                attribute Izz : Real = 0.08759773308281037;
                                attribute sigma_Izz : Real = 0.37017423652493897;
                                attribute Ixy : Real = 1.1607197599555166e-06;
                                attribute sigma_Ixy : Real = 0.02351283871158888;
                                attribute Ixz : Real = 0.00017214346146315752;
                                attribute sigma_Ixz : Real = 0.022566176940390956;
                                attribute Iyz : Real = -0.00015290859179811018;
                                attribute sigma_Iyz : Real = 0.02209918015384651;
                            }
                            part <'C.1.1.4.5.4.3.3'> 'Part 726' {
                                attribute POIconv : String = "+";
                                attribute Ipoint : Boolean = false;
                                attribute mass : Real = 0.9820598490748089;
                                attribute sigma_mass : Real = 0.28909372274994966;
                                attribute Cx : Real = 76.58592541702092;
                                attribute sigma_Cx : Real = 28.721044428837228;
                                attribute Cy : Real = 10.32382482662797;
                                attribute sigma_Cy : Real = 28.23690002309109;
                                attribute Cz : Real = 11.086071189492941;
                                attribute sigma_Cz : Real = 29.057750463592832;
                                attribute Ixx : Real = 1.2352330856583003;
                                attribute sigma_Ixx : Real = 0.37074144170588635;
                                attribute Iyy : Real = 1.319911151793171;
                                attribute sigma_Iyy : Real = 0.3723953238821935;
                                attribute Izz : Real = 1.2463314898424065;
                                attribute sigma_Izz : Real = 0.37017423652493897;
                                attribute Ixy : Real = 0.056891119545845095;
                                attribute sigma_Ixy : Real = 0.02351283871158888;
                                attribute Ixz : Real = -0.05919706189432759;
                                attribute sigma_Ixz : Real = 0.022566176940390956;
                                attribute Iyz : Real = 0.07792969714656524;
                                attribute sigma_Iyz : Real = 0.02209918015384651;
                            }
                        }
                        part <'C.1.1.4.5.4.4'> 'Subassembly 206' {
                            attribute POIconv : String = "-";
                            attribute Ipoint : Boolean = false;
                            attribute mass : Real = 2.2502805188901256;
                            attribute sigma_mass : Real = 0.5781874454998993;
                            attribute Cx : Real = -4.123733226722783;
                            attribute sigma_Cx : Real = 26.2700791975108;
                            attribute Cy : Real = -20.86659148932034;
                            attribute sigma_Cy : Real = 20.457073333100222;
                            attribute Cz : Real = -42.838870949720636;
                            attribute sigma_Cz : Real = 20.857621879208253;
                            attribute Ixx : Real = 10904.051029700639;
                            attribute sigma_Ixx : Real = 6038.97977173752;
                            attribute Iyy : Real = 17242.286614847286;
                            attribute sigma_Iyy : Real = 8362.061031059462;
                            attribute Izz : Real = 17405.92971697631;
                            attribute sigma_Izz : Real = 8330.03144805456;
                            attribute Ixy : Real = -7886.227957994629;
                            attribute sigma_Ixy : Real = 3936.4954541843454;
                            attribute Ixz : Real = 6618.156800184548;
                            attribute sigma_Ixz : Real = 3921.4195129327327;
                            attribute Iyz : Real = 4798.596263275697;
                            attribute sigma_Iyz : Real = 2971.9983879716883;
                            part <'C.1.1.4.5.4.4.1'> 'Part 727' {
                                attribute POIconv : String = "-";
                                attribute Ipoint : Boolean = false;
                                attribute mass : Real = 0.9679883005630691;
                                attribute sigma_mass : Real = 0.28909372274994966;
                                attribute Cx : Real = -23.69741532020271;
                                attribute sigma_Cx : Real = 28.721044428837228;
                                attribute Cy : Real = -28.017089562490582;
                                attribute sigma_Cy : Real = 28.23690002309109;
                                attribute Cz : Real = -62.21753763966262;
                                attribute sigma_Cz : Real = 29.057750463592832;
                                attribute Ixx : Real = 1.3383063645782607;
                                attribute sigma_Ixx : Real = 0.37074144170588635;
                                attribute Iyy : Real = 1.255114206859061;
                                attribute sigma_Iyy : Real = 0.3723953238821935;
                                attribute Izz : Real = 1.2460074778371693;
                                attribute sigma_Izz : Real = 0.37017423652493897;
                                attribute Ixy : Real = 0.06867246262344523;
                                attribute sigma_Ixy : Real = 0.02351283871158888;
                                attribute Ixz : Real = -0.06883853919434785;
                                attribute sigma_Ixz : Real = 0.022566176940390956;
                                attribute Iyz : Real = 0.07667324795403546;
                                attribute sigma_Iyz : Real = 0.02209918015384651;
                            }
                            part <'C.1.1.4.5.4.4.2'> 'Part 728' {
                                attribute POIconv : String = "-";
                                attribute Ipoint : Boolean = false;
                                attribute mass : Real = 0.5458135985324625;
                                attribute sigma_mass : Real = 0.28909372274994966;
                                attribute Cx : Real = -97.94251257553697;
                                attribute sigma_Cx : Real = 28.721044428837228;
                                attribute Cy : Real = -88.97118531167507;
                                attribute sigma_Cy : Real = 28.23690002309109;
                                attribute Cz : Real = 41.8939096853137;
                                attribute sigma_Cz : Real = 29.057750463592832;
                                attribute Ixx : Real = 0.5382167557069855;
                                attribute sigma_Ixx : Real = 0.37074144170588635;
                                attribute Iyy : Real = 0.6619471992858849;
                                attribute sigma_Iyy : Real = 0.3723953238821935;
                                attribute Izz : Real = 0.6689725073341343;
                                attribute sigma_Izz : Real = 0.37017423652493897;
                                attribute Ixy : Real = 0.03512038716917919;
                                attribute sigma_Ixy : Real = 0.02351283871158888;
                                attribute Ixz : Real = 0.059161951153099884;
                                attribute sigma_Ixz : Real = 0.022566176940390956;
                                attribute Iyz : Real = -0.02083720483697001;
                                attribute sigma_Iyz : Real = 0.02209918015384651;
                            }
                            part <'C.1.1.4.5.4.4.3'> 'Part 729' {
                                attribute POIconv : String = "-";
                                attribute Ipoint : Boolean = false;
                                attribute mass : Real = 0.6791087179814931;
                                attribute sigma_mass : Real = 0.28909372274994966;
                                attribute Cx : Real = 92.34358565881848;
                                attribute sigma_Cx : Real = 28.721044428837228;
                                attribute Cy : Real = 44.98140406794846;
                                attribute sigma_Cy : Real = 28.23690002309109;
                                attribute Cz : Real = -82.79626253060997;
                                attribute sigma_Cz : Real = 29.057750463592832;
                                attribute Ixx : Real = 0.9166713651258287;
                                attribute sigma_Ixx : Real = 0.37074144170588635;
                                attribute Iyy : Real = 0.9950820915552686;
                                attribute sigma_Iyy : Real = 0.3723953238821935;
                                attribute Izz : Real = 0.8846571007402796;
                                attribute sigma_Izz : Real = 0.37017423652493897;
                                attribute Ixy : Real = -0.05896341081210538;
                                attribute sigma_Ixy : Real = 0.02351283871158888;
                                attribute Ixz : Real = 0.0010311795524071917;
                                attribute sigma_Ixz : Real = 0.022566176940390956;
                                attribute Iyz : Real = -0.0072754479997270355;
                                attribute sigma_Iyz : Real = 0.02209918015384651;
                            }
                            part <'C.1.1.4.5.4.4.4'> 'Part 730' {
                                attribute POIconv : String = "-";
                                attribute Ipoint : Boolean = false;
                                attribute mass : Real = 0.057369901813101025;
                                attribute sigma_mass : Real = 0.28909372274994966;
                                attribute Cx : Real = 76.80482738651335;
                                attribute sigma_Cx : Real = 28.721044428837228;
                                attribute Cy : Real = -31.74225827679038;
                                attribute sigma_Cy : Real = 28.23690002309109;
                                attribute Cz : Real = -49.01925986632705;
                                attribute sigma_Cz : Real = 29.057750463592832;
                                attribute Ixx : Real = 0.06952625605585436;
                                attribute sigma_Ixx : Real = 0.37074144170588635;
                                attribute Iyy : Real = 0.08069026843191593;
                                attribute sigma_Iyy : Real = 0.3723953238821935;
                                attribute Izz : Real = 0.06871774520129935;
                                attribute sigma_Izz : Real = 0.37017423652493897;
                                attribute Ixy : Real = 0.005131710382125855;
                                attribute sigma_Ixy : Real = 0.02351283871158888;
                                attribute Ixz : Real = 0.00023080825890815342;
                                attribute sigma_Ixz : Real = 0.022566176940390956;
                                attribute Iyz : Real = 0.0007136671413002496;
                                attribute sigma_Iyz : Real = 0.02209918015384651;
                            }
                        }
                    }
                }
            }
        }
        part <'C.1.2'> 'Segment 2' {
            attribute POIconv : String = "-";
            attribute Ipoint : Boolean = false;
            attribute mass : Real = 266.3865596487843;
            attribute sigma_mass : Real = 6.699244132471146;
            attribute Cx : Real = -1.5287156843419805;
            attribute sigma_Cx : Real = 2.142504440485087;
            attribute Cy : Real = -1.602139923411377;
            attribute sigma_Cy : Real = 2.099954289911099;
            attribute Cz : Real = 0.6943022415077745;
            attribute sigma_Cz : Real = 2.132440048978046;
            attribute Ixx : Real = 1758962.1376963435;
            attribute sigma_Ixx : Real = 86341.37744085681;
            attribute Iyy : Real = 1777634.2141295988;
            attribute sigma_Iyy : Real = 88008.50895984579;
            attribute Izz : Real = 1762878.7556889555;
            attribute sigma_Izz : Real = 87517.1937377702;
            attribute Ixy : Real = -19969.6188961804;
            attribute sigma_Ixy : Real = 40512.885604667106;
            attribute Ixz : Real = -22222.91470757852;
            attribute sigma_Ixz : Real = 40934.36241274292;
            attribute Iyz : Real = -44886.683826933295;
            attribute sigma_Iyz : Real = 40579.63336983919;
            part <'C.1.2.1'> 'Element 5' {
                attribute POIconv : String = "-";
                attribute Ipoint : Boolean = false;
                attribute mass : Real = 92.11771942176436;
                attribute sigma_mass : Real = 3.921458047480574;
                attribute Cx : Real = -0.9899767172142269;
                attribute sigma_Cx : Real = 3.7040338771264585;
                attribute Cy : Real = -0.40209260467488867;
                attribute sigma_Cy : Real = 3.4785584273251517;
                attribute Cz : Real = -2.46618940387303;
                attribute sigma_Cz : Real = 3.640706871042598;
                attribute Ixx : Real = 581928.498839205;
                attribute sigma_Ixx : Real = 48677.96569695046;
                attribute Iyy : Real = 642466.3321320936;
                attribute sigma_Iyy : Real = 54131.56157075486;
                attribute Izz : Real = 574392.7412442162;
                attribute sigma_Izz : Real = 51052.85021413074;
                attribute Ixy : Real = 12446.310332638699;
                attribute sigma_Ixy : Real = 23217.02876921234;
                attribute Ixz : Real = 5351.939952034734;
                attribute sigma_Ixz : Real = 25005.815215402854;
                attribute Iyz : Real = -11841.401293655188;
                attribute sigma_Iyz : Real = 22810.483373418756;
                part <'C.1.2.1.1'> 'Subsystem 16' {
                    attribute POIconv : String = "-";
                    attribute Ipoint : Boolean = false;
                    attribute mass : Real = 24.84054889836488;
                    attribute sigma_mass : Real = 1.9819267103177565;
                    attribute Cx : Real = -10.659355322243258;
                    attribute sigma_Cx : Real = 6.898342504254546;
                    attribute Cy : Real = 1.6325081484234196;
                    attribute sigma_Cy : Real = 6.165335724960494;
                    attribute Cz : Real = -11.40889281612488;
                    attribute sigma_Cz : Real = 7.372131267871263;
                    attribute Ixx : Real = 167612.17161635612;
                    attribute sigma_Ixx : Real = 25260.237764318576;
                    attribute Iyy : Real = 189794.86231765818;
                    attribute sigma_Iyy : Real = 29189.97936888452;
                    attribute Izz : Real = 130926.06476349535;
                    attribute sigma_Izz : Real = 23260.18642141626;
                    attribute Ixy : Real = -6688.052580646998;
                    attribute sigma_Ixy : Real = 10715.893586454526;
                    attribute Ixz : Real = 23739.18880972491;
                    attribute sigma_Ixz : Real = 13642.626986189827;
                    attribute Iyz : Real = -644.7822551584895;
                    attribute sigma_Iyz : Real = 11713.936533339807;
                    part <'C.1.2.1.1.1'> 'Assembly 58' {
                        attribute POIconv : String = "-";
                        attribute Ipoint : Boolean = false;
                        attribute mass : Real = 4.50699752832111;
                        attribute sigma_mass : Real = 0.8672811682498489;
                        attribute Cx : Real = -12.806800302346216;
                        attribute sigma_Cx : Real = 17.30201792820827;
                        attribute Cy : Real = 17.446850983387417;
                        attribute sigma_Cy : Real = 14.308573062048657;
                        attribute Cz : Real = -13.7621833679598;
                        attribute sigma_Cz : Real = 18.027880630890337;
                        attribute Ixx : Real = 32088.43693847803;
                        attribute sigma_Ixx : Real = 10642.066243791009;
                        attribute Iyy : Real = 31771.24128126083;
                        attribute sigma_Iyy : Real = 12823.925387838362;
                        attribute Izz : Real = 20009.699877105253;
                        attribute sigma_Izz : Real = 9782.310123666222;
                        attribute Ixy : Real = -87.87611306424242;
                        attribute sigma_Ixy : Real = 4031.330455617396;
                        attribute Ixz : Real = 11744.722596098582;
                        attribute sigma_Ixz : Real = 5914.589666031073;
                        attribute Iyz : Real = 3619.0990125372823;
                        attribute sigma_Iyz : Real = 5096.283011914762;
                        part <'C.1.2.1.1.1.1'> 'Subassembly 207' {
                            attribute POIconv : String = "-";
                            attribute Ipoint : Boolean = false;
                            attribute mass : Real = 1.1447987995315343;
                            attribute sigma_mass : Real = 0.5007250159521434;
                            attribute Cx : Real = -44.03993237401911;
                            attribute sigma_Cx : Real = 40.105000434284065;
                            attribute Cy : Real = -14.337081307710639;
                            attribute sigma_Cy : Real = 25.798572990548802;
                            attribute Cz : Real = -0.3937326350292246;
                            attribute sigma_Cz : Real = 39.90228787277825;
                            attribute Ixx : Real = 8907.737632064858;
                            attribute sigma_Ixx : Real = 5751.769153159397;
                            attribute Iyy : Real = 9900.932576300358;
                            attribute sigma_Iyy : Real = 8058.624278895026;
                            attribute Izz : Real = 5088.253889560365;
                            attribute sigma_Izz : Real = 5570.618010488907;
                            attribute Ixy : Real = -1871.0176456873646;
                            attribute sigma_Ixy : Real = 1541.7789405336814;
                            attribute Ixz : Real = 3968.2994906523327;
                            attribute sigma_Ixz : Real = 3487.0211841417754;
                            attribute Iyz : Real = 3668.6539656123987;
                            attribute sigma_Iyz : Real = 2576.9195760278026;
                            part <'C.1.2.1.1.1.1.1'> 'Part 731' {
                                attribute POIconv : String = "+";
                                attribute Ipoint : Boolean = false;
                                attribute mass : Real = 0.6804637058416847;
                                attribute sigma_mass : Real = 0.28909372274994966;
                                attribute Cx : Real = -82.76614844799042;
                                attribute sigma_Cx : Real = 28.721044428837228;
                                attribute Cy : Real = -47.76298082433641;
                                attribute sigma_Cy : Real = 28.23690002309109;
                                attribute Cz : Real = 63.294122368097305;
                                attribute sigma_Cz : Real = 29.057750463592832;
                                attribute Ixx : Real = 0.7629432285981665;
                                attribute sigma_Ixx : Real = 0.37074144170588635;
                                attribute Iyy : Real = 0.8421712701444337;
                                attribute sigma_Iyy : Real = 0.3723953238821935;
                                attribute Izz : Real = 0.7932281294553125;
                                attribute sigma_Izz : Real = 0.37017423652493897;
                                attribute Ixy : Real = -0.040747429195994375;
                                attribute sigma_Ixy : Real = 0.02351283871158888;
                                attribute Ixz : Real = 0.07982067472193621;
                                attribute sigma_Ixz : Real = 0.022566176940390956;
                                attribute Iyz : Real = -0.03702446897993501;
                                attribute sigma_Iyz : Real = 0.02209918015384651;
                            }
                            part <'C.1.2.1.1.1.1.2'> 'Part 732' {
                                attribute POIconv : String = "+";
                                attribute Ipoint : Boolean = false;
                                attribute mass : Real = 0.0872471402049996;
                                attribute sigma_mass : Real = 0.28909372274994966;
                                attribute Cx : Real = 82.55250179208815;
                                attribute sigma_Cx : Real = 28.721044428837228;
                                attribute Cy : Real = -5.411630170419812;
                                attribute sigma_Cy : Real = 28.23690002309109;
                                attribute Cz : Real = -71.15427576936781;
                                attribute sigma_Cz : Real = 29.057750463592832;
                                attribute Ixx : Real = 0.11257619230429793;
                                attribute sigma_Ixx : Real = 0.37074144170588635;
                                attribute Iyy : Real = 0.1246403998381112;
                                attribute sigma_Iyy : Real = 0.3723953238821935;
                                attribute Izz : Real = 0.11991330708654552;
                                attribute sigma_Izz : Real = 0.37017423652493897;
                                attribute Ixy : Real = -0.0032220311242106107;
                                attribute sigma_Ixy : Real = 0.02351283871158888;
                                attribute Ixz : Real = 0.0026909518310395584;
                                attribute sigma_Ixz : Real = 0.022566176940390956;
                                attribute Iyz : Real = -0.0017268308576099392;
                                attribute sigma_Iyz : Real = 0.02209918015384651;
                            }
                            part <'C.1.2.1.1.1.1.3'> 'Part 733' {
                                attribute POIconv : String = "-";
                                attribute Ipoint : Boolean = false;
                                attribute mass : Real = 0.37708795348485;
                                attribute sigma_mass : Real = 0.28909372274994966;
                                attribute Cx : Real = -3.4473955165594816;
                                attribute sigma_Cx : Real = 28.721044428837228;
                                attribute Cy : Real = 43.91561853699386;
                                attribute sigma_Cy : Real = 28.23690002309109;
                                attribute Cz : Real = -98.94797829911113;
                                attribute sigma_Cz : Real = 29.057750463592832;
                                attribute Ixx : Real = 0.49265900196150153;
                                attribute sigma_Ixx : Real = 0.37074144170588635;
                                attribute Iyy : Real = 0.3794068111394347;
                                attribute sigma_Iyy : Real = 0.3723953238821935;
                                attribute Izz : Real = 0.46816149458660183;
                                attribute sigma_Izz : Real = 0.37017423652493897;
                                attribute Ixy : Real = 0.022108336751683156;
                                attribute sigma_Ixy : Real = 0.02351283871158888;
                                attribute Ixz : Real = -0.010211977595304967;
                                attribute sigma_Ixz : Real = 0.022566176940390956;
                                attribute Iyz : Real = 0.04406619851694948;
                                attribute sigma_Iyz : Real = 0.02209918015384651;
                            }
                        }
                        part <'C.1.2.1.1.1.2'> 'Subassembly 208' {
                            attribute POIconv : String = "-";
                            attribute Ipoint : Boolean = false;
                            attribute mass : Real = 1.4672204708249774;
                            attribute sigma_mass : Real = 0.40884026350990615;
                            attribute Cx : Real = -1.6252680653858438;
                            attribute sigma_Cx : Real = 20.73832809344051;
                            attribute Cy : Real = 54.648169069729015;
                            attribute sigma_Cy : Real = 22.204372281831247;
                            attribute Cz : Real = -20.8694310305034;
                            attribute sigma_Cz : Real = 26.08279899857504;
                            attribute Ixx : Real = 5689.374876836684;
                            attribute sigma_Ixx : Real = 4084.726184441792;
                            attribute Iyy : Real = 4330.357589708461;
                            attribute sigma_Iyy : Real = 3498.802247289625;
                            attribute Izz : Real = 1463.5897409464792;
                            attribute sigma_Izz : Real = 1876.1059678293623;
                            attribute Ixy : Real = -269.5826294992185;
                            attribute sigma_Ixy : Real = 927.1531871412849;
                            attribute Ixz : Real = 469.4951513862253;
                            attribute sigma_Ixz : Real = 1596.6615385159196;
                            attribute Iyz : Real = 2456.2458343274316;
                            attribute sigma_Iyz : Real = 1966.5752788946656;
                            part <'C.1.2.1.1.1.2.1'> 'Part 734' {
                                attribute POIconv : String = "+";
                                attribute Ipoint : Boolean = false;
                                attribute mass : Real = 0.5951115685270634;
                                attribute sigma_mass : Real = 0.28909372274994966;
                                attribute Cx : Real = 5.548908468335867;
                                attribute sigma_Cx : Real = 28.721044428837228;
                                attribute Cy : Real = 92.18274871818721;
                                attribute sigma_Cy : Real = 28.23690002309109;
                                attribute Cz : Real = -86.23134288936853;
                                attribute sigma_Cz : Real = 29.057750463592832;
                                attribute Ixx : Real = 0.6239526384625814;
                                attribute sigma_Ixx : Real = 0.37074144170588635;
                                attribute Iyy : Real = 0.5989152296145334;
                                attribute sigma_Iyy : Real = 0.3723953238821935;
                                attribute Izz : Real = 0.6269662989457233;
                                attribute sigma_Izz : Real = 0.37017423652493897;
                                attribute Ixy : Real = -0.004337172890690839;
                                attribute sigma_Ixy : Real = 0.02351283871158888;
                                attribute Ixz : Real = 0.021114383488938397;
                                attribute sigma_Ixz : Real = 0.022566176940390956;
                                attribute Iyz : Real = 0.016508367062713213;
                                attribute sigma_Iyz : Real = 0.02209918015384651;
                            }
                            part <'C.1.2.1.1.1.2.2'> 'Part 735' {
                                attribute POIconv : String = "+";
                                attribute Ipoint : Boolean = false;
                                attribute mass : Real = 0.872108902297914;
                                attribute sigma_mass : Real = 0.28909372274994966;
                                attribute Cx : Real = -6.520798243582249;
                                attribute sigma_Cx : Real = 28.721044428837228;
                                attribute Cy : Real = 29.035241017118096;
                                attribute sigma_Cy : Real = 28.23690002309109;
                                attribute Cz : Real = 23.73237246647477;
                                attribute sigma_Cz : Real = 29.057750463592832;
                                attribute Ixx : Real = 0.8805630776543457;
                                attribute sigma_Ixx : Real = 0.37074144170588635;
                                attribute Iyy : Real = 0.8999397241871576;
                                attribute sigma_Iyy : Real = 0.3723953238821935;
                                attribute Izz : Real = 0.8894808707558973;
                                attribute sigma_Izz : Real = 0.37017423652493897;
                                attribute Ixy : Real = -0.017241277974757066;
                                attribute sigma_Ixy : Real = 0.02351283871158888;
                                attribute Ixz : Real = -0.03328122971330339;
                                attribute sigma_Ixz : Real = 0.022566176940390956;
                                attribute Iyz : Real = 0.02604022754460038;
                                attribute sigma_Iyz : Real = 0.02209918015384651;
                            }
                        }
                        part <'C.1.2.1.1.1.3'> 'Subassembly 209' {
                            attribute POIconv : String = "-";
                            attribute Ipoint : Boolean = false;
                            attribute mass : Real = 1.8949782579645982;
                            attribute sigma_mass : Real = 0.5781874454998993;
                            attribute Cx : Real = -2.5956651472721464;
                            attribute sigma_Cx : Real = 27.657235034837143;
                            attribute Cy : Real = 7.84445695578734;
                            attribute sigma_Cy : Real = 21.820146288829996;
                            attribute Cz : Real = -16.33545146138166;
                            attribute sigma_Cz : Real = 28.880550093251983;
                            attribute Ixx : Real = 13838.302182002088;
                            attribute sigma_Ixx : Real = 7133.469926324677;
                            attribute Iyy : Real = 15750.909282592322;
                            attribute sigma_Iyy : Real = 8673.291475711923;
                            attribute Izz : Real = 8598.302002103695;
                            attribute sigma_Izz : Real = 6316.270114605727;
                            attribute Ixy : Real = 3613.690603525894;
                            attribute sigma_Ixy : Real = 2812.4348683749067;
                            attribute Ixz : Real = 6662.537962241764;
                            attribute sigma_Ixz : Real = 4154.044581829072;
                            attribute Iyz : Real = -3333.3355775294303;
                            attribute sigma_Iyz : Real = 3282.5604408086615;
                            part <'C.1.2.1.1.1.3.1'> 'Part 736' {
                                attribute POIconv : String = "+";
                                attribute Ipoint : Boolean = false;
                                attribute mass : Real = 0.008498315708246083;
                                attribute sigma_mass : Real = 0.28909372274994966;
                                attribute Cx : Real = 95.8209665492177;
                                attribute sigma_Cx : Real = 28.721044428837228;
                                attribute Cy : Real = 10.03832914866507;
                                attribute sigma_Cy : Real = 28.23690002309109;
                                attribute Cz : Real = -85.71276320144534;
                                attribute sigma_Cz : Real = 29.057750463592832;
                                attribute Ixx : Real = 0.01010350024606598;
                                attribute sigma_Ixx : Real = 0.37074144170588635;
                                attribute Iyy : Real = 0.00820784706025794;
                                attribute sigma_Iyy : Real = 0.3723953238821935;
                                attribute Izz : Real = 0.010515066389495425;
                                attribute sigma_Izz : Real = 0.37017423652493897;
                                attribute Ixy : Real = 0.00023126819134562212;
                                attribute sigma_Ixy : Real = 0.02351283871158888;
                                attribute Ixz : Real = 0.00012528071019289914;
                                attribute sigma_Ixz : Real = 0.022566176940390956;
                                attribute Iyz : Real = 0.0004255321773142125;
                                attribute sigma_Iyz : Real = 0.02209918015384651;
                            }
                            part <'C.1.2.1.1.1.3.2'> 'Part 737' {
                                attribute POIconv : String = "+";
                                attribute Ipoint : Boolean = false;
                                attribute mass : Real = 0.4892256704615429;
                                attribute sigma_mass : Real = 0.28909372274994966;
                                attribute Cx : Real = 17.618257645517588;
                                attribute sigma_Cx : Real = 28.721044428837228;
                                attribute Cy : Real = 27.53212545067072;
                                attribute sigma_Cy : Real = 28.23690002309109;
                                attribute Cz : Real = -96.17204638198018;
                                attribute sigma_Cz : Real = 29.057750463592832;
                                attribute Ixx : Real = 0.4969958259508533;
                                attribute sigma_Ixx : Real = 0.37074144170588635;
                                attribute Iyy : Real = 0.5265120312163792;
                                attribute sigma_Iyy : Real = 0.3723953238821935;
                                attribute Izz : Real = 0.5355846342958775;
                                attribute sigma_Izz : Real = 0.37017423652493897;
                                attribute Ixy : Real = 0.0190510341032654;
                                attribute sigma_Ixy : Real = 0.02351283871158888;
                                attribute Ixz : Real = 0.008945837549478563;
                                attribute sigma_Ixz : Real = 0.022566176940390956;
                                attribute Iyz : Real = 0.0060182447598878894;
                                attribute sigma_Iyz : Real = 0.02209918015384651;
                            }
                            part <'C.1.2.1.1.1.3.3'> 'Part 738' {
                                attribute POIconv : String = "-";
                                attribute Ipoint : Boolean = false;
                                attribute mass : Real = 0.4114048428549431;
                                attribute sigma_mass : Real = 0.28909372274994966;
                                attribute Cx : Real = 81.30457135848701;
                                attribute sigma_Cx : Real = 28.721044428837228;
                                attribute Cy : Real = -71.8050632160157;
                                attribute sigma_Cy : Real = 28.23690002309109;
                                attribute Cz : Real = -91.16176166571677;
                                attribute sigma_Cz : Real = 29.057750463592832;
                                attribute Ixx : Real = 0.44402303017076217;
                                attribute sigma_Ixx : Real = 0.37074144170588635;
                                attribute Iyy : Real = 0.4763219719018769;
                                attribute sigma_Iyy : Real = 0.3723953238821935;
                                attribute Izz : Real = 0.41585003026945555;
                                attribute sigma_Izz : Real = 0.37017423652493897;
                                attribute Ixy : Real = -0.02162839523967402;
                                attribute sigma_Ixy : Real = 0.02351283871158888;
                                attribute Ixz : Real = -0.053712151596749094;
                                attribute sigma_Ixz : Real = 0.022566176940390956;
                                attribute Iyz : Real = -0.014969335860785337;
                                attribute sigma_Iyz : Real = 0.02209918015384651;
                            }
                            part <'C.1.2.1.1.1.3.4'> 'Part 739' {
                                attribute POIconv : String = "+";
                                attribute Ipoint : Boolean = false;
                                attribute mass : Real = 0.9858494289398659;
                                attribute sigma_mass : Real = 0.28909372274994966;
                                attribute Cx : Real = -48.487570974975824;
                                attribute sigma_Cx : Real = 28.721044428837228;
                                attribute Cy : Real = 31.294124433770776;
                                attribute sigma_Cy : Real = 28.23690002309109;
                                attribute Cz : Real = 55.107109947130084;
                                attribute sigma_Cz : Real = 29.057750463592832;
                                attribute Ixx : Real = 1.1757576125781801;
                                attribute sigma_Ixx : Real = 0.37074144170588635;
                                attribute Iyy : Real = 1.0082079378489615;
                                attribute sigma_Iyy : Real = 0.3723953238821935;
                                attribute Izz : Real = 1.1376475595997482;
                                attribute sigma_Izz : Real = 0.37017423652493897;
                                attribute Ixy : Real = -0.07972945487492622;
                                attribute sigma_Ixy : Real = 0.02351283871158888;
                                attribute Ixz : Real = -0.03983517562227505;
                                attribute sigma_Ixz : Real = 0.022566176940390956;
                                attribute Iyz : Real = 0.049635722526859744;
                                attribute sigma_Iyz : Real = 0.02209918015384651;
                            }
                        }
                    }
                    part <'C.1.2.1.1.2'> 'Assembly 59' {
                        attribute POIconv : String = "-";
                        attribute Ipoint : Boolean = false;
                        attribute mass : Real = 5.13017081810208;
                        attribute sigma_mass : Real = 0.8176805270198123;
                        attribute Cx : Real = -8.007885434157341;
                        attribute sigma_Cx : Real = 13.687610307129285;
                        attribute Cy : Real = 0.8685283252615729;
                        attribute sigma_Cy : Real = 13.315111437729428;
                        attribute Cz : Real = -0.276442092053057;
                        attribute sigma_Cz : Real = 14.069702089806293;
                        attribute Ixx : Real = 25530.20097694342;
                        attribute sigma_Ixx : Real = 8852.851925190065;
                        attribute Iyy : Real = 29201.620159628736;
                        attribute sigma_Iyy : Real = 9672.244242073693;
                        attribute Izz : Real = 25069.712167157282;
                        attribute sigma_Izz : Real = 8700.558055384721;
                        attribute Ixy : Real = 549.5944825542019;
                        attribute sigma_Ixy : Real = 4286.305817453788;
                        attribute Ixz : Real = -540.4479890629996;
                        attribute sigma_Ixz : Real = 4813.477759078484;
                        attribute Iyz : Real = -2268.920651323839;
                        attribute sigma_Iyz : Real = 4124.315049184119;
                        part <'C.1.2.1.1.2.1'> 'Subassembly 210' {
                            attribute POIconv : String = "-";
                            attribute Ipoint : Boolean = false;
                            attribute mass : Real = 1.783695446806494;
                            attribute sigma_mass : Real = 0.5781874454998993;
                            attribute Cx : Real = 34.33685146129769;
                            attribute sigma_Cx : Real = 19.68876455984951;
                            attribute Cy : Real = -10.625399669557105;
                            attribute sigma_Cy : Real = 23.556908881900302;
                            attribute Cz : Real = 8.61849268244936;
                            attribute sigma_Cz : Real = 25.58294412738883;
                            attribute Ixx : Real = 12706.065132622864;
                            attribute sigma_Ixx : Real = 6189.560283640648;
                            attribute Iyy : Real = 11121.606095186211;
                            attribute sigma_Iyy : Real = 5819.78593330799;
                            attribute Izz : Real = 7707.4904583382;
                            attribute sigma_Izz : Real = 4583.840599500848;
                            attribute Ixy : Real = 10.32620297719231;
                            attribute sigma_Ixy : Real = 1956.4071794594902;
                            attribute Ixz : Real = 4881.588460485842;
                            attribute sigma_Ixz : Real = 2763.36075262285;
                            attribute Iyz : Real = 676.9372524037088;
                            attribute sigma_Iyz : Real = 2633.8717202402545;
                            part <'C.1.2.1.1.2.1.1'> 'Part 740' {
                                attribute POIconv : String = "-";
                                attribute Ipoint : Boolean = false;
                                attribute mass : Real = 0.3524647980094887;
                                attribute sigma_mass : Real = 0.28909372274994966;
                                attribute Cx : Real = 17.589840944856405;
                                attribute sigma_Cx : Real = 28.721044428837228;
                                attribute Cy : Real = -98.27087316662073;
                                attribute sigma_Cy : Real = 28.23690002309109;
                                attribute Cz : Real = 38.97576960735023;
                                attribute sigma_Cz : Real = 29.057750463592832;
                                attribute Ixx : Real = 0.4258627296014497;
                                attribute sigma_Ixx : Real = 0.37074144170588635;
                                attribute Iyy : Real = 0.4110435441094528;
                                attribute sigma_Iyy : Real = 0.3723953238821935;
                                attribute Izz : Real = 0.4137752782792825;
                                attribute sigma_Izz : Real = 0.37017423652493897;
                                attribute Ixy : Real = -0.002382145990967037;
                                attribute sigma_Ixy : Real = 0.02351283871158888;
                                attribute Ixz : Real = 0.007633384612226931;
                                attribute sigma_Ixz : Real = 0.022566176940390956;
                                attribute Iyz : Real = 0.00929356051204898;
                                attribute sigma_Iyz : Real = 0.02209918015384651;
                            }
                            part <'C.1.2.1.1.2.1.2'> 'Part 741' {
                                attribute POIconv : String = "-";
                                attribute Ipoint : Boolean = false;
                                attribute mass : Real = 0.3731747709093615;
                                attribute sigma_mass : Real = 0.28909372274994966;
                                attribute Cx : Real = -11.087685823440552;
                                attribute sigma_Cx : Real = 28.721044428837228;
                                attribute Cy : Real = 57.89243211038411;
                                attribute sigma_Cy : Real = 28.23690002309109;
                                attribute Cz : Real = 62.26490465924144;
                                attribute sigma_Cz : Real = 29.057750463592832;
                                attribute Ixx : Real = 0.3509286307150823;
                                attribute sigma_Ixx : Real = 0.37074144170588635;
                                attribute Iyy : Real = 0.35218270227074583;
                                attribute sigma_Iyy : Real = 0.3723953238821935;
                                attribute Izz : Real = 0.3515830593384509;
                                attribute sigma_Izz : Real = 0.37017423652493897;
                                attribute Ixy : Real = 0.0048160232423513066;
                                attribute sigma_Ixy : Real = 0.02351283871158888;
                                attribute Ixz : Real = 0.0008138250968522599;
                                attribute sigma_Ixz : Real = 0.022566176940390956;
                                attribute Iyz : Real = -0.0017294838101161493;
                                attribute sigma_Iyz : Real = 0.02209918015384651;
                            }
                            part <'C.1.2.1.1.2.1.3'> 'Part 742' {
                                attribute POIconv : String = "+";
                                attribute Ipoint : Boolean = false;
                                attribute mass : Real = 0.7001743357286323;
                                attribute sigma_mass : Real = 0.28909372274994966;
                                attribute Cx : Real = 84.57673550583422;
                                attribute sigma_Cx : Real = 28.721044428837228;
                                attribute Cy : Real = 3.156300587579608;
                                attribute sigma_Cy : Real = 28.23690002309109;
                                attribute Cz : Real = -73.20337975397706;
                                attribute sigma_Cz : Real = 29.057750463592832;
                                attribute Ixx : Real = 1.0666391176590142;
                                attribute sigma_Ixx : Real = 0.37074144170588635;
                                attribute Iyy : Real = 0.9689360931603728;
                                attribute sigma_Iyy : Real = 0.3723953238821935;
                                attribute Izz : Real = 1.0040021375078358;
                                attribute sigma_Izz : Real = 0.37017423652493897;
                                attribute Ixy : Real = 0.01753679927963258;
                                attribute sigma_Ixy : Real = 0.02351283871158888;
                                attribute Ixz : Real = 0.061439194178128806;
                                attribute sigma_Ixz : Real = 0.022566176940390956;
                                attribute Iyz : Real = -0.02060570819559051;
                                attribute sigma_Iyz : Real = 0.02209918015384651;
                            }
                            part <'C.1.2.1.1.2.1.4'> 'Part 743' {
                                attribute POIconv : String = "+";
                                attribute Ipoint : Boolean = false;
                                attribute mass : Real = 0.3578815421590116;
                                attribute sigma_mass : Real = 0.28909372274994966;
                                attribute Cx : Real = -0.09536426514387131;
                                attribute sigma_Cx : Real = 28.721044428837228;
                                attribute Cy : Real = -22.71536346524954;
                                attribute sigma_Cy : Real = 28.23690002309109;
                                attribute Cz : Real = 82.86153981462121;
                                attribute sigma_Cz : Real = 29.057750463592832;
                                attribute Ixx : Real = 0.4564375566026807;
                                attribute sigma_Ixx : Real = 0.37074144170588635;
                                attribute Iyy : Real = 0.46100574731399746;
                                attribute sigma_Iyy : Real = 0.3723953238821935;
                                attribute Izz : Real = 0.5164296956069518;
                                attribute sigma_Izz : Real = 0.37017423652493897;
                                attribute Ixy : Real = 0.0018357401942787263;
                                attribute sigma_Ixy : Real = 0.02351283871158888;
                                attribute Ixz : Real = 0.018394305828290897;
                                attribute sigma_Ixz : Real = 0.022566176940390956;
                                attribute Iyz : Real = -0.02495232358022128;
                                attribute sigma_Iyz : Real = 0.02209918015384651;
                            }
                        }
                        part <'C.1.2.1.1.2.2'> 'Subassembly 211' {
                            attribute POIconv : String = "-";
                            attribute Ipoint : Boolean = false;
                            attribute mass : Real = 1.4966696552748324;
                            attribute sigma_mass : Real = 0.40884026350990615;
                            attribute Cx : Real = 17.195259688754664;
                            attribute sigma_Cx : Real = 20.430103958596156;
                            attribute Cy : Real = 9.115250902588137;
                            attribute sigma_Cy : Real = 23.18643071793659;
                            attribute Cz : Real = 30.768182174901156;
                            attribute sigma_Cz : Real = 24.1271273062732;
                            attribute Ixx : Real = 5746.8082641519395;
                            attribute sigma_Ixx : Real = 4081.6150916048978;
                            attribute Iyy : Real = 3103.8238899369467;
                            attribute sigma_Iyy : Real = 2922.177011557226;
                            attribute Izz : Real = 2694.385545797264;
                            attribute sigma_Izz : Real = 2636.529569341302;
                            attribute Ixy : Real = 257.8567164348731;
                            attribute sigma_Ixy : Real = 1285.3488056436813;
                            attribute Ixz : Real = 276.78445025245617;
                            attribute sigma_Ixz : Real = 1379.9733840917597;
                            attribute Iyz : Real = -2865.01829557475;
                            attribute sigma_Iyz : Real = 2036.4815862349378;
                            part <'C.1.2.1.1.2.2.1'> 'Part 744' {
                                attribute POIconv : String = "-";
                                attribute Ipoint : Boolean = false;
                                attribute mass : Real = 0.6776843973651994;
                                attribute sigma_mass : Real = 0.28909372274994966;
                                attribute Cx : Real = 21.6790278442204;
                                attribute sigma_Cx : Real = 28.721044428837228;
                                attribute Cy : Real = -37.29653721675277;
                                attribute sigma_Cy : Real = 28.23690002309109;
                                attribute Cz : Real = -19.07854271121323;
                                attribute sigma_Cz : Real = 29.057750463592832;
                                attribute Ixx : Real = 0.9764823301807641;
                                attribute sigma_Ixx : Real = 0.37074144170588635;
                                attribute Iyy : Real = 0.9432967659398266;
                                attribute sigma_Iyy : Real = 0.3723953238821935;
                                attribute Izz : Real = 0.8389583984732274;
                                attribute sigma_Izz : Real = 0.37017423652493897;
                                attribute Ixy : Real = 0.03668961292485377;
                                attribute sigma_Ixy : Real = 0.02351283871158888;
                                attribute Ixz : Real = 0.02635295473512606;
                                attribute sigma_Ixz : Real = 0.022566176940390956;
                                attribute Iyz : Real = 0.0019964469050437164;
                                attribute sigma_Iyz : Real = 0.02209918015384651;
                            }
                            part <'C.1.2.1.1.2.2.2'> 'Part 745' {
                                attribute POIconv : String = "-";
                                attribute Ipoint : Boolean = false;
                                attribute mass : Real = 0.8189852579096332;
                                attribute sigma_mass : Real = 0.28909372274994966;
                                attribute Cx : Real = 13.485083356499672;
                                attribute sigma_Cx : Real = 28.721044428837228;
                                attribute Cy : Real = 47.51953762024641;
                                attribute sigma_Cy : Real = 28.23690002309109;
                                attribute Cz : Real = 72.01477042399347;
                                attribute sigma_Cz : Real = 29.057750463592832;
                                attribute Ixx : Real = 0.9866077048101372;
                                attribute sigma_Ixx : Real = 0.37074144170588635;
                                attribute Iyy : Real = 0.8188473953264852;
                                attribute sigma_Iyy : Real = 0.3723953238821935;
                                attribute Izz : Real = 0.9672519572000952;
                                attribute sigma_Izz : Real = 0.37017423652493897;
                                attribute Ixy : Real = 0.09962186153086014;
                                attribute sigma_Ixy : Real = 0.02351283871158888;
                                attribute Ixz : Real = -0.036196655509834606;
                                attribute sigma_Ixz : Real = 0.022566176940390956;
                                attribute Iyz : Real = 0.09620780002706718;
                                attribute sigma_Iyz : Real = 0.02209918015384651;
                            }
                        }
                        part <'C.1.2.1.1.2.3'> 'Subassembly 212' {
                            attribute POIconv : String = "-";
                            attribute Ipoint : Boolean = false;
                            attribute mass : Real = 1.8498057160207537;
                            attribute sigma_mass : Real = 0.40884026350990615;
                            attribute Cx : Real = -69.23101602498193;
                            attribute sigma_Cx : Real = 20.445762946184885;
                            attribute Cy : Real = 5.279287532383466;
                            attribute sigma_Cy : Real = 21.875878198850913;
                            attribute Cz : Real = -33.971549214308524;
                            attribute sigma_Cz : Real = 20.559593658139185;
                            attribute Ixx : Real = 3020.1441696867278;
                            attribute sigma_Ixx : Real = 3056.874029422309;
                            attribute Iyy : Real = 209.8655717897965;
                            attribute sigma_Iyy : Real = 797.2723933112752;
                            attribute Izz : Real = 3211.858096212978;
                            attribute sigma_Izz : Real = 3160.1858562591306;
                            attribute Ixy : Real = -775.1757406097505;
                            attribute sigma_Ixy : Real = 1572.0371633968539;
                            attribute Ixz : Real = -39.956834854800064;
                            attribute sigma_Ixz : Real = 402.3737254093288;
                            attribute Iyz : Real = -154.948598938119;
                            attribute sigma_Iyz : Real = 1534.896236718078;
                            part <'C.1.2.1.1.2.3.1'> 'Part 746' {
                                attribute POIconv : String = "-";
                                attribute Ipoint : Boolean = false;
                                attribute mass : Real = 0.8998692514791619;
                                attribute sigma_mass : Real = 0.28909372274994966;
                                attribute Cx : Real = -58.5591247305274;
                                attribute sigma_Cx : Real = 28.721044428837228;
                                attribute Cy : Real = 46.724122390151024;
                                attribute sigma_Cy : Real = 28.23690002309109;
                                attribute Cz : Real = -31.836828589439392;
                                attribute sigma_Cz : Real = 29.057750463592832;
                                attribute Ixx : Real = 1.1177223875317448;
                                attribute sigma_Ixx : Real = 0.37074144170588635;
                                attribute Iyy : Real = 1.0022752527058716;
                                attribute sigma_Iyy : Real = 0.3723953238821935;
                                attribute Izz : Real = 1.2520463243671025;
                                attribute sigma_Izz : Real = 0.37017423652493897;
                                attribute Ixy : Real = -0.05281833187798392;
                                attribute sigma_Ixy : Real = 0.02351283871158888;
                                attribute Ixz : Real = 0.002811801961034743;
                                attribute sigma_Ixz : Real = 0.022566176940390956;
                                attribute Iyz : Real = -0.0022142105824800914;
                                attribute sigma_Iyz : Real = 0.02209918015384651;
                            }
                            part <'C.1.2.1.1.2.3.2'> 'Part 747' {
                                attribute POIconv : String = "-";
                                attribute Ipoint : Boolean = false;
                                attribute mass : Real = 0.9499364645415918;
                                attribute sigma_mass : Real = 0.28909372274994966;
                                attribute Cx : Real = -79.34043616987765;
                                attribute sigma_Cx : Real = 28.721044428837228;
                                attribute Cy : Real = -33.98116189055145;
                                attribute sigma_Cy : Real = 28.23690002309109;
                                attribute Cz : Real = -35.99375756457448;
                                attribute sigma_Cz : Real = 29.057750463592832;
                                attribute Ixx : Real = 1.142982380782115;
                                attribute sigma_Ixx : Real = 0.37074144170588635;
                                attribute Iyy : Real = 1.3086528638228532;
                                attribute sigma_Iyy : Real = 0.3723953238821935;
                                attribute Izz : Real = 1.1386084378401995;
                                attribute sigma_Izz : Real = 0.37017423652493897;
                                attribute Ixy : Real = -0.08531444657742686;
                                attribute sigma_Ixy : Real = 0.02351283871158888;
                                attribute Ixz : Real = -0.03938223383212878;
                                attribute sigma_Ixz : Real = 0.022566176940390956;
                                attribute Iyz : Real = 0.0860008952847964;
                                attribute sigma_Iyz : Real = 0.02209918015384651;
                            }
                        }
                    }
                    part <'C.1.2.1.1.3'> 'Assembly 60' {
                        attribute POIconv : String = "-";
                        attribute Ipoint : Boolean = false;
                        attribute mass : Real = 3.8760724450475537;
                        attribute sigma_mass : Real = 0.867281168249849;
                        attribute Cx : Real = 6.117971217892843;
                        attribute sigma_Cx : Real = 18.60235425610876;
                        attribute Cy : Real = 0.863657642556391;
                        attribute sigma_Cy : Real = 17.402682448436472;
                        attribute Cz : Real = 14.296513625001904;
                        attribute sigma_Cz : Real = 20.069345611933684;
                        attribute Ixx : Real = 33070.90907718704;
                        attribute sigma_Ixx : Real = 12109.346051993412;
                        attribute Iyy : Real = 34097.50468165106;
                        attribute sigma_Iyy : Real = 13274.20443871856;
                        attribute Izz : Real = 31453.151282213075;
                        attribute sigma_Izz : Real = 11283.170310582813;
                        attribute Ixy : Real = -11711.788623318263;
                        attribute sigma_Ixy : Real = 5520.572432542666;
                        attribute Ixz : Real = 9512.23316575595;
                        attribute sigma_Ixz : Real = 6389.76512932457;
                        attribute Iyz : Real = 4507.916345605054;
                        attribute sigma_Iyz : Real = 5604.98003963897;
                        part <'C.1.2.1.1.3.1'> 'Subassembly 213' {
                            attribute POIconv : String = "-";
                            attribute Ipoint : Boolean = false;
                            attribute mass : Real = 1.1720333177589346;
                            attribute sigma_mass : Real = 0.5781874454998993;
                            attribute Cx : Real = 7.493554915998779;
                            attribute sigma_Cx : Real = 33.61013903748433;
                            attribute Cy : Real = -28.513972400689823;
                            attribute sigma_Cy : Real = 28.326746873319934;
                            attribute Cz : Real = -30.157431718580874;
                            attribute sigma_Cz : Real = 36.97085533351685;
                            attribute Ixx : Real = 5631.16921562977;
                            attribute sigma_Ixx : Real = 5732.2111658903295;
                            attribute Iyy : Real = 5693.106255023995;
                            attribute sigma_Iyy : Real = 7541.985512981017;
                            attribute Izz : Real = 4947.861965327729;
                            attribute sigma_Izz : Real = 4936.887173237681;
                            attribute Ixy : Real = 542.0647794286194;
                            attribute sigma_Ixy : Real = 2178.306554580071;
                            attribute Ixz : Real = 323.7745936522981;
                            attribute sigma_Ixz : Real = 3742.2665624789256;
                            attribute Iyz : Real = -1899.8100258949526;
                            attribute sigma_Iyz : Real = 2384.815256753644;
                            part <'C.1.2.1.1.3.1.1'> 'Part 748' {
                                attribute POIconv : String = "+";
                                attribute Ipoint : Boolean = false;
                                attribute mass : Real = 0.39689005199656824;
                                attribute sigma_mass : Real = 0.28909372274994966;
                                attribute Cx : Real = -23.252603830769658;
                                attribute sigma_Cx : Real = 28.721044428837228;
                                attribute Cy : Real = -24.79836782440543;
                                attribute sigma_Cy : Real = 28.23690002309109;
                                attribute Cz : Real = -75.31434493139386;
                                attribute sigma_Cz : Real = 29.057750463592832;
                                attribute Ixx : Real = 0.4334524829250718;
                                attribute sigma_Ixx : Real = 0.37074144170588635;
                                attribute Iyy : Real = 0.4286218616998627;
                                attribute sigma_Iyy : Real = 0.3723953238821935;
                                attribute Izz : Real = 0.42020117894506914;
                                attribute sigma_Izz : Real = 0.37017423652493897;
                                attribute Ixy : Real = -0.003096940950002379;
                                attribute sigma_Ixy : Real = 0.02351283871158888;
                                attribute Ixz : Real = -0.009915462050657891;
                                attribute sigma_Ixz : Real = 0.022566176940390956;
                                attribute Iyz : Real = 0.0038362948562042382;
                                attribute sigma_Iyz : Real = 0.02209918015384651;
                            }
                            part <'C.1.2.1.1.3.1.2'> 'Part 749' {
                                attribute POIconv : String = "-";
                                attribute Ipoint : Boolean = false;
                                attribute mass : Real = 0.36715233089006505;
                                attribute sigma_mass : Real = 0.28909372274994966;
                                attribute Cx : Real = 32.00223217718303;
                                attribute sigma_Cx : Real = 28.721044428837228;
                                attribute Cy : Real = -89.40441003069282;
                                attribute sigma_Cy : Real = 28.23690002309109;
                                attribute Cz : Real = -54.3915722053498;
                                attribute sigma_Cz : Real = 29.057750463592832;
                                attribute Ixx : Real = 0.4719654567221899;
                                attribute sigma_Ixx : Real = 0.37074144170588635;
                                attribute Iyy : Real = 0.460320418295716;
                                attribute sigma_Iyy : Real = 0.3723953238821935;
                                attribute Izz : Real = 0.46101187755155804;
                                attribute sigma_Izz : Real = 0.37017423652493897;
                                attribute Ixy : Real = -0.00251825365628728;
                                attribute sigma_Ixy : Real = 0.02351283871158888;
                                attribute Ixz : Real = -0.0049723586261868095;
                                attribute sigma_Ixz : Real = 0.022566176940390956;
                                attribute Iyz : Real = 0.003343582954485104;
                                attribute sigma_Iyz : Real = 0.02209918015384651;
                            }
                            part <'C.1.2.1.1.3.1.3'> 'Part 750' {
                                attribute POIconv : String = "-";
                                attribute Ipoint : Boolean = false;
                                attribute mass : Real = 0.2973035856145434;
                                attribute sigma_mass : Real = 0.28909372274994966;
                                attribute Cx : Real = 56.80312239564955;
                                attribute sigma_Cx : Real = 28.721044428837228;
                                attribute Cy : Real = 20.184138836339116;
                                attribute sigma_Cy : Real = 28.23690002309109;
                                attribute Cz : Real = 16.486272821202874;
                                attribute sigma_Cz : Real = 29.057750463592832;
                                attribute Ixx : Real = 0.4165385188469107;
                                attribute sigma_Ixx : Real = 0.37074144170588635;
                                attribute Iyy : Real = 0.41021507699301324;
                                attribute sigma_Iyy : Real = 0.3723953238821935;
                                attribute Izz : Real = 0.4321250382861898;
                                attribute sigma_Izz : Real = 0.37017423652493897;
                                attribute Ixy : Real = 0.01599767566384614;
                                attribute sigma_Ixy : Real = 0.02351283871158888;
                                attribute Ixz : Real = 0.0016296869304939594;
                                attribute sigma_Ixz : Real = 0.022566176940390956;
                                attribute Iyz : Real = 0.0025697867139138717;
                                attribute sigma_Iyz : Real = 0.02209918015384651;
                            }
                            part <'C.1.2.1.1.3.1.4'> 'Part 751' {
                                attribute POIconv : String = "-";
                                attribute Ipoint : Boolean = false;
                                attribute mass : Real = 0.11068734925775789;
                                attribute sigma_mass : Real = 0.28909372274994966;
                                attribute Cx : Real = -96.00051855668426;
                                attribute sigma_Cx : Real = 28.721044428837228;
                                attribute Cy : Real = 29.335967730730772;
                                attribute sigma_Cy : Real = 28.23690002309109;
                                attribute Cz : Real = 86.86235672794282;
                                attribute sigma_Cz : Real = 29.057750463592832;
                                attribute Ixx : Real = 0.13287541940067435;
                                attribute sigma_Ixx : Real = 0.37074144170588635;
                                attribute Iyy : Real = 0.1493999821924077;
                                attribute sigma_Iyy : Real = 0.3723953238821935;
                                attribute Izz : Real = 0.13480151636001594;
                                attribute sigma_Izz : Real = 0.37017423652493897;
                                attribute Ixy : Real = 0.0005346451701485279;
                                attribute sigma_Ixy : Real = 0.02351283871158888;
                                attribute Ixz : Real = 0.016063611740379388;
                                attribute sigma_Ixz : Real = 0.022566176940390956;
                                attribute Iyz : Real = -0.003326603736358102;
                                attribute sigma_Iyz : Real = 0.02209918015384651;
                            }
                        }
                        part <'C.1.2.1.1.3.2'> 'Subassembly 214' {
                            attribute POIconv : String = "-";
                            attribute Ipoint : Boolean = false;
                            attribute mass : Real = 2.704039127288619;
                            attribute sigma_mass : Real = 0.6464332159373649;
                            attribute Cx : Real = 5.5217409676439075;
                            attribute sigma_Cx : Real = 22.331782183674637;
                            attribute Cy : Real = 13.59703892391583;
                            attribute sigma_Cy : Real = 20.562453082053327;
                            attribute Cz : Real = 33.56454289377829;
                            attribute sigma_Cz : Real = 21.430161870192745;
                            attribute Ixx : Real = 22669.781215658124;
                            attribute sigma_Ixx : Real = 9237.203397036807;
                            attribute Iyy : Real = 25081.20862720483;
                            attribute sigma_Iyy : Real = 9905.154022714014;
                            attribute Izz : Real = 25052.16243549814;
                            attribute sigma_Izz : Real = 9841.182335066263;
                            attribute Ixy : Real = -12321.746035399427;
                            attribute sigma_Ixy : Real = 4878.266515004303;
                            attribute Ixz : Real = 9085.72409771871;
                            attribute sigma_Ixz : Real = 4732.6760810967935;
                            attribute Iyz : Real = 8601.773440626963;
                            attribute sigma_Iyz : Real = 4431.965168264186;
                            part <'C.1.2.1.1.3.2.1'> 'Part 752' {
                                attribute POIconv : String = "+";
                                attribute Ipoint : Boolean = false;
                                attribute mass : Real = 0.2992536970761139;
                                attribute sigma_mass : Real = 0.28909372274994966;
                                attribute Cx : Real = 85.29202463105321;
                                attribute sigma_Cx : Real = 28.721044428837228;
                                attribute Cy : Real = 63.26323663815856;
                                attribute sigma_Cy : Real = 28.23690002309109;
                                attribute Cz : Real = 67.95464907772839;
                                attribute sigma_Cz : Real = 29.057750463592832;
                                attribute Ixx : Real = 0.38744432852985544;
                                attribute sigma_Ixx : Real = 0.37074144170588635;
                                attribute Iyy : Real = 0.4356089676417009;
                                attribute sigma_Iyy : Real = 0.3723953238821935;
                                attribute Izz : Real = 0.3900464582805366;
                                attribute sigma_Izz : Real = 0.37017423652493897;
                                attribute Ixy : Real = -0.034687679455557854;
                                attribute sigma_Ixy : Real = 0.02351283871158888;
                                attribute Ixz : Real = 0.0006856327784017383;
                                attribute sigma_Ixz : Real = 0.022566176940390956;
                                attribute Iyz : Real = -0.024857684271430862;
                                attribute sigma_Iyz : Real = 0.02209918015384651;
                            }
                            part <'C.1.2.1.1.3.2.2'> 'Part 753' {
                                attribute POIconv : String = "-";
                                attribute Ipoint : Boolean = false;
                                attribute mass : Real = 0.4824196958669927;
                                attribute sigma_mass : Real = 0.28909372274994966;
                                attribute Cx : Real = 75.37926463410258;
                                attribute sigma_Cx : Real = 28.721044428837228;
                                attribute Cy : Real = 86.7199407890439;
                                attribute sigma_Cy : Real = 28.23690002309109;
                                attribute Cz : Real = -51.597818080335855;
                                attribute sigma_Cz : Real = 29.057750463592832;
                                attribute Ixx : Real = 0.5972836744420277;
                                attribute sigma_Ixx : Real = 0.37074144170588635;
                                attribute Iyy : Real = 0.6088349565192258;
                                attribute sigma_Iyy : Real = 0.3723953238821935;
                                attribute Izz : Real = 0.4651221313919162;
                                attribute sigma_Izz : Real = 0.37017423652493897;
                                attribute Ixy : Real = -0.005143026305932856;
                                attribute sigma_Ixy : Real = 0.02351283871158888;
                                attribute Ixz : Real = 0.02245609712122978;
                                attribute sigma_Ixz : Real = 0.022566176940390956;
                                attribute Iyz : Real = -0.002820177434061783;
                                attribute sigma_Iyz : Real = 0.02209918015384651;
                            }
                            part <'C.1.2.1.1.3.2.3'> 'Part 754' {
                                attribute POIconv : String = "-";
                                attribute Ipoint : Boolean = false;
                                attribute mass : Real = 0.731420080100419;
                                attribute sigma_mass : Real = 0.28909372274994966;
                                attribute Cx : Real = -87.23915270529687;
                                attribute sigma_Cx : Real = 28.721044428837228;
                                attribute Cy : Real = -75.01831972040236;
                                attribute sigma_Cy : Real = 28.23690002309109;
                                attribute Cz : Real = 72.04496175982058;
                                attribute sigma_Cz : Real = 29.057750463592832;
                                attribute Ixx : Real = 1.0759963707122355;
                                attribute sigma_Ixx : Real = 0.37074144170588635;
                                attribute Iyy : Real = 0.9533618149858826;
                                attribute sigma_Iyy : Real = 0.3723953238821935;
                                attribute Izz : Real = 0.9150329569349791;
                                attribute sigma_Izz : Real = 0.37017423652493897;
                                attribute Ixy : Real = -0.09269870400481497;
                                attribute sigma_Ixy : Real = 0.02351283871158888;
                                attribute Ixz : Real = -0.013819817713409153;
                                attribute sigma_Ixz : Real = 0.022566176940390956;
                                attribute Iyz : Real = -0.01576985372709947;
                                attribute sigma_Iyz : Real = 0.02209918015384651;
                            }
                            part <'C.1.2.1.1.3.2.4'> 'Part 755' {
                                attribute POIconv : String = "-";
                                attribute Ipoint : Boolean = false;
                                attribute mass : Real = 0.8046920785717666;
                                attribute sigma_mass : Real = 0.28909372274994966;
                                attribute Cx : Real = -21.137832244858146;
                                attribute sigma_Cx : Real = 28.721044428837228;
                                attribute Cy : Real = -3.009476698935032;
                                attribute sigma_Cy : Real = 28.23690002309109;
                                attribute Cz : Real = 86.59949153661728;
                                attribute sigma_Cz : Real = 29.057750463592832;
                                attribute Ixx : Real = 0.8875065574219388;
                                attribute sigma_Ixx : Real = 0.37074144170588635;
                                attribute Iyy : Real = 0.8774204459401267;
                                attribute sigma_Iyy : Real = 0.3723953238821935;
                                attribute Izz : Real = 0.9706186754508619;
                                attribute sigma_Izz : Real = 0.37017423652493897;
                                attribute Ixy : Real = -0.00021913966782130648;
                                attribute sigma_Ixy : Real = 0.02351283871158888;
                                attribute Ixz : Real = -0.0036418256558426315;
                                attribute sigma_Ixz : Real = 0.022566176940390956;
                                attribute Iyz : Real = -0.00294138001072363;
                                attribute sigma_Iyz : Real = 0.02209918015384651;
                            }
                            part <'C.1.2.1.1.3.2.5'> 'Part 756' {
                                attribute POIconv : String = "+";
                                attribute Ipoint : Boolean = false;
                                attribute mass : Real = 0.38625357567332685;
                                attribute sigma_mass : Real = 0.28909372274994966;
                                attribute Cx : Real = 87.66397093422711;
                                attribute sigma_Cx : Real = 28.721044428837228;
                                attribute Cy : Real = 86.19044567458332;
                                attribute sigma_Cy : Real = 28.23690002309109;
                                attribute Cz : Real = -70.07079608738422;
                                attribute sigma_Cz : Real = 29.057750463592832;
                                attribute Ixx : Real = 0.5604927172738877;
                                attribute sigma_Ixx : Real = 0.37074144170588635;
                                attribute Iyy : Real = 0.5651094200121082;
                                attribute sigma_Iyy : Real = 0.3723953238821935;
                                attribute Izz : Real = 0.6038361024888986;
                                attribute sigma_Izz : Real = 0.37017423652493897;
                                attribute Ixy : Real = 0.0028351004458055575;
                                attribute sigma_Ixy : Real = 0.02351283871158888;
                                attribute Ixz : Real = 0.008843891778887662;
                                attribute sigma_Ixz : Real = 0.022566176940390956;
                                attribute Iyz : Real = -0.019213378798346857;
                                attribute sigma_Iyz : Real = 0.02209918015384651;
                            }
                        }
                    }
                    part <'C.1.2.1.1.4'> 'Assembly 61' {
                        attribute POIconv : String = "-";
                        attribute Ipoint : Boolean = false;
                        attribute mass : Real = 4.842399241282838;
                        attribute sigma_mass : Real = 0.9141946211470771;
                        attribute Cx : Real = -12.898256461940132;
                        attribute sigma_Cx : Real = 12.288990896828075;
                        attribute Cy : Real = -7.227758584645112;
                        attribute sigma_Cy : Real = 12.713373852202169;
                        attribute Cz : Real = -8.792598834426581;
                        attribute sigma_Cz : Real = 15.554344078867052;
                        attribute Ixx : Real = 29755.26990890933;
                        attribute sigma_Ixx : Real = 10181.33549281089;
                        attribute Iyy : Real = 30241.956994824126;
                        attribute sigma_Iyy : Real = 10242.899650688834;
                        attribute Izz : Real = 12708.487455508832;
                        attribute sigma_Izz : Real = 5805.093055907293;
                        attribute Ixy : Real = -1538.3681602709723;
                        attribute sigma_Ixy : Real = 2738.229477534897;
                        attribute Ixz : Real = 2319.2054931285215;
                        attribute sigma_Ixz : Real = 4692.34268640176;
                        attribute Iyz : Real = -950.2184796074102;
                        attribute sigma_Iyz : Real = 4711.203564141709;
                        part <'C.1.2.1.1.4.1'> 'Subassembly 215' {
                            attribute POIconv : String = "-";
                            attribute Ipoint : Boolean = false;
                            attribute mass : Real = 2.6993003280763515;
                            attribute sigma_mass : Real = 0.6464332159373649;
                            attribute Cx : Real = -13.025455632292338;
                            attribute sigma_Cx : Real = 16.446303585886806;
                            attribute Cy : Real = 4.554073569551643;
                            attribute sigma_Cy : Real = 17.36240728919933;
                            attribute Cz : Real = 1.1279838372138484;
                            attribute sigma_Cz : Real = 19.839157577482972;
                            attribute Ixx : Real = 13863.40074162288;
                            attribute sigma_Ixx : Real = 7076.309554355116;
                            attribute Iyy : Real = 14047.87719706599;
                            attribute sigma_Iyy : Real = 6934.717196206327;
                            attribute Izz : Real = 7004.972420096683;
                            attribute sigma_Izz : Real = 4323.379333684008;
                            attribute Ixy : Real = 134.2766538048382;
                            attribute sigma_Ixy : Real = 1986.8101264946456;
                            attribute Ixz : Real = -3457.073006040331;
                            attribute sigma_Ixz : Real = 3168.3556816893424;
                            attribute Iyz : Real = -4140.495698442074;
                            attribute sigma_Iyz : Real = 3348.2869399990172;
                            part <'C.1.2.1.1.4.1.1'> 'Part 757' {
                                attribute POIconv : String = "+";
                                attribute Ipoint : Boolean = false;
                                attribute mass : Real = 0.5277951386689674;
                                attribute sigma_mass : Real = 0.28909372274994966;
                                attribute Cx : Real = -22.000057948753238;
                                attribute sigma_Cx : Real = 28.721044428837228;
                                attribute Cy : Real = 73.35792551748455;
                                attribute sigma_Cy : Real = 28.23690002309109;
                                attribute Cz : Real = 92.66872312873602;
                                attribute sigma_Cz : Real = 29.057750463592832;
                                attribute Ixx : Real = 0.6599775728875614;
                                attribute sigma_Ixx : Real = 0.37074144170588635;
                                attribute Iyy : Real = 0.6729828603777622;
                                attribute sigma_Iyy : Real = 0.3723953238821935;
                                attribute Izz : Real = 0.6721468524486317;
                                attribute sigma_Izz : Real = 0.37017423652493897;
                                attribute Ixy : Real = 0.012797544881179762;
                                attribute sigma_Ixy : Real = 0.02351283871158888;
                                attribute Ixz : Real = 0.04098930642177462;
                                attribute sigma_Ixz : Real = 0.022566176940390956;
                                attribute Iyz : Real = 0.013045679529243823;
                                attribute sigma_Iyz : Real = 0.02209918015384651;
                            }
                            part <'C.1.2.1.1.4.1.2'> 'Part 758' {
                                attribute POIconv : String = "+";
                                attribute Ipoint : Boolean = false;
                                attribute mass : Real = 0.8053474915262777;
                                attribute sigma_mass : Real = 0.28909372274994966;
                                attribute Cx : Real = 37.55772658623755;
                                attribute sigma_Cx : Real = 28.721044428837228;
                                attribute Cy : Real = -2.7468798216432333;
                                attribute sigma_Cy : Real = 28.23690002309109;
                                attribute Cz : Real = 28.147784527391195;
                                attribute sigma_Cz : Real = 29.057750463592832;
                                attribute Ixx : Real = 0.980439222471684;
                                attribute sigma_Ixx : Real = 0.37074144170588635;
                                attribute Iyy : Real = 1.041424184657024;
                                attribute sigma_Iyy : Real = 0.3723953238821935;
                                attribute Izz : Real = 1.0076098768063189;
                                attribute sigma_Izz : Real = 0.37017423652493897;
                                attribute Ixy : Real = -0.010019175134829465;
                                attribute sigma_Ixy : Real = 0.02351283871158888;
                                attribute Ixz : Real = -0.007402587072056047;
                                attribute sigma_Ixz : Real = 0.022566176940390956;
                                attribute Iyz : Real = 0.005689361431303748;
                                attribute sigma_Iyz : Real = 0.02209918015384651;
                            }
                            part <'C.1.2.1.1.4.1.3'> 'Part 759' {
                                attribute POIconv : String = "-";
                                attribute Ipoint : Boolean = false;
                                attribute mass : Real = 0.2798572542674374;
                                attribute sigma_mass : Real = 0.28909372274994966;
                                attribute Cx : Real = -1.8543540965765715;
                                attribute sigma_Cx : Real = 28.721044428837228;
                                attribute Cy : Real = -38.02656470797956;
                                attribute sigma_Cy : Real = 28.23690002309109;
                                attribute Cz : Real = 8.29140255227685;
                                attribute sigma_Cz : Real = 29.057750463592832;
                                attribute Ixx : Real = 0.319043573662642;
                                attribute sigma_Ixx : Real = 0.37074144170588635;
                                attribute Iyy : Real = 0.3612154677599895;
                                attribute sigma_Iyy : Real = 0.3723953238821935;
                                attribute Izz : Real = 0.36260014519152894;
                                attribute sigma_Izz : Real = 0.37017423652493897;
                                attribute Ixy : Real = 0.004002795928620026;
                                attribute sigma_Ixy : Real = 0.02351283871158888;
                                attribute Ixz : Real = 0.0049391579486995334;
                                attribute sigma_Ixz : Real = 0.022566176940390956;
                                attribute Iyz : Real = -0.0216381314967697;
                                attribute sigma_Iyz : Real = 0.02209918015384651;
                            }
                            part <'C.1.2.1.1.4.1.4'> 'Part 760' {
                                attribute POIconv : String = "+";
                                attribute Ipoint : Boolean = false;
                                attribute mass : Real = 0.9471244623491075;
                                attribute sigma_mass : Real = 0.28909372274994966;
                                attribute Cx : Real = -51.52808767743409;
                                attribute sigma_Cx : Real = 28.721044428837228;
                                attribute Cy : Real = -10.05314807407558;
                                attribute sigma_Cy : Real = 28.23690002309109;
                                attribute Cz : Real = -74.55631201155484;
                                attribute sigma_Cz : Real = 29.057750463592832;
                                attribute Ixx : Real = 1.2448887865830731;
                                attribute sigma_Ixx : Real = 0.37074144170588635;
                                attribute Iyy : Real = 1.219913015585758;
                                attribute sigma_Iyy : Real = 0.3723953238821935;
                                attribute Izz : Real = 1.2360221746950788;
                                attribute sigma_Izz : Real = 0.37017423652493897;
                                attribute Ixy : Real = -0.010508502236888088;
                                attribute sigma_Ixy : Real = 0.02351283871158888;
                                attribute Ixz : Real = -0.0014892940963207291;
                                attribute sigma_Ixz : Real = 0.022566176940390956;
                                attribute Iyz : Real = 0.01337938894965738;
                                attribute sigma_Iyz : Real = 0.02209918015384651;
                            }
                            part <'C.1.2.1.1.4.1.5'> 'Part 761' {
                                attribute POIconv : String = "-";
                                attribute Ipoint : Boolean = false;
                                attribute mass : Real = 0.1391759812645614;
                                attribute sigma_mass : Real = 0.28909372274994966;
                                attribute Cx : Real = -32.136630872264504;
                                attribute sigma_Cx : Real = 28.721044428837228;
                                attribute Cy : Real = -29.095242777839303;
                                attribute sigma_Cy : Real = 28.23690002309109;
                                attribute Cz : Real = -1.727196853607893;
                                attribute sigma_Cz : Real = 29.057750463592832;
                                attribute Ixx : Real = 0.15586377958796008;
                                attribute sigma_Ixx : Real = 0.37074144170588635;
                                attribute Iyy : Real = 0.1790932487070789;
                                attribute sigma_Iyy : Real = 0.3723953238821935;
                                attribute Izz : Real = 0.16947107755359206;
                                attribute sigma_Izz : Real = 0.37017423652493897;
                                attribute Ixy : Real = -0.0020703784647289935;
                                attribute sigma_Ixy : Real = 0.02351283871158888;
                                attribute Ixz : Real = 0.007364274583466635;
                                attribute sigma_Ixz : Real = 0.022566176940390956;
                                attribute Iyz : Real = 0.018147694171923696;
                                attribute sigma_Iyz : Real = 0.02209918015384651;
                            }
                        }
                        part <'C.1.2.1.1.4.2'> 'Subassembly 216' {
                            attribute POIconv : String = "-";
                            attribute Ipoint : Boolean = false;
                            attribute mass : Real = 2.143098913206486;
                            attribute sigma_mass : Real = 0.6464332159373649;
                            attribute Cx : Real = -12.738045115582333;
                            attribute sigma_Cx : Real = 18.491251530398664;
                            attribute Cy : Real = -22.06734587722643;
                            attribute sigma_Cy : Real = 17.728561964678814;
                            attribute Cz : Real = -21.287884000803533;
                            attribute sigma_Cz : Real = 24.24141257104981;
                            attribute Ixx : Real = 14444.96978340998;
                            attribute sigma_Ixx : Real = 6942.408742679695;
                            attribute Iyy : Real = 15593.714838567112;
                            attribute sigma_Iyy : Real = 7348.305806638306;
                            attribute Izz : Real = 4856.783246636361;
                            attribute sigma_Izz : Real = 3533.801997925582;
                            attribute Ixy : Real = -1681.7852454925394;
                            attribute sigma_Ixy : Real = 1712.020519707815;
                            attribute Ixz : Real = 5768.582038691624;
                            attribute sigma_Ixz : Real = 3397.106100742795;
                            attribute Iyz : Real = 3903.162415121986;
                            attribute sigma_Iyz : Real = 3087.1258657468074;
                            part <'C.1.2.1.1.4.2.1'> 'Part 762' {
                                attribute POIconv : String = "-";
                                attribute Ipoint : Boolean = false;
                                attribute mass : Real = 0.24065079136332498;
                                attribute sigma_mass : Real = 0.28909372274994966;
                                attribute Cx : Real = -19.398300489410758;
                                attribute sigma_Cx : Real = 28.721044428837228;
                                attribute Cy : Real = 13.430628506466746;
                                attribute sigma_Cy : Real = 28.23690002309109;
                                attribute Cz : Real = -36.78402896039188;
                                attribute sigma_Cz : Real = 29.057750463592832;
                                attribute Ixx : Real = 0.32285130454318084;
                                attribute sigma_Ixx : Real = 0.37074144170588635;
                                attribute Iyy : Real = 0.3022483775826096;
                                attribute sigma_Iyy : Real = 0.3723953238821935;
                                attribute Izz : Real = 0.34521169758474934;
                                attribute sigma_Izz : Real = 0.37017423652493897;
                                attribute Ixy : Real = -0.00010714679072289656;
                                attribute sigma_Ixy : Real = 0.02351283871158888;
                                attribute Ixz : Real = -0.01540431113764842;
                                attribute sigma_Ixz : Real = 0.022566176940390956;
                                attribute Iyz : Real = 0.003224401918999439;
                                attribute sigma_Iyz : Real = 0.02209918015384651;
                            }
                            part <'C.1.2.1.1.4.2.2'> 'Part 763' {
                                attribute POIconv : String = "+";
                                attribute Ipoint : Boolean = false;
                                attribute mass : Real = 0.6926015382464975;
                                attribute sigma_mass : Real = 0.28909372274994966;
                                attribute Cx : Real = 27.922243298962712;
                                attribute sigma_Cx : Real = 28.721044428837228;
                                attribute Cy : Real = -15.271924389526248;
                                attribute sigma_Cy : Real = 28.23690002309109;
                                attribute Cz : Real = -97.4251854699105;
                                attribute sigma_Cz : Real = 29.057750463592832;
                                attribute Ixx : Real = 0.7579189228996535;
                                attribute sigma_Ixx : Real = 0.37074144170588635;
                                attribute Iyy : Real = 0.7762027341634707;
                                attribute sigma_Iyy : Real = 0.3723953238821935;
                                attribute Izz : Real = 0.747914059974558;
                                attribute sigma_Izz : Real = 0.37017423652493897;
                                attribute Ixy : Real = -0.012381074577790929;
                                attribute sigma_Ixy : Real = 0.02351283871158888;
                                attribute Ixz : Real = -0.007272485362996863;
                                attribute sigma_Ixz : Real = 0.022566176940390956;
                                attribute Iyz : Real = -0.013261630503456993;
                                attribute sigma_Iyz : Real = 0.02209918015384651;
                            }
                            part <'C.1.2.1.1.4.2.3'> 'Part 764' {
                                attribute POIconv : String = "+";
                                attribute Ipoint : Boolean = false;
                                attribute mass : Real = 0.09721460776636377;
                                attribute sigma_mass : Real = 0.28909372274994966;
                                attribute Cx : Real = 34.01378854177892;
                                attribute sigma_Cx : Real = 28.721044428837228;
                                attribute Cy : Real = 8.866165345534682;
                                attribute sigma_Cy : Real = 28.23690002309109;
                                attribute Cz : Real = -20.01916980370879;
                                attribute sigma_Cz : Real = 29.057750463592832;
                                attribute Ixx : Real = 0.12628605288038988;
                                attribute sigma_Ixx : Real = 0.37074144170588635;
                                attribute Iyy : Real = 0.1331928710910463;
                                attribute sigma_Iyy : Real = 0.3723953238821935;
                                attribute Izz : Real = 0.1302974547031479;
                                attribute sigma_Izz : Real = 0.37017423652493897;
                                attribute Ixy : Real = -0.0034043748472266933;
                                attribute sigma_Ixy : Real = 0.02351283871158888;
                                attribute Ixz : Real = -0.00744904209373886;
                                attribute sigma_Ixz : Real = 0.022566176940390956;
                                attribute Iyz : Real = -0.00035498980847123993;
                                attribute sigma_Iyz : Real = 0.02209918015384651;
                            }
                            part <'C.1.2.1.1.4.2.4'> 'Part 765' {
                                attribute POIconv : String = "+";
                                attribute Ipoint : Boolean = false;
                                attribute mass : Real = 0.8070877520779614;
                                attribute sigma_mass : Real = 0.28909372274994966;
                                attribute Cx : Real = -56.81523885577917;
                                attribute sigma_Cx : Real = 28.721044428837228;
                                attribute Cy : Real = -56.775956274941564;
                                attribute sigma_Cy : Real = 28.23690002309109;
                                attribute Cz : Real = 73.24771415442228;
                                attribute sigma_Cz : Real = 29.057750463592832;
                                attribute Ixx : Real = 0.8549413265791542;
                                attribute sigma_Ixx : Real = 0.37074144170588635;
                                attribute Iyy : Real = 0.8487442864754311;
                                attribute sigma_Iyy : Real = 0.3723953238821935;
                                attribute Izz : Real = 0.696494459273452;
                                attribute sigma_Izz : Real = 0.37017423652493897;
                                attribute Ixy : Real = 0.0009494314552722415;
                                attribute sigma_Ixy : Real = 0.02351283871158888;
                                attribute Ixz : Real = 0.003463092506280538;
                                attribute sigma_Ixz : Real = 0.022566176940390956;
                                attribute Iyz : Real = -0.03778196418151167;
                                attribute sigma_Iyz : Real = 0.02209918015384651;
                            }
                            part <'C.1.2.1.1.4.2.5'> 'Part 766' {
                                attribute POIconv : String = "-";
                                attribute Ipoint : Boolean = false;
                                attribute mass : Real = 0.3055442237523384;
                                attribute sigma_mass : Real = 0.28909372274994966;
                                attribute Cx : Real = 1.8936157692223787;
                                attribute sigma_Cx : Real = 28.721044428837228;
                                attribute Cy : Real = 16.410128958523273;
                                attribute sigma_Cy : Real = 28.23690002309109;
                                attribute Cz : Real = -86.61358072422445;
                                attribute sigma_Cz : Real = 29.057750463592832;
                                attribute Ixx : Real = 0.3064496150515967;
                                attribute sigma_Ixx : Real = 0.37074144170588635;
                                attribute Iyy : Real = 0.3242030123640101;
                                attribute sigma_Iyy : Real = 0.3723953238821935;
                                attribute Izz : Real = 0.32837305119860355;
                                attribute sigma_Izz : Real = 0.37017423652493897;
                                attribute Ixy : Real = 0.011985892578234516;
                                attribute sigma_Ixy : Real = 0.02351283871158888;
                                attribute Ixz : Real = -0.01288303649725082;
                                attribute sigma_Ixz : Real = 0.022566176940390956;
                                attribute Iyz : Real = -0.018099896429694087;
                                attribute sigma_Iyz : Real = 0.02209918015384651;
                            }
                        }
                    }
                    part <'C.1.2.1.1.5'> 'Assembly 62' {
                        attribute POIconv : String = "-";
                        attribute Ipoint : Boolean = false;
                        attribute mass : Real = 6.484908865611301;
                        attribute sigma_mass : Real = 0.9588154076086138;
                        attribute Cx : Real = -19.620536636475695;
                        attribute sigma_Cx : Real = 14.882041076831763;
                        attribute Cy : Real = -1.6783769162429567;
                        attribute sigma_Cy : Real = 11.969878278000179;
                        attribute Cz : Real = -35.898096907696804;
                        attribute sigma_Cz : Real = 14.513583840835214;
                        attribute Ixx : Real = 38439.445517537126;
                        attribute sigma_Ixx : Real = 12233.34313700904;
                        attribute Iyy : Real = 55645.410660158275;
                        attribute sigma_Iyy : Real = 16202.700896444443;
                        attribute Izz : Real = 38408.409270149656;
                        attribute sigma_Izz : Real = 13917.910427237292;
                        attribute Ixy : Real = 6175.399335412616;
                        attribute sigma_Ixy : Real = 6203.801418420703;
                        attribute Ixz : Real = 3944.069578629133;
                        attribute sigma_Ixz : Real = 7262.029914262294;
                        attribute Iyz : Real = -5427.076339002082;
                        attribute sigma_Iyz : Real = 5582.79549037294;
                        part <'C.1.2.1.1.5.1'> 'Subassembly 217' {
                            attribute POIconv : String = "-";
                            attribute Ipoint : Boolean = false;
                            attribute mass : Real = 2.943458231328521;
                            attribute sigma_mass : Real = 0.5781874454998993;
                            attribute Cx : Real = 28.979092171130972;
                            attribute sigma_Cx : Real = 19.619073625321285;
                            attribute Cy : Real = -33.125117587718115;
                            attribute sigma_Cy : Real = 16.63818168487331;
                            attribute Cz : Real = -75.77162640586857;
                            attribute sigma_Cz : Real = 17.95226593603951;
                            attribute Ixx : Real = 5644.030298892996;
                            attribute sigma_Ixx : Real = 4576.082707015225;
                            attribute Iyy : Real = 14279.614767249022;
                            attribute sigma_Iyy : Real = 7411.345535144487;
                            attribute Izz : Real = 14031.640764006768;
                            attribute sigma_Izz : Real = 6993.872250597901;
                            attribute Ixy : Real = -3024.6706519559693;
                            attribute sigma_Ixy : Real = 3248.7949724848177;
                            attribute Ixz : Real = -3199.5666590247906;
                            attribute sigma_Ixz : Real = 3479.6735440898615;
                            attribute Iyz : Real = -1706.0688046409118;
                            attribute sigma_Iyz : Real = 2185.8059336310466;
                            part <'C.1.2.1.1.5.1.1'> 'Part 767' {
                                attribute POIconv : String = "+";
                                attribute Ipoint : Boolean = false;
                                attribute mass : Real = 0.3013742657515686;
                                attribute sigma_mass : Real = 0.28909372274994966;
                                attribute Cx : Real = 95.47040383331478;
                                attribute sigma_Cx : Real = 28.721044428837228;
                                attribute Cy : Real = 25.583136966452003;
                                attribute sigma_Cy : Real = 28.23690002309109;
                                attribute Cz : Real = 14.539825124666095;
                                attribute sigma_Cz : Real = 29.057750463592832;
                                attribute Ixx : Real = 0.4577300568244157;
                                attribute sigma_Ixx : Real = 0.37074144170588635;
                                attribute Iyy : Real = 0.43506241096384446;
                                attribute sigma_Iyy : Real = 0.3723953238821935;
                                attribute Izz : Real = 0.4522514845491837;
                                attribute sigma_Izz : Real = 0.37017423652493897;
                                attribute Ixy : Real = 0.010077297957306877;
                                attribute sigma_Ixy : Real = 0.02351283871158888;
                                attribute Ixz : Real = -0.02689692338783546;
                                attribute sigma_Ixz : Real = 0.022566176940390956;
                                attribute Iyz : Real = 0.015255887571808577;
                                attribute sigma_Iyz : Real = 0.02209918015384651;
                            }
                            part <'C.1.2.1.1.5.1.2'> 'Part 768' {
                                attribute POIconv : String = "-";
                                attribute Ipoint : Boolean = false;
                                attribute mass : Real = 0.7623726509781554;
                                attribute sigma_mass : Real = 0.28909372274994966;
                                attribute Cx : Real = 69.47185345925391;
                                attribute sigma_Cx : Real = 28.721044428837228;
                                attribute Cy : Real = -2.0173172000795603;
                                attribute sigma_Cy : Real = 28.23690002309109;
                                attribute Cz : Real = -86.9432061444968;
                                attribute sigma_Cz : Real = 29.057750463592832;
                                attribute Ixx : Real = 0.8576376699327082;
                                attribute sigma_Ixx : Real = 0.37074144170588635;
                                attribute Iyy : Real = 0.8397148979056432;
                                attribute sigma_Iyy : Real = 0.3723953238821935;
                                attribute Izz : Real = 0.8724622839788563;
                                attribute sigma_Izz : Real = 0.37017423652493897;
                                attribute Ixy : Real = -0.0005638058209259089;
                                attribute sigma_Ixy : Real = 0.02351283871158888;
                                attribute Ixz : Real = -0.037207320753214354;
                                attribute sigma_Ixz : Real = 0.022566176940390956;
                                attribute Iyz : Real = 0.007065152923579082;
                                attribute sigma_Iyz : Real = 0.02209918015384651;
                            }
                            part <'C.1.2.1.1.5.1.3'> 'Part 769' {
                                attribute POIconv : String = "+";
                                attribute Ipoint : Boolean = false;
                                attribute mass : Real = 0.8892537194259931;
                                attribute sigma_mass : Real = 0.28909372274994966;
                                attribute Cx : Real = -64.19002362526953;
                                attribute sigma_Cx : Real = 28.721044428837228;
                                attribute Cy : Real = -53.05831846781075;
                                attribute sigma_Cy : Real = 28.23690002309109;
                                attribute Cz : Real = -96.73349955119193;
                                attribute sigma_Cz : Real = 29.057750463592832;
                                attribute Ixx : Real = 1.2116187826435152;
                                attribute sigma_Ixx : Real = 0.37074144170588635;
                                attribute Iyy : Real = 1.2584359351323027;
                                attribute sigma_Iyy : Real = 0.3723953238821935;
                                attribute Izz : Real = 1.1302634331857786;
                                attribute sigma_Izz : Real = 0.37017423652493897;
                                attribute Ixy : Real = 0.1341589230066552;
                                attribute sigma_Ixy : Real = 0.02351283871158888;
                                attribute Ixz : Real = -0.043961895459784996;
                                attribute sigma_Ixz : Real = 0.022566176940390956;
                                attribute Iyz : Real = 0.0583613139433051;
                                attribute sigma_Iyz : Real = 0.02209918015384651;
                            }
                            part <'C.1.2.1.1.5.1.4'> 'Part 770' {
                                attribute POIconv : String = "+";
                                attribute Ipoint : Boolean = false;
                                attribute mass : Real = 0.9904575951728039;
                                attribute sigma_mass : Real = 0.28909372274994966;
                                attribute Cx : Real = 61.228467524051666;
                                attribute sigma_Cx : Real = 28.721044428837228;
                                attribute Cy : Real = -57.03651010990143;
                                attribute sigma_Cy : Real = 28.23690002309109;
                                attribute Cz : Real = -75.83242342807353;
                                attribute sigma_Cz : Real = 29.057750463592832;
                                attribute Ixx : Real = 1.450999436849402;
                                attribute sigma_Ixx : Real = 0.37074144170588635;
                                attribute Iyy : Real = 1.4465851973513726;
                                attribute sigma_Iyy : Real = 0.3723953238821935;
                                attribute Izz : Real = 1.3892521103541877;
                                attribute sigma_Izz : Real = 0.37017423652493897;
                                attribute Ixy : Real = 0.052761326607632594;
                                attribute sigma_Ixy : Real = 0.02351283871158888;
                                attribute Ixz : Real = -0.026873505293566823;
                                attribute sigma_Ixz : Real = 0.022566176940390956;
                                attribute Iyz : Real = 0.04661180770760234;
                                attribute sigma_Iyz : Real = 0.02209918015384651;
                            }
                        }
                        part <'C.1.2.1.1.5.2'> 'Subassembly 218' {
                            attribute POIconv : String = "-";
                            attribute Ipoint : Boolean = false;
                            attribute mass : Real = 1.4949265108737162;
                            attribute sigma_mass : Real = 0.5007250159521434;
                            attribute Cx : Real = -75.21755519694425;
                            attribute sigma_Cx : Real = 20.12784319423887;
                            attribute Cy : Real = 24.95839353155861;
                            attribute sigma_Cy : Real = 22.58380319217517;
                            attribute Cz : Real = -18.726436068049587;
                            attribute sigma_Cz : Real = 30.18692437907815;
                            attribute Ixx : Real = 5792.626919922435;
                            attribute sigma_Ixx : Real = 4496.133846563863;
                            attribute Iyy : Real = 4195.945303357224;
                            attribute sigma_Iyy : Real = 3812.9929984886885;
                            attribute Izz : Real = 1668.5213495529517;
                            attribute sigma_Izz : Real = 1937.815746970555;
                            attribute Ixy : Real = -238.85711378480323;
                            attribute sigma_Ixy : Real = 924.3997533075286;
                            attribute Ixz : Real = 365.1830413060651;
                            attribute sigma_Ixz : Real = 1400.4571336073823;
                            attribute Iyz : Real = 2468.8772106711153;
                            attribute sigma_Iyz : Real = 1941.0270381916944;
                            part <'C.1.2.1.1.5.2.1'> 'Part 771' {
                                attribute POIconv : String = "-";
                                attribute Ipoint : Boolean = false;
                                attribute mass : Real = 0.44893197653046807;
                                attribute sigma_mass : Real = 0.28909372274994966;
                                attribute Cx : Real = -82.07687162794173;
                                attribute sigma_Cx : Real = 28.721044428837228;
                                attribute Cy : Real = -22.418993525207043;
                                attribute sigma_Cy : Real = 28.23690002309109;
                                attribute Cz : Real = 44.156579952687025;
                                attribute sigma_Cz : Real = 29.057750463592832;
                                attribute Ixx : Real = 0.5267818403123529;
                                attribute sigma_Ixx : Real = 0.37074144170588635;
                                attribute Iyy : Real = 0.5375664968353558;
                                attribute sigma_Iyy : Real = 0.3723953238821935;
                                attribute Izz : Real = 0.5297466495891611;
                                attribute sigma_Izz : Real = 0.37017423652493897;
                                attribute Ixy : Real = 0.06213713452967075;
                                attribute sigma_Ixy : Real = 0.02351283871158888;
                                attribute Ixz : Real = 0.011125821022531384;
                                attribute sigma_Ixz : Real = 0.022566176940390956;
                                attribute Iyz : Real = 0.0032525252110808655;
                                attribute sigma_Iyz : Real = 0.02209918015384651;
                            }
                            part <'C.1.2.1.1.5.2.2'> 'Part 772' {
                                attribute POIconv : String = "-";
                                attribute Ipoint : Boolean = false;
                                attribute mass : Real = 0.10964515079557896;
                                attribute sigma_mass : Real = 0.28909372274994966;
                                attribute Cx : Real = -78.54775837622583;
                                attribute sigma_Cx : Real = 28.721044428837228;
                                attribute Cy : Real = 5.75883281417191;
                                attribute sigma_Cy : Real = 28.23690002309109;
                                attribute Cz : Real = 69.36393277719617;
                                attribute sigma_Cz : Real = 29.057750463592832;
                                attribute Ixx : Real = 0.16545610425835094;
                                attribute sigma_Ixx : Real = 0.37074144170588635;
                                attribute Iyy : Real = 0.1653972942144043;
                                attribute sigma_Iyy : Real = 0.3723953238821935;
                                attribute Izz : Real = 0.16613567936764315;
                                attribute sigma_Izz : Real = 0.37017423652493897;
                                attribute Ixy : Real = -0.0015699121439025992;
                                attribute sigma_Ixy : Real = 0.02351283871158888;
                                attribute Ixz : Real = -0.0004238479312110214;
                                attribute sigma_Ixz : Real = 0.022566176940390956;
                                attribute Iyz : Real = -0.00016084089021757016;
                                attribute sigma_Iyz : Real = 0.02209918015384651;
                            }
                            part <'C.1.2.1.1.5.2.3'> 'Part 773' {
                                attribute POIconv : String = "+";
                                attribute Ipoint : Boolean = false;
                                attribute mass : Real = 0.9363493835476693;
                                attribute sigma_mass : Real = 0.28909372274994966;
                                attribute Cx : Real = -71.53889937326312;
                                attribute sigma_Cx : Real = 28.721044428837228;
                                attribute Cy : Real = 49.92168517783284;
                                attribute sigma_Cy : Real = 28.23690002309109;
                                attribute Cz : Real = -59.19090276584029;
                                attribute sigma_Cz : Real = 29.057750463592832;
                                attribute Ixx : Real = 1.1456403850620283;
                                attribute sigma_Ixx : Real = 0.37074144170588635;
                                attribute Iyy : Real = 1.0428318413211264;
                                attribute sigma_Iyy : Real = 0.3723953238821935;
                                attribute Izz : Real = 1.2169378553798562;
                                attribute sigma_Izz : Real = 0.37017423652493897;
                                attribute Ixy : Real = 0.0285679258404769;
                                attribute sigma_Ixy : Real = 0.02351283871158888;
                                attribute Ixz : Real = 0.013028664946784282;
                                attribute sigma_Ixz : Real = 0.022566176940390956;
                                attribute Iyz : Real = -0.12759449934227868;
                                attribute sigma_Iyz : Real = 0.02209918015384651;
                            }
                        }
                        part <'C.1.2.1.1.5.3'> 'Subassembly 219' {
                            attribute POIconv : String = "-";
                            attribute Ipoint : Boolean = false;
                            attribute mass : Real = 2.0465241234090645;
                            attribute sigma_mass : Real = 0.5781874454998993;
                            attribute Cx : Real = -48.90800986783696;
                            attribute sigma_Cx : Real = 27.73774491539879;
                            attribute Cy : Real = 24.09319976254735;
                            attribute sigma_Cy : Real = 20.47983305641674;
                            attribute Cz : Real = 8.907481751131122;
                            attribute sigma_Cz : Real = 25.638882012524128;
                            attribute Ixx : Real = 12443.00369084374;
                            attribute sigma_Ixx : Real = 6631.722686490458;
                            attribute Iyy : Real = 14612.266153428076;
                            attribute sigma_Iyy : Real = 9284.193773018687;
                            attribute Izz : Real = 4049.0403021782045;
                            attribute sigma_Izz : Real = 7857.7188065809;
                            attribute Ixy : Real = 1181.8816308742585;
                            attribute sigma_Ixy : Real = 2963.362679044444;
                            attribute Ixz : Real = -3038.225555760594;
                            attribute sigma_Ixz : Real = 3052.65014646926;
                            attribute Iyz : Real = 547.8140601077755;
                            attribute sigma_Iyz : Real = 2808.5267465301913;
                            part <'C.1.2.1.1.5.3.1'> 'Part 774' {
                                attribute POIconv : String = "-";
                                attribute Ipoint : Boolean = false;
                                attribute mass : Real = 0.22822092658933252;
                                attribute sigma_mass : Real = 0.28909372274994966;
                                attribute Cx : Real = -42.45407823473215;
                                attribute sigma_Cx : Real = 28.721044428837228;
                                attribute Cy : Real = 65.19768619909883;
                                attribute sigma_Cy : Real = 28.23690002309109;
                                attribute Cz : Real = 68.07190831750631;
                                attribute sigma_Cz : Real = 29.057750463592832;
                                attribute Ixx : Real = 0.2519599745029747;
                                attribute sigma_Ixx : Real = 0.37074144170588635;
                                attribute Iyy : Real = 0.2849329417934086;
                                attribute sigma_Iyy : Real = 0.3723953238821935;
                                attribute Izz : Real = 0.2544985260512138;
                                attribute sigma_Izz : Real = 0.37017423652493897;
                                attribute Ixy : Real = 0.008337022183107324;
                                attribute sigma_Ixy : Real = 0.02351283871158888;
                                attribute Ixz : Real = 0.002969449483961998;
                                attribute sigma_Ixz : Real = 0.022566176940390956;
                                attribute Iyz : Real = -0.016146147023346737;
                                attribute sigma_Iyz : Real = 0.02209918015384651;
                            }
                            part <'C.1.2.1.1.5.3.2'> 'Part 775' {
                                attribute POIconv : String = "-";
                                attribute Ipoint : Boolean = false;
                                attribute mass : Real = 0.104783451550873;
                                attribute sigma_mass : Real = 0.28909372274994966;
                                attribute Cx : Real = 99.49730103835464;
                                attribute sigma_Cx : Real = 28.721044428837228;
                                attribute Cy : Real = -41.50637527927756;
                                attribute sigma_Cy : Real = 28.23690002309109;
                                attribute Cz : Real = 24.398598726838827;
                                attribute sigma_Cz : Real = 29.057750463592832;
                                attribute Ixx : Real = 0.15946042967904428;
                                attribute sigma_Ixx : Real = 0.37074144170588635;
                                attribute Iyy : Real = 0.1360520345405073;
                                attribute sigma_Iyy : Real = 0.3723953238821935;
                                attribute Izz : Real = 0.1404153103220111;
                                attribute sigma_Izz : Real = 0.37017423652493897;
                                attribute Ixy : Real = -0.003013201887400724;
                                attribute sigma_Ixy : Real = 0.02351283871158888;
                                attribute Ixz : Real = -0.010874443877669969;
                                attribute sigma_Ixz : Real = 0.022566176940390956;
                                attribute Iyz : Real = 0.003281610730306406;
                                attribute sigma_Iyz : Real = 0.02209918015384651;
                            }
                            part <'C.1.2.1.1.5.3.3'> 'Part 776' {
                                attribute POIconv : String = "+";
                                attribute Ipoint : Boolean = false;
                                attribute mass : Real = 0.9823710635530297;
                                attribute sigma_mass : Real = 0.28909372274994966;
                                attribute Cx : Real = -42.41316132247448;
                                attribute sigma_Cx : Real = 28.721044428837228;
                                attribute Cy : Real = 16.09321190044284;
                                attribute sigma_Cy : Real = 28.23690002309109;
                                attribute Cz : Real = 67.75510092265904;
                                attribute sigma_Cz : Real = 29.057750463592832;
                                attribute Ixx : Real = 1.2763381627499564;
                                attribute sigma_Ixx : Real = 0.37074144170588635;
                                attribute Iyy : Real = 1.1808771402304434;
                                attribute sigma_Iyy : Real = 0.3723953238821935;
                                attribute Izz : Real = 1.2707901107618664;
                                attribute sigma_Izz : Real = 0.37017423652493897;
                                attribute Ixy : Real = 0.02686755004193902;
                                attribute sigma_Ixy : Real = 0.02351283871158888;
                                attribute Ixz : Real = 0.13115652833312072;
                                attribute sigma_Ixz : Real = 0.022566176940390956;
                                attribute Iyz : Real = -0.0013094827294243363;
                                attribute sigma_Iyz : Real = 0.02209918015384651;
                            }
                            part <'C.1.2.1.1.5.3.4'> 'Part 777' {
                                attribute POIconv : String = "+";
                                attribute Ipoint : Boolean = false;
                                attribute mass : Real = 0.7311486817158293;
                                attribute sigma_mass : Real = 0.28909372274994966;
                                attribute Cx : Real = -80.91749688610435;
                                attribute sigma_Cx : Real = 28.721044428837228;
                                attribute Cy : Real = 31.412918213754892;
                                attribute sigma_Cy : Real = 28.23690002309109;
                                attribute Cz : Real = -90.84783890284598;
                                attribute sigma_Cz : Real = 29.057750463592832;
                                attribute Ixx : Real = 0.9980395740991406;
                                attribute sigma_Ixx : Real = 0.37074144170588635;
                                attribute Iyy : Real = 1.053134739700956;
                                attribute sigma_Iyy : Real = 0.3723953238821935;
                                attribute Izz : Real = 0.9662200240424487;
                                attribute sigma_Izz : Real = 0.37017423652493897;
                                attribute Ixy : Real = 0.00528769245190217;
                                attribute sigma_Ixy : Real = 0.02351283871158888;
                                attribute Ixz : Real = -0.06299754912570033;
                                attribute sigma_Ixz : Real = 0.022566176940390956;
                                attribute Iyz : Real = -0.007697997122978592;
                                attribute sigma_Iyz : Real = 0.02209918015384651;
                            }
                        }
                    }
                }
                part <'C.1.2.1.2'> 'Subsystem 17' {
                    attribute POIconv : String = "-";
                    attribute Ipoint : Boolean = false;
                    attribute mass : Real = 27.25672480392945;
                    attribute sigma_mass : Real = 2.163379326394654;
                    attribute Cx : Real = -8.572234553639534;
                    attribute sigma_Cx : Real = 6.483582404584337;
                    attribute Cy : Real = -9.319328885612252;
                    attribute sigma_Cy : Real = 6.440999931098003;
                    attribute Cz : Real = -5.704620407858392;
                    attribute sigma_Cz : Real = 6.515228856636327;
                    attribute Ixx : Real = 179351.88879094648;
                    attribute sigma_Ixx : Real = 26230.263537060553;
                    attribute Iyy : Real = 177389.82918936116;
                    attribute sigma_Iyy : Real = 25555.39701246825;
                    attribute Izz : Real = 168138.89733236097;
                    attribute sigma_Izz : Real = 25491.093771776206;
                    attribute Ixy : Real = 11062.339477469986;
                    attribute sigma_Ixy : Real = 12070.822387746444;
                    attribute Ixz : Real = -11974.735089794582;
                    attribute sigma_Ixz : Real = 11994.469606430486;
                    attribute Iyz : Real = -13901.24613337552;
                    attribute sigma_Iyz : Real = 12281.36480873314;
                    part <'C.1.2.1.2.1'> 'Assembly 63' {
                        attribute POIconv : String = "-";
                        attribute Ipoint : Boolean = false;
                        attribute mass : Real = 4.156143491565715;
                        attribute sigma_mass : Real = 0.8176805270198123;
                        attribute Cx : Real = 0.603891676721497;
                        attribute sigma_Cx : Real = 16.559761351999;
                        attribute Cy : Real = -18.72011817768422;
                        attribute sigma_Cy : Real = 16.074656299951627;
                        attribute Cz : Real = -11.40155187932165;
                        attribute sigma_Cz : Real = 15.790740784289765;
                        attribute Ixx : Real = 24183.225510979242;
                        attribute sigma_Ixx : Real = 8942.72661532473;
                        attribute Iyy : Real = 24466.945148787712;
                        attribute sigma_Iyy : Real = 9219.39785693739;
                        attribute Izz : Real = 27785.308207808877;
                        attribute sigma_Izz : Real = 9922.454198259846;
                        attribute Ixy : Real = 5270.09552002747;
                        attribute sigma_Ixy : Real = 4888.975314811177;
                        attribute Ixz : Real = -4099.847116981029;
                        attribute sigma_Ixz : Real = 4201.342102463648;
                        attribute Iyz : Real = 1607.8324929080386;
                        attribute sigma_Iyz : Real = 4133.843189598347;
                        part <'C.1.2.1.2.1.1'> 'Subassembly 220' {
                            attribute POIconv : String = "-";
                            attribute Ipoint : Boolean = false;
                            attribute mass : Real = 1.8710269595130813;
                            attribute sigma_mass : Real = 0.5007250159521434;
                            attribute Cx : Real = -12.494815232730911;
                            attribute sigma_Cx : Real = 22.467452111217607;
                            attribute Cy : Real = 20.37286798727725;
                            attribute sigma_Cy : Real = 20.787485938924238;
                            attribute Cz : Real = -10.449740100502003;
                            attribute sigma_Cz : Real = 22.24592298933676;
                            attribute Ixx : Real = 7684.856934653275;
                            attribute sigma_Ixx : Real = 4658.623880357701;
                            attribute Iyy : Real = 8929.472322522835;
                            attribute sigma_Iyy : Real = 5489.329852705984;
                            attribute Izz : Real = 9133.84790337982;
                            attribute sigma_Izz : Real = 5075.524505914408;
                            attribute Ixy : Real = 2044.1719437786426;
                            attribute sigma_Ixy : Real = 2414.684044541696;
                            attribute Ixz : Real = -3342.386525398322;
                            attribute sigma_Ixz : Real = 2702.869391809356;
                            attribute Iyz : Real = -914.0604803903576;
                            attribute sigma_Iyz : Real = 2092.659697431685;
                            part <'C.1.2.1.2.1.1.1'> 'Part 778' {
                                attribute POIconv : String = "+";
                                attribute Ipoint : Boolean = false;
                                attribute mass : Real = 0.41286444995505733;
                                attribute sigma_mass : Real = 0.28909372274994966;
                                attribute Cx : Real = -80.11870658956468;
                                attribute sigma_Cx : Real = 28.721044428837228;
                                attribute Cy : Real = -9.176073502749205;
                                attribute sigma_Cy : Real = 28.23690002309109;
                                attribute Cz : Real = -93.96118237636983;
                                attribute sigma_Cz : Real = 29.057750463592832;
                                attribute Ixx : Real = 0.5006014442701897;
                                attribute sigma_Ixx : Real = 0.37074144170588635;
                                attribute Iyy : Real = 0.5613260149464682;
                                attribute sigma_Iyy : Real = 0.3723953238821935;
                                attribute Izz : Real = 0.5083341661142695;
                                attribute sigma_Izz : Real = 0.37017423652493897;
                                attribute Ixy : Real = -0.008335125569639095;
                                attribute sigma_Ixy : Real = 0.02351283871158888;
                                attribute Ixz : Real = -0.0011739496303814223;
                                attribute sigma_Ixz : Real = 0.022566176940390956;
                                attribute Iyz : Real = 0.011941151418716867;
                                attribute sigma_Iyz : Real = 0.02209918015384651;
                            }
                            part <'C.1.2.1.2.1.1.2'> 'Part 779' {
                                attribute POIconv : String = "+";
                                attribute Ipoint : Boolean = false;
                                attribute mass : Real = 0.6349201471554116;
                                attribute sigma_mass : Real = 0.28909372274994966;
                                attribute Cx : Real = -42.936782632023096;
                                attribute sigma_Cx : Real = 28.721044428837228;
                                attribute Cy : Real = 84.37530072405934;
                                attribute sigma_Cy : Real = 28.23690002309109;
                                attribute Cz : Real = 6.909901229664683;
                                attribute sigma_Cz : Real = 29.057750463592832;
                                attribute Ixx : Real = 0.8262026797328038;
                                attribute sigma_Ixx : Real = 0.37074144170588635;
                                attribute Iyy : Real = 0.7573006946951042;
                                attribute sigma_Iyy : Real = 0.3723953238821935;
                                attribute Izz : Real = 0.7951284252119959;
                                attribute sigma_Izz : Real = 0.37017423652493897;
                                attribute Ixy : Real = -0.017584851290701836;
                                attribute sigma_Ixy : Real = 0.02351283871158888;
                                attribute Ixz : Real = 0.0555827345314092;
                                attribute sigma_Ixz : Real = 0.022566176940390956;
                                attribute Iyz : Real = 0.01313166517758729;
                                attribute sigma_Iyz : Real = 0.02209918015384651;
                            }
                            part <'C.1.2.1.2.1.1.3'> 'Part 780' {
                                attribute POIconv : String = "-";
                                attribute Ipoint : Boolean = false;
                                attribute mass : Real = 0.8232423624026124;
                                attribute sigma_mass : Real = 0.28909372274994966;
                                attribute Cx : Real = 44.8974197730422;
                                attribute sigma_Cx : Real = 28.721044428837228;
                                attribute Cy : Real = -14.16948288679123;
                                attribute sigma_Cy : Real = 28.23690002309109;
                                attribute Cz : Real = 18.04359396919608;
                                attribute sigma_Cz : Real = 29.057750463592832;
                                attribute Ixx : Real = 0.8529543994773128;
                                attribute sigma_Ixx : Real = 0.37074144170588635;
                                attribute Iyy : Real = 1.0005047722865716;
                                attribute sigma_Iyy : Real = 0.3723953238821935;
                                attribute Izz : Real = 0.8875006861511404;
                                attribute sigma_Izz : Real = 0.37017423652493897;
                                attribute Ixy : Real = 0.03742509760428832;
                                attribute sigma_Ixy : Real = 0.02351283871158888;
                                attribute Ixz : Real = -0.0202389373245859;
                                attribute sigma_Ixz : Real = 0.022566176940390956;
                                attribute Iyz : Real = -0.04347066600767492;
                                attribute sigma_Iyz : Real = 0.02209918015384651;
                            }
                        }
                        part <'C.1.2.1.2.1.2'> 'Subassembly 221' {
                            attribute POIconv : String = "-";
                            attribute Ipoint : Boolean = false;
                            attribute mass : Real = 2.285116532052634;
                            attribute sigma_mass : Real = 0.6464332159373649;
                            attribute Cx : Real = 11.328961238198561;
                            attribute sigma_Cx : Real = 23.479281026296327;
                            attribute Cy : Real = -50.72900263348582;
                            attribute sigma_Cy : Real = 20.2409347451315;
                            attribute Cz : Real = -12.180884343803875;
                            attribute sigma_Cz : Real = 22.202968184689535;
                            attribute Ixx : Real = 11294.608209404085;
                            attribute sigma_Ixx : Real = 6262.314051506223;
                            attribute Iyy : Real = 14950.515973112842;
                            attribute sigma_Iyy : Real = 7231.99181364304;
                            attribute Izz : Real = 12866.908954466977;
                            attribute sigma_Izz : Real = 7132.652077885541;
                            attribute Ixy : Real = 1483.3565305092282;
                            attribute sigma_Ixy : Real = 3435.2247133554097;
                            attribute Ixz : Real = -799.8875331450397;
                            attribute sigma_Ixz : Real = 3122.340056819173;
                            attribute Iyz : Real = 2648.515841569539;
                            attribute sigma_Iyz : Real = 2724.1689221925462;
                            part <'C.1.2.1.2.1.2.1'> 'Part 781' {
                                attribute POIconv : String = "+";
                                attribute Ipoint : Boolean = false;
                                attribute mass : Real = 0.8406150858458131;
                                attribute sigma_mass : Real = 0.28909372274994966;
                                attribute Cx : Real = 28.289434034377337;
                                attribute sigma_Cx : Real = 28.721044428837228;
                                attribute Cy : Real = -92.75471246801317;
                                attribute sigma_Cy : Real = 28.23690002309109;
                                attribute Cz : Real = 54.273062804713845;
                                attribute sigma_Cz : Real = 29.057750463592832;
                                attribute Ixx : Real = 1.0377826440673519;
                                attribute sigma_Ixx : Real = 0.37074144170588635;
                                attribute Iyy : Real = 0.9991675080828684;
                                attribute sigma_Iyy : Real = 0.3723953238821935;
                                attribute Izz : Real = 0.9348811901149295;
                                attribute sigma_Izz : Real = 0.37017423652493897;
                                attribute Ixy : Real = 0.08029893263442443;
                                attribute sigma_Ixy : Real = 0.02351283871158888;
                                attribute Ixz : Real = -0.021818523502584213;
                                attribute sigma_Ixz : Real = 0.022566176940390956;
                                attribute Iyz : Real = 0.02859973497923255;
                                attribute sigma_Iyz : Real = 0.02209918015384651;
                            }
                            part <'C.1.2.1.2.1.2.2'> 'Part 782' {
                                attribute POIconv : String = "+";
                                attribute Ipoint : Boolean = false;
                                attribute mass : Real = 0.41138457311852833;
                                attribute sigma_mass : Real = 0.28909372274994966;
                                attribute Cx : Real = -60.38090195506811;
                                attribute sigma_Cx : Real = 28.721044428837228;
                                attribute Cy : Real = -74.73182738758624;
                                attribute sigma_Cy : Real = 28.23690002309109;
                                attribute Cz : Real = -70.47930038534105;
                                attribute sigma_Cz : Real = 29.057750463592832;
                                attribute Ixx : Real = 0.5922631980969985;
                                attribute sigma_Ixx : Real = 0.37074144170588635;
                                attribute Iyy : Real = 0.5411192511834149;
                                attribute sigma_Iyy : Real = 0.3723953238821935;
                                attribute Izz : Real = 0.5990343141784179;
                                attribute sigma_Izz : Real = 0.37017423652493897;
                                attribute Ixy : Real = -0.020869722686725885;
                                attribute sigma_Ixy : Real = 0.02351283871158888;
                                attribute Ixz : Real = -0.01523174005210233;
                                attribute sigma_Ixz : Real = 0.022566176940390956;
                                attribute Iyz : Real = 0.023378957476498523;
                                attribute sigma_Iyz : Real = 0.02209918015384651;
                            }
                            part <'C.1.2.1.2.1.2.3'> 'Part 783' {
                                attribute POIconv : String = "-";
                                attribute Ipoint : Boolean = false;
                                attribute mass : Real = 0.3103963250808883;
                                attribute sigma_mass : Real = 0.28909372274994966;
                                attribute Cx : Real = -86.36587564833462;
                                attribute sigma_Cx : Real = 28.721044428837228;
                                attribute Cy : Real = 37.37825551070273;
                                attribute sigma_Cy : Real = 28.23690002309109;
                                attribute Cz : Real = -12.789325974881649;
                                attribute sigma_Cz : Real = 29.057750463592832;
                                attribute Ixx : Real = 0.4558636942131506;
                                attribute sigma_Ixx : Real = 0.37074144170588635;
                                attribute Iyy : Real = 0.4362299037507578;
                                attribute sigma_Iyy : Real = 0.3723953238821935;
                                attribute Izz : Real = 0.41569703789169093;
                                attribute sigma_Izz : Real = 0.37017423652493897;
                                attribute Ixy : Real = -0.01724698906522204;
                                attribute sigma_Ixy : Real = 0.02351283871158888;
                                attribute Ixz : Real = 0.02656037023855388;
                                attribute sigma_Ixz : Real = 0.022566176940390956;
                                attribute Iyz : Real = -0.01424340741913138;
                                attribute sigma_Iyz : Real = 0.02209918015384651;
                            }
                            part <'C.1.2.1.2.1.2.4'> 'Part 784' {
                                attribute POIconv : String = "-";
                                attribute Ipoint : Boolean = false;
                                attribute mass : Real = 0.6346428919578903;
                                attribute sigma_mass : Real = 0.28909372274994966;
                                attribute Cx : Real = 77.9730660840869;
                                attribute sigma_Cx : Real = 28.721044428837228;
                                attribute Cy : Real = -28.495900006964803;
                                attribute sigma_Cy : Real = 28.23690002309109;
                                attribute Cz : Real = -50.029381830245256;
                                attribute sigma_Cz : Real = 29.057750463592832;
                                attribute Ixx : Real = 0.7329935548123732;
                                attribute sigma_Ixx : Real = 0.37074144170588635;
                                attribute Iyy : Real = 0.7614634901049598;
                                attribute sigma_Iyy : Real = 0.3723953238821935;
                                attribute Izz : Real = 0.7121820272445466;
                                attribute sigma_Izz : Real = 0.37017423652493897;
                                attribute Ixy : Real = -0.005801728419172125;
                                attribute sigma_Ixy : Real = 0.02351283871158888;
                                attribute Ixz : Real = 0.03259256217629318;
                                attribute sigma_Ixz : Real = 0.022566176940390956;
                                attribute Iyz : Real = -0.0846216388887258;
                                attribute sigma_Iyz : Real = 0.02209918015384651;
                            }
                            part <'C.1.2.1.2.1.2.5'> 'Part 785' {
                                attribute POIconv : String = "+";
                                attribute Ipoint : Boolean = false;
                                attribute mass : Real = 0.08807765604951419;
                                attribute sigma_mass : Real = 0.28909372274994966;
                                attribute Cx : Real = 48.47814557142556;
                                attribute sigma_Cx : Real = 28.721044428837228;
                                attribute Cy : Real = -8.225739328190684;
                                attribute sigma_Cy : Real = 28.23690002309109;
                                attribute Cz : Real = -99.26294223405421;
                                attribute sigma_Cz : Real = 29.057750463592832;
                                attribute Ixx : Real = 0.11491125136854019;
                                attribute sigma_Ixx : Real = 0.37074144170588635;
                                attribute Iyy : Real = 0.11290689270670443;
                                attribute sigma_Iyy : Real = 0.3723953238821935;
                                attribute Izz : Real = 0.11238279128986862;
                                attribute sigma_Izz : Real = 0.37017423652493897;
                                attribute Ixy : Real = -0.0101107471521697;
                                attribute sigma_Ixy : Real = 0.02351283871158888;
                                attribute Ixz : Real = 0.0052061339342657645;
                                attribute sigma_Ixz : Real = 0.022566176940390956;
                                attribute Iyz : Real = 0.004563497151681397;
                                attribute sigma_Iyz : Real = 0.02209918015384651;
                            }
                        }
                    }
                    part <'C.1.2.1.2.2'> 'Assembly 64' {
                        attribute POIconv : String = "-";
                        attribute Ipoint : Boolean = false;
                        attribute mass : Real = 2.973777374527883;
                        attribute sigma_mass : Real = 0.6464332159373648;
                        attribute Cx : Real = -0.6734305234581199;
                        attribute sigma_Cx : Real = 19.093743130248473;
                        attribute Cy : Real = 31.132405732898178;
                        attribute sigma_Cy : Real = 16.69617072276162;
                        attribute Cz : Real = 42.64586121110202;
                        attribute sigma_Cz : Real = 17.664254093547648;
                        attribute Ixx : Real = 14719.842096861492;
                        attribute sigma_Ixx : Real = 6518.901918875247;
                        attribute Iyy : Real = 19752.13497368992;
                        attribute sigma_Iyy : Real = 7916.021577128479;
                        attribute Izz : Real = 19456.24049368613;
                        attribute sigma_Izz : Real = 8087.3309394149555;
                        attribute Ixy : Real = 5067.557014318863;
                        attribute sigma_Ixy : Real = 3959.2568485325273;
                        attribute Ixz : Real = -3736.66226744529;
                        attribute sigma_Ixz : Real = 3726.4089147167083;
                        attribute Iyz : Real = 687.7926876975348;
                        attribute sigma_Iyz : Real = 3116.8550587308005;
                        part <'C.1.2.1.2.2.1'> 'Subassembly 222' {
                            attribute POIconv : String = "-";
                            attribute Ipoint : Boolean = false;
                            attribute mass : Real = 2.0355444495796693;
                            attribute sigma_mass : Real = 0.5007250159521434;
                            attribute Cx : Real = -3.708532819692382;
                            attribute sigma_Cx : Real = 23.301471920264138;
                            attribute Cy : Real = 29.62719535904792;
                            attribute sigma_Cy : Real = 20.894460821596297;
                            attribute Cz : Real = 48.90200677308319;
                            attribute sigma_Cz : Real = 20.72514711304791;
                            attribute Ixx : Real = 10493.399324321463;
                            attribute sigma_Ixx : Real = 5546.07490024184;
                            attribute Iyy : Real = 14038.374727917493;
                            attribute sigma_Iyy : Real = 6653.051266330394;
                            attribute Izz : Real = 15253.660300681518;
                            attribute sigma_Izz : Real = 7334.994816659488;
                            attribute Ixy : Real = 7030.6533885792805;
                            attribute sigma_Ixy : Real = 3601.6828008288817;
                            attribute Ixz : Real = -1160.09954011517;
                            attribute sigma_Ixz : Real = 3044.6840910435844;
                            attribute Iyz : Real = 2500.93634455625;
                            attribute sigma_Iyz : Real = 2643.1101776696305;
                            part <'C.1.2.1.2.2.1.1'> 'Part 786' {
                                attribute POIconv : String = "+";
                                attribute Ipoint : Boolean = false;
                                attribute mass : Real = 0.7031996298830491;
                                attribute sigma_mass : Real = 0.28909372274994966;
                                attribute Cx : Real = 81.47697360254824;
                                attribute sigma_Cx : Real = 28.721044428837228;
                                attribute Cy : Real = -43.803377309814095;
                                attribute sigma_Cy : Real = 28.23690002309109;
                                attribute Cz : Real = 86.12206494435668;
                                attribute sigma_Cz : Real = 29.057750463592832;
                                attribute Ixx : Real = 0.8271366912517517;
                                attribute sigma_Ixx : Real = 0.37074144170588635;
                                attribute Iyy : Real = 0.8186292982732727;
                                attribute sigma_Iyy : Real = 0.3723953238821935;
                                attribute Izz : Real = 0.804797359763256;
                                attribute sigma_Izz : Real = 0.37017423652493897;
                                attribute Ixy : Real = 0.021796703704930157;
                                attribute sigma_Ixy : Real = 0.02351283871158888;
                                attribute Ixz : Real = -0.023162278768574483;
                                attribute sigma_Ixz : Real = 0.022566176940390956;
                                attribute Iyz : Real = 0.08761959001342756;
                                attribute sigma_Iyz : Real = 0.02209918015384651;
                            }
                            part <'C.1.2.1.2.2.1.2'> 'Part 787' {
                                attribute POIconv : String = "-";
                                attribute Ipoint : Boolean = false;
                                attribute mass : Real = 0.6107096083378419;
                                attribute sigma_mass : Real = 0.28909372274994966;
                                attribute Cx : Real = -10.976454429328442;
                                attribute sigma_Cx : Real = 28.721044428837228;
                                attribute Cy : Real = 61.08013056218624;
                                attribute sigma_Cy : Real = 28.23690002309109;
                                attribute Cz : Real = -23.59348777681589;
                                attribute sigma_Cz : Real = 29.057750463592832;
                                attribute Ixx : Real = 0.7580609423746537;
                                attribute sigma_Ixx : Real = 0.37074144170588635;
                                attribute Iyy : Real = 0.8641249607043112;
                                attribute sigma_Iyy : Real = 0.3723953238821935;
                                attribute Izz : Real = 0.8865991324989235;
                                attribute sigma_Izz : Real = 0.37017423652493897;
                                attribute Ixy : Real = -0.029844529749869755;
                                attribute sigma_Ixy : Real = 0.02351283871158888;
                                attribute Ixz : Real = 0.0134027210150167;
                                attribute sigma_Ixz : Real = 0.022566176940390956;
                                attribute Iyz : Real = 0.0010237878947334162;
                                attribute sigma_Iyz : Real = 0.02209918015384651;
                            }
                            part <'C.1.2.1.2.2.1.3'> 'Part 788' {
                                attribute POIconv : String = "+";
                                attribute Ipoint : Boolean = false;
                                attribute mass : Real = 0.7216352113587782;
                                attribute sigma_mass : Real = 0.28909372274994966;
                                attribute Cx : Real = -80.56707042269409;
                                attribute sigma_Cx : Real = 28.721044428837228;
                                attribute Cy : Real = 74.56366918049753;
                                attribute sigma_Cy : Real = 28.23690002309109;
                                attribute Cz : Real = 73.98471292108297;
                                attribute sigma_Cz : Real = 29.057750463592832;
                                attribute Ixx : Real = 0.9517261039315572;
                                attribute sigma_Ixx : Real = 0.37074144170588635;
                                attribute Iyy : Real = 0.9263140208916567;
                                attribute sigma_Iyy : Real = 0.3723953238821935;
                                attribute Izz : Real = 0.9808649857378658;
                                attribute sigma_Izz : Real = 0.37017423652493897;
                                attribute Ixy : Real = -0.0807944541635773;
                                attribute sigma_Ixy : Real = 0.02351283871158888;
                                attribute Ixz : Real = -0.030194919784497253;
                                attribute sigma_Ixz : Real = 0.022566176940390956;
                                attribute Iyz : Real = 0.04721151010382231;
                                attribute sigma_Iyz : Real = 0.02209918015384651;
                            }
                        }
                        part <'C.1.2.1.2.2.2'> 'Subassembly 223' {
                            attribute POIconv : String = "-";
                            attribute Ipoint : Boolean = false;
                            attribute mass : Real = 0.9382329249482138;
                            attribute sigma_mass : Real = 0.40884026350990615;
                            attribute Cx : Real = 5.91137956871293;
                            attribute sigma_Cx : Real = 33.10533522904533;
                            attribute Cy : Real = 34.398036836293684;
                            attribute sigma_Cy : Real = 27.254999744359914;
                            attribute Cz : Real = 29.072832557096802;
                            attribute sigma_Cz : Real = 32.66059121429138;
                            attribute Ixx : Real = 3959.3074446074015;
                            attribute sigma_Ixx : Real = 3273.4499649918243;
                            attribute Iyy : Real = 5401.809764450042;
                            attribute sigma_Iyy : Real = 4143.699522966448;
                            attribute Izz : Real = 4128.530061359201;
                            attribute sigma_Izz : Real = 3362.69861886119;
                            attribute Ixy : Real = -1933.6217070724945;
                            attribute sigma_Ixy : Real = 1625.7647317769693;
                            attribute Ixz : Real = -2699.069063668282;
                            attribute sigma_Ixz : Real = 2071.6418956026323;
                            attribute Iyz : Real = -1873.8987123134775;
                            attribute sigma_Iyz : Real = 1588.423690951579;
                            part <'C.1.2.1.2.2.2.1'> 'Part 789' {
                                attribute POIconv : String = "-";
                                attribute Ipoint : Boolean = false;
                                attribute mass : Real = 0.5963625535315369;
                                attribute sigma_mass : Real = 0.28909372274994966;
                                attribute Cx : Real = -35.33959714695811;
                                attribute sigma_Cx : Real = 28.721044428837228;
                                attribute Cy : Real = 5.758345918729901;
                                attribute sigma_Cy : Real = 28.23690002309109;
                                attribute Cz : Real = -10.905125783756375;
                                attribute sigma_Cz : Real = 29.057750463592832;
                                attribute Ixx : Real = 0.7097071432749391;
                                attribute sigma_Ixx : Real = 0.37074144170588635;
                                attribute Iyy : Real = 0.6050444493016389;
                                attribute sigma_Iyy : Real = 0.3723953238821935;
                                attribute Izz : Real = 0.7361689943627573;
                                attribute sigma_Izz : Real = 0.37017423652493897;
                                attribute Ixy : Real = -0.0514443556230926;
                                attribute sigma_Ixy : Real = 0.02351283871158888;
                                attribute Ixz : Real = 0.0009522132880161172;
                                attribute sigma_Ixz : Real = 0.022566176940390956;
                                attribute Iyz : Real = 0.0027711750428329107;
                                attribute sigma_Iyz : Real = 0.02209918015384651;
                            }
                            part <'C.1.2.1.2.2.2.2'> 'Part 790' {
                                attribute POIconv : String = "+";
                                attribute Ipoint : Boolean = false;
                                attribute mass : Real = 0.3418703714166768;
                                attribute sigma_mass : Real = 0.28909372274994966;
                                attribute Cx : Real = 77.8700512368232;
                                attribute sigma_Cx : Real = 28.721044428837228;
                                attribute Cy : Real = 84.35743851587176;
                                attribute sigma_Cy : Real = 28.23690002309109;
                                attribute Cz : Real = 98.81083653308451;
                                attribute sigma_Cz : Real = 29.057750463592832;
                                attribute Ixx : Real = 0.3761324052244434;
                                attribute sigma_Ixx : Real = 0.37074144170588635;
                                attribute Iyy : Real = 0.4090230709603732;
                                attribute sigma_Iyy : Real = 0.3723953238821935;
                                attribute Izz : Real = 0.3315132307243925;
                                attribute sigma_Izz : Real = 0.37017423652493897;
                                attribute Ixy : Real = -0.009686537253991271;
                                attribute sigma_Ixy : Real = 0.02351283871158888;
                                attribute Ixz : Real = -0.0016634354892348304;
                                attribute sigma_Ixz : Real = 0.022566176940390956;
                                attribute Iyz : Real = -0.007568236412766384;
                                attribute sigma_Iyz : Real = 0.02209918015384651;
                            }
                        }
                    }
                    part <'C.1.2.1.2.3'> 'Assembly 65' {
                        attribute POIconv : String = "-";
                        attribute Ipoint : Boolean = false;
                        attribute mass : Real = 5.042212698342744;
                        attribute sigma_mass : Real = 1.0423422407897138;
                        attribute Cx : Real = 12.09722488484198;
                        attribute sigma_Cx : Real = 15.380857287545778;
                        attribute Cy : Real = -9.944192325300824;
                        attribute sigma_Cy : Real = 16.628257083545627;
                        attribute Cz : Real = 4.001875641439915;
                        attribute sigma_Cz : Real = 16.75271053964809;
                        attribute Ixx : Real = 30387.80880143847;
                        attribute sigma_Ixx : Real = 12782.230252374344;
                        attribute Iyy : Real = 33657.53725132164;
                        attribute sigma_Iyy : Real = 11769.50839993066;
                        attribute Izz : Real = 24777.40657957908;
                        attribute sigma_Izz : Real = 10870.192847062006;
                        attribute Ixy : Real = -4064.797283358908;
                        attribute sigma_Ixy : Real = 4830.2868098825975;
                        attribute Ixz : Real = 1454.915744943317;
                        attribute sigma_Ixz : Real = 5708.963097662048;
                        attribute Iyz : Real = 7952.045592226707;
                        attribute sigma_Iyz : Real = 5486.68013237591;
                        part <'C.1.2.1.2.3.1'> 'Subassembly 224' {
                            attribute POIconv : String = "-";
                            attribute Ipoint : Boolean = false;
                            attribute mass : Real = 1.0772014544475823;
                            attribute sigma_mass : Real = 0.5781874454998993;
                            attribute Cx : Real = -29.85636324355656;
                            attribute sigma_Cx : Real = 28.467453029837625;
                            attribute Cy : Real = -30.340307113302735;
                            attribute sigma_Cy : Real = 49.50819854744116;
                            attribute Cz : Real = -18.02902794366928;
                            attribute sigma_Cz : Real = 28.459580757448638;
                            attribute Ixx : Real = 4853.052958352444;
                            attribute sigma_Ixx : Real = 6791.425662120865;
                            attribute Iyy : Real = 4353.40151749965;
                            attribute sigma_Iyy : Real = 3253.9736945566806;
                            attribute Izz : Real = 5221.689005485604;
                            attribute sigma_Izz : Real = 6666.864066212959;
                            attribute Ixy : Real = -802.6516791862957;
                            attribute sigma_Ixy : Real = 2023.3321592388666;
                            attribute Ixz : Real = -2111.237498774969;
                            attribute sigma_Ixz : Real = 1593.9810730126521;
                            attribute Iyz : Real = -965.5330107531322;
                            attribute sigma_Iyz : Real = 2248.1521520288634;
                            part <'C.1.2.1.2.3.1.1'> 'Part 791' {
                                attribute POIconv : String = "-";
                                attribute Ipoint : Boolean = false;
                                attribute mass : Real = 0.012558446371462195;
                                attribute sigma_mass : Real = 0.28909372274994966;
                                attribute Cx : Real = -9.401254961267114;
                                attribute sigma_Cx : Real = 28.721044428837228;
                                attribute Cy : Real = 96.58035659231246;
                                attribute sigma_Cy : Real = 28.23690002309109;
                                attribute Cz : Real = -64.46152739226818;
                                attribute sigma_Cz : Real = 29.057750463592832;
                                attribute Ixx : Real = 0.015639866775647954;
                                attribute sigma_Ixx : Real = 0.37074144170588635;
                                attribute Iyy : Real = 0.015467731929471446;
                                attribute sigma_Iyy : Real = 0.3723953238821935;
                                attribute Izz : Real = 0.018537051960053934;
                                attribute sigma_Izz : Real = 0.37017423652493897;
                                attribute Ixy : Real = 0.00018817300658688984;
                                attribute sigma_Ixy : Real = 0.02351283871158888;
                                attribute Ixz : Real = 0.0009787084608281348;
                                attribute sigma_Ixz : Real = 0.022566176940390956;
                                attribute Iyz : Real = 0.0007396656484681778;
                                attribute sigma_Iyz : Real = 0.02209918015384651;
                            }
                            part <'C.1.2.1.2.3.1.2'> 'Part 792' {
                                attribute POIconv : String = "-";
                                attribute Ipoint : Boolean = false;
                                attribute mass : Real = 0.13000083908019588;
                                attribute sigma_mass : Real = 0.28909372274994966;
                                attribute Cx : Real = -72.66408405266702;
                                attribute sigma_Cx : Real = 28.721044428837228;
                                attribute Cy : Real = 74.18267871253192;
                                attribute sigma_Cy : Real = 28.23690002309109;
                                attribute Cz : Real = -38.575056521221995;
                                attribute sigma_Cz : Real = 29.057750463592832;
                                attribute Ixx : Real = 0.1786128631912603;
                                attribute sigma_Ixx : Real = 0.37074144170588635;
                                attribute Iyy : Real = 0.1621730835901498;
                                attribute sigma_Iyy : Real = 0.3723953238821935;
                                attribute Izz : Real = 0.16749981245858192;
                                attribute sigma_Izz : Real = 0.37017423652493897;
                                attribute Ixy : Real = 0.0027644068384633305;
                                attribute sigma_Ixy : Real = 0.02351283871158888;
                                attribute Ixz : Real = -0.0005334154205201602;
                                attribute sigma_Ixz : Real = 0.022566176940390956;
                                attribute Iyz : Real = 0.0036116496686958302;
                                attribute sigma_Iyz : Real = 0.02209918015384651;
                            }
                            part <'C.1.2.1.2.3.1.3'> 'Part 793' {
                                attribute POIconv : String = "-";
                                attribute Ipoint : Boolean = false;
                                attribute mass : Real = 0.4713674660718534;
                                attribute sigma_mass : Real = 0.28909372274994966;
                                attribute Cx : Real = 22.665188275277615;
                                attribute sigma_Cx : Real = 28.721044428837228;
                                attribute Cy : Real = -14.303641393780708;
                                attribute sigma_Cy : Real = 28.23690002309109;
                                attribute Cz : Real = 30.133107444271445;
                                attribute sigma_Cz : Real = 29.057750463592832;
                                attribute Ixx : Real = 0.5397245576688406;
                                attribute sigma_Ixx : Real = 0.37074144170588635;
                                attribute Iyy : Real = 0.6836537021671852;
                                attribute sigma_Iyy : Real = 0.3723953238821935;
                                attribute Izz : Real = 0.6085699672212673;
                                attribute sigma_Izz : Real = 0.37017423652493897;
                                attribute Ixy : Real = -0.03318666805579211;
                                attribute sigma_Ixy : Real = 0.02351283871158888;
                                attribute Ixz : Real = 0.008271110673804191;
                                attribute sigma_Ixz : Real = 0.022566176940390956;
                                attribute Iyz : Real = -0.039573510499747326;
                                attribute sigma_Iyz : Real = 0.02209918015384651;
                            }
                            part <'C.1.2.1.2.3.1.4'> 'Part 794' {
                                attribute POIconv : String = "+";
                                attribute Ipoint : Boolean = false;
                                attribute mass : Real = 0.46327470292407086;
                                attribute sigma_mass : Real = 0.28909372274994966;
                                attribute Cx : Real = -71.8374929856509;
                                attribute sigma_Cx : Real = 28.721044428837228;
                                attribute Cy : Real = -79.42816913127899;
                                attribute sigma_Cy : Real = 28.23690002309109;
                                attribute Cz : Real = -60.00831709243357;
                                attribute sigma_Cz : Real = 29.057750463592832;
                                attribute Ixx : Real = 0.4667536653394323;
                                attribute sigma_Ixx : Real = 0.37074144170588635;
                                attribute Iyy : Real = 0.5582397311971575;
                                attribute sigma_Iyy : Real = 0.3723953238821935;
                                attribute Izz : Real = 0.5499085677142368;
                                attribute sigma_Izz : Real = 0.37017423652493897;
                                attribute Ixy : Real = -0.026660538558051554;
                                attribute sigma_Ixy : Real = 0.02351283871158888;
                                attribute Ixz : Real = 0.0403206039388385;
                                attribute sigma_Ixz : Real = 0.022566176940390956;
                                attribute Iyz : Real = -0.03456744239219553;
                                attribute sigma_Iyz : Real = 0.02209918015384651;
                            }
                        }
                        part <'C.1.2.1.2.3.2'> 'Subassembly 225' {
                            attribute POIconv : String = "-";
                            attribute Ipoint : Boolean = false;
                            attribute mass : Real = 0.5240436705516186;
                            attribute sigma_mass : Real = 0.40884026350990615;
                            attribute Cx : Real = 45.72983586371949;
                            attribute sigma_Cx : Real = 32.5735618815654;
                            attribute Cy : Real = -28.97648182965912;
                            attribute sigma_Cy : Real = 36.11415143466105;
                            attribute Cz : Real = 37.20932025758853;
                            attribute sigma_Cz : Real = 23.18491657469875;
                            attribute Ixx : Real = 396.7679487484478;
                            attribute sigma_Ixx : Real = 850.4957218996514;
                            attribute Iyy : Real = 267.70004300630467;
                            attribute sigma_Iyy : Real = 622.3705194396888;
                            attribute Izz : Real = 662.1573028622296;
                            attribute sigma_Izz : Real = 1323.8266988566097;
                            attribute Ixy : Real = -324.4526412540889;
                            attribute sigma_Ixy : Real = 652.698861972709;
                            attribute Ixz : Real = -14.336560607942442;
                            attribute sigma_Ixz : Real = 209.21111880505416;
                            attribute Iyz : Real = -17.418460089504798;
                            attribute sigma_Iyz : Real = 254.83166285553742;
                            part <'C.1.2.1.2.3.2.1'> 'Part 795' {
                                attribute POIconv : String = "-";
                                attribute Ipoint : Boolean = false;
                                attribute mass : Real = 0.39806503427005374;
                                attribute sigma_mass : Real = 0.28909372274994966;
                                attribute Cx : Real = 33.050579437986016;
                                attribute sigma_Cx : Real = 28.721044428837228;
                                attribute Cy : Real = -44.42807612940669;
                                attribute sigma_Cy : Real = 28.23690002309109;
                                attribute Cz : Real = 36.527072079479694;
                                attribute sigma_Cz : Real = 29.057750463592832;
                                attribute Ixx : Real = 0.5221425703793039;
                                attribute sigma_Ixx : Real = 0.37074144170588635;
                                attribute Iyy : Real = 0.5838256671670221;
                                attribute sigma_Iyy : Real = 0.3723953238821935;
                                attribute Izz : Real = 0.48283318939255543;
                                attribute sigma_Izz : Real = 0.37017423652493897;
                                attribute Ixy : Real = -0.052691696772483615;
                                attribute sigma_Ixy : Real = 0.02351283871158888;
                                attribute Ixz : Real = -0.01589208358967671;
                                attribute sigma_Ixz : Real = 0.022566176940390956;
                                attribute Iyz : Real = 0.03376923647044447;
                                attribute sigma_Iyz : Real = 0.02209918015384651;
                            }
                            part <'C.1.2.1.2.3.2.2'> 'Part 796' {
                                attribute POIconv : String = "+";
                                attribute Ipoint : Boolean = false;
                                attribute mass : Real = 0.12597863628156483;
                                attribute sigma_mass : Real = 0.28909372274994966;
                                attribute Cx : Real = 85.793522791937;
                                attribute sigma_Cx : Real = 28.721044428837228;
                                attribute Cy : Real = 19.847188564017415;
                                attribute sigma_Cy : Real = 28.23690002309109;
                                attribute Cz : Real = 39.365075808018446;
                                attribute sigma_Cz : Real = 29.057750463592832;
                                attribute Ixx : Real = 0.13465962923434727;
                                attribute sigma_Ixx : Real = 0.37074144170588635;
                                attribute Iyy : Real = 0.14294484600814117;
                                attribute sigma_Iyy : Real = 0.3723953238821935;
                                attribute Izz : Real = 0.13153587967221464;
                                attribute sigma_Izz : Real = 0.37017423652493897;
                                attribute Ixy : Real = -0.008150964249004536;
                                attribute sigma_Ixy : Real = 0.02351283871158888;
                                attribute Ixz : Real = -0.003214904828495585;
                                attribute sigma_Ixz : Real = 0.022566176940390956;
                                attribute Iyz : Real = -0.0035920655210944325;
                                attribute sigma_Iyz : Real = 0.02209918015384651;
                            }
                        }
                        part <'C.1.2.1.2.3.3'> 'Subassembly 226' {
                            attribute POIconv : String = "-";
                            attribute Ipoint : Boolean = false;
                            attribute mass : Real = 1.2148368115082848;
                            attribute sigma_mass : Real = 0.5007250159521434;
                            attribute Cx : Real = 1.7569335939661257;
                            attribute sigma_Cx : Real = 33.09919518825618;
                            attribute Cy : Real = -35.319652118346326;
                            attribute sigma_Cy : Real = 24.639310325110376;
                            attribute Cz : Real = 76.84959931822362;
                            attribute sigma_Cz : Real = 29.821975821529882;
                            attribute Ixx : Real = 1022.5844454239185;
                            attribute sigma_Ixx : Real = 1780.9523559366837;
                            attribute Iyy : Real = 2055.4398729786394;
                            attribute sigma_Iyy : Real = 3413.8463572067226;
                            attribute Izz : Real = 1246.7478311399184;
                            attribute sigma_Izz : Real = 2319.234646474648;
                            attribute Ixy : Real = -28.67555779015976;
                            attribute sigma_Ixy : Real = 778.235185273009;
                            attribute Ixz : Real = -949.9034197766925;
                            attribute sigma_Ixz : Real = 1605.7193385074374;
                            attribute Iyz : Real = 89.87513293107426;
                            attribute sigma_Iyz : Real = 525.0626599492441;
                            part <'C.1.2.1.2.3.3.1'> 'Part 797' {
                                attribute POIconv : String = "+";
                                attribute Ipoint : Boolean = false;
                                attribute mass : Real = 0.07205253432295285;
                                attribute sigma_mass : Real = 0.28909372274994966;
                                attribute Cx : Real = 68.93592262640595;
                                attribute sigma_Cx : Real = 28.721044428837228;
                                attribute Cy : Real = -2.637602109462023;
                                attribute sigma_Cy : Real = 28.23690002309109;
                                attribute Cz : Real = 99.48066803626716;
                                attribute sigma_Cz : Real = 29.057750463592832;
                                attribute Ixx : Real = 0.11211532557190812;
                                attribute sigma_Ixx : Real = 0.37074144170588635;
                                attribute Iyy : Real = 0.10582829990345527;
                                attribute sigma_Iyy : Real = 0.3723953238821935;
                                attribute Izz : Real = 0.10527760182278931;
                                attribute sigma_Izz : Real = 0.37017423652493897;
                                attribute Ixy : Real = 0.004385117292331931;
                                attribute sigma_Ixy : Real = 0.02351283871158888;
                                attribute Ixz : Real = -0.0037896988567930195;
                                attribute sigma_Ixz : Real = 0.022566176940390956;
                                attribute Iyz : Real = 0.0019253537541727747;
                                attribute sigma_Iyz : Real = 0.02209918015384651;
                            }
                            part <'C.1.2.1.2.3.3.2'> 'Part 798' {
                                attribute POIconv : String = "+";
                                attribute Ipoint : Boolean = false;
                                attribute mass : Real = 0.15758021018328144;
                                attribute sigma_mass : Real = 0.28909372274994966;
                                attribute Cx : Real = -68.36304180324078;
                                attribute sigma_Cx : Real = 28.721044428837228;
                                attribute Cy : Real = -25.796094117686152;
                                attribute sigma_Cy : Real = 28.23690002309109;
                                attribute Cz : Real = 6.208848906680942;
                                attribute sigma_Cz : Real = 29.057750463592832;
                                attribute Ixx : Real = 0.15362150771886662;
                                attribute sigma_Ixx : Real = 0.37074144170588635;
                                attribute Iyy : Real = 0.20440283854162733;
                                attribute sigma_Iyy : Real = 0.3723953238821935;
                                attribute Izz : Real = 0.18334220277604707;
                                attribute sigma_Izz : Real = 0.37017423652493897;
                                attribute Ixy : Real = -0.000839053861175939;
                                attribute sigma_Ixy : Real = 0.02351283871158888;
                                attribute Ixz : Real = -0.020888683997046145;
                                attribute sigma_Ixz : Real = 0.022566176940390956;
                                attribute Iyz : Real = -0.0003394102806807878;
                                attribute sigma_Iyz : Real = 0.02209918015384651;
                            }
                            part <'C.1.2.1.2.3.3.3'> 'Part 799' {
                                attribute POIconv : String = "+";
                                attribute Ipoint : Boolean = false;
                                attribute mass : Real = 0.9852040670020505;
                                attribute sigma_mass : Real = 0.28909372274994966;
                                attribute Cx : Real = 8.059286838397384;
                                attribute sigma_Cx : Real = 28.721044428837228;
                                attribute Cy : Real = -39.23310409300029;
                                attribute sigma_Cy : Real = 28.23690002309109;
                                attribute Cz : Real = 86.49324448779225;
                                attribute sigma_Cz : Real = 29.057750463592832;
                                attribute Ixx : Real = 1.1073300174930836;
                                attribute sigma_Ixx : Real = 0.37074144170588635;
                                attribute Iyy : Real = 1.1611449787739927;
                                attribute sigma_Iyy : Real = 0.3723953238821935;
                                attribute Izz : Real = 1.019627518350172;
                                attribute sigma_Izz : Real = 0.37017423652493897;
                                attribute Ixy : Real = 0.0070599408844334;
                                attribute sigma_Ixy : Real = 0.02351283871158888;
                                attribute Ixz : Real = -0.04051163122632177;
                                attribute sigma_Ixz : Real = 0.022566176940390956;
                                attribute Iyz : Real = 0.024918638078416794;
                                attribute sigma_Iyz : Real = 0.02209918015384651;
                            }
                        }
                        part <'C.1.2.1.2.3.4'> 'Subassembly 227' {
                            attribute POIconv : String = "-";
                            attribute Ipoint : Boolean = false;
                            attribute mass : Real = 2.2261307618352584;
                            attribute sigma_mass : Real = 0.5781874454998993;
                            attribute Cx : Real = 30.12369324575326;
                            attribute sigma_Cx : Real = 21.322315481091433;
                            attribute Cy : Real = 18.25339566336283;
                            attribute sigma_Cy : Real = 21.564683280626813;
                            attribute Cz : Real = -32.90904062073485;
                            attribute sigma_Cz : Real = 22.917361297164266;
                            attribute Ixx : Real = 10344.694237704647;
                            attribute sigma_Ixx : Real = 6549.206601677248;
                            attribute Iyy : Real = 13058.442249069465;
                            attribute sigma_Iyy : Real = 6999.3873433360895;
                            attribute Izz : Real = 11114.575047776514;
                            attribute sigma_Izz : Real = 6133.384288105696;
                            attribute Ixy : Real = -872.4005757705615;
                            attribute sigma_Ixy : Real = 2864.2990817689515;
                            attribute Ixz : Real = 3714.9994373009986;
                            attribute sigma_Ixz : Real = 3377.8864137444357;
                            attribute Iyz : Real = 4435.319933053629;
                            attribute sigma_Iyz : Real = 3213.527194388968;
                            part <'C.1.2.1.2.3.4.1'> 'Part 800' {
                                attribute POIconv : String = "-";
                                attribute Ipoint : Boolean = false;
                                attribute mass : Real = 0.412517970159417;
                                attribute sigma_mass : Real = 0.28909372274994966;
                                attribute Cx : Real = 33.30162116326392;
                                attribute sigma_Cx : Real = 28.721044428837228;
                                attribute Cy : Real = -51.69420065358281;
                                attribute sigma_Cy : Real = 28.23690002309109;
                                attribute Cz : Real = 18.527037790045142;
                                attribute sigma_Cz : Real = 29.057750463592832;
                                attribute Ixx : Real = 0.39914024350096833;
                                attribute sigma_Ixx : Real = 0.37074144170588635;
                                attribute Iyy : Real = 0.4004222290436658;
                                attribute sigma_Iyy : Real = 0.3723953238821935;
                                attribute Izz : Real = 0.4117342307167128;
                                attribute sigma_Izz : Real = 0.37017423652493897;
                                attribute Ixy : Real = 0.016242073070566482;
                                attribute sigma_Ixy : Real = 0.02351283871158888;
                                attribute Ixz : Real = -0.00856392281014176;
                                attribute sigma_Ixz : Real = 0.022566176940390956;
                                attribute Iyz : Real = 0.008455876638044018;
                                attribute sigma_Iyz : Real = 0.02209918015384651;
                            }
                            part <'C.1.2.1.2.3.4.2'> 'Part 801' {
                                attribute POIconv : String = "-";
                                attribute Ipoint : Boolean = false;
                                attribute mass : Real = 0.8211163207006175;
                                attribute sigma_mass : Real = 0.28909372274994966;
                                attribute Cx : Real = -38.44122253358364;
                                attribute sigma_Cx : Real = 28.721044428837228;
                                attribute Cy : Real = 23.973912466317415;
                                attribute sigma_Cy : Real = 28.23690002309109;
                                attribute Cz : Real = -6.632704706862569;
                                attribute sigma_Cz : Real = 29.057750463592832;
                                attribute Ixx : Real = 1.0889735886199274;
                                attribute sigma_Ixx : Real = 0.37074144170588635;
                                attribute Iyy : Real = 1.075248296849076;
                                attribute sigma_Iyy : Real = 0.3723953238821935;
                                attribute Izz : Real = 1.0801764746287663;
                                attribute sigma_Izz : Real = 0.37017423652493897;
                                attribute Ixy : Real = -0.0027327348575962762;
                                attribute sigma_Ixy : Real = 0.02351283871158888;
                                attribute Ixz : Real = 0.00799863620921257;
                                attribute sigma_Ixz : Real = 0.022566176940390956;
                                attribute Iyz : Real = -0.0016216595719821237;
                                attribute sigma_Iyz : Real = 0.02209918015384651;
                            }
                            part <'C.1.2.1.2.3.4.3'> 'Part 802' {
                                attribute POIconv : String = "+";
                                attribute Ipoint : Boolean = false;
                                attribute mass : Real = 0.13423355266870932;
                                attribute sigma_mass : Real = 0.28909372274994966;
                                attribute Cx : Real = 88.8820132240653;
                                attribute sigma_Cx : Real = 28.721044428837228;
                                attribute Cy : Real = -57.840714836493134;
                                attribute sigma_Cy : Real = 28.23690002309109;
                                attribute Cz : Real = 54.37013851478696;
                                attribute sigma_Cz : Real = 29.057750463592832;
                                attribute Ixx : Real = 0.18268631099148483;
                                attribute sigma_Ixx : Real = 0.37074144170588635;
                                attribute Iyy : Real = 0.17522656286624175;
                                attribute sigma_Iyy : Real = 0.3723953238821935;
                                attribute Izz : Real = 0.18576274098727155;
                                attribute sigma_Izz : Real = 0.37017423652493897;
                                attribute Ixy : Real = 0.017604999117550334;
                                attribute sigma_Ixy : Real = 0.02351283871158888;
                                attribute Ixz : Real = -0.006578320417710843;
                                attribute sigma_Ixz : Real = 0.022566176940390956;
                                attribute Iyz : Real = -0.0001542702207145344;
                                attribute sigma_Iyz : Real = 0.02209918015384651;
                            }
                            part <'C.1.2.1.2.3.4.4'> 'Part 803' {
                                attribute POIconv : String = "-";
                                attribute Ipoint : Boolean = false;
                                attribute mass : Real = 0.8582629183065146;
                                attribute sigma_mass : Real = 0.28909372274994966;
                                attribute Cx : Real = 85.00370723195374;
                                attribute sigma_Cx : Real = 28.721044428837228;
                                attribute Cy : Real = 58.3015123847872;
                                attribute sigma_Cy : Real = 28.23690002309109;
                                attribute Cz : Real = -96.42108110710979;
                                attribute sigma_Cz : Real = 29.057750463592832;
                                attribute Ixx : Real = 1.1485407594489083;
                                attribute sigma_Ixx : Real = 0.37074144170588635;
                                attribute Iyy : Real = 1.148576204634625;
                                attribute sigma_Iyy : Real = 0.3723953238821935;
                                attribute Izz : Real = 1.201531343942549;
                                attribute sigma_Izz : Real = 0.37017423652493897;
                                attribute Ixy : Real = -0.012600764820023994;
                                attribute sigma_Ixy : Real = 0.02351283871158888;
                                attribute Ixz : Real = -0.03880720970075034;
                                attribute sigma_Ixz : Real = 0.022566176940390956;
                                attribute Iyz : Real = 0.041898289418054985;
                                attribute sigma_Iyz : Real = 0.02209918015384651;
                            }
                        }
                    }
                    part <'C.1.2.1.2.4'> 'Assembly 66' {
                        attribute POIconv : String = "-";
                        attribute Ipoint : Boolean = false;
                        attribute mass : Real = 11.37820858547068;
                        attribute sigma_mass : Real = 1.355969753252389;
                        attribute Cx : Real = -16.36138004206407;
                        attribute sigma_Cx : Real = 9.80498936648042;
                        attribute Cy : Real = -9.067961222285742;
                        attribute sigma_Cy : Real = 9.732806934407346;
                        attribute Cz : Real = -18.628458841523685;
                        attribute sigma_Cz : Real = 9.625193022353296;
                        attribute Ixx : Real = 68768.39661754506;
                        attribute sigma_Ixx : Real = 15897.34413324861;
                        attribute Iyy : Real = 61422.66438181892;
                        attribute sigma_Iyy : Real = 14903.497345450984;
                        attribute Izz : Real = 63980.443693964866;
                        attribute sigma_Izz : Real = 15620.624513224811;
                        attribute Ixy : Real = 9208.337027526852;
                        attribute sigma_Ixy : Real = 7380.636469071498;
                        attribute Ixz : Real = -4608.677154618289;
                        attribute sigma_Ixz : Real = 6978.277859052828;
                        attribute Iyz : Real = -10257.184611148448;
                        attribute sigma_Iyz : Real = 7635.788492709429;
                        part <'C.1.2.1.2.4.1'> 'Subassembly 228' {
                            attribute POIconv : String = "-";
                            attribute Ipoint : Boolean = false;
                            attribute mass : Real = 2.7242623378606514;
                            attribute sigma_mass : Real = 0.6464332159373649;
                            attribute Cx : Real = -55.162169696635786;
                            attribute sigma_Cx : Real = 15.444932976042965;
                            attribute Cy : Real = 34.83957408109909;
                            attribute sigma_Cy : Real = 19.127947560232634;
                            attribute Cz : Real = -3.644436624940352;
                            attribute sigma_Cz : Real = 17.941688051373216;
                            attribute Ixx : Real = 12984.710267250231;
                            attribute sigma_Ixx : Real = 6649.945637902535;
                            attribute Iyy : Real = 8263.97484941645;
                            attribute sigma_Iyy : Real = 4839.658313267446;
                            attribute Izz : Real = 7975.165089887268;
                            attribute sigma_Izz : Real = 5360.734313331673;
                            attribute Ixy : Real = 2845.365073030884;
                            attribute sigma_Ixy : Real = 2302.775460373171;
                            attribute Ixz : Real = -1443.9353092258516;
                            attribute sigma_Ixz : Real = 2255.7563165378947;
                            attribute Iyz : Real = 1572.7125846709416;
                            attribute sigma_Iyz : Real = 2858.6225834404563;
                            part <'C.1.2.1.2.4.1.1'> 'Part 804' {
                                attribute POIconv : String = "-";
                                attribute Ipoint : Boolean = false;
                                attribute mass : Real = 0.8647730712809134;
                                attribute sigma_mass : Real = 0.28909372274994966;
                                attribute Cx : Real = -37.79769390821457;
                                attribute sigma_Cx : Real = 28.721044428837228;
                                attribute Cy : Real = 18.432783475145698;
                                attribute sigma_Cy : Real = 28.23690002309109;
                                attribute Cz : Real = 54.54795099794865;
                                attribute sigma_Cz : Real = 29.057750463592832;
                                attribute Ixx : Real = 1.0818066292808868;
                                attribute sigma_Ixx : Real = 0.37074144170588635;
                                attribute Iyy : Real = 1.2149066237522415;
                                attribute sigma_Iyy : Real = 0.3723953238821935;
                                attribute Izz : Real = 1.121349771579344;
                                attribute sigma_Izz : Real = 0.37017423652493897;
                                attribute Ixy : Real = -0.004667889009889363;
                                attribute sigma_Ixy : Real = 0.02351283871158888;
                                attribute Ixz : Real = 0.02446029180214645;
                                attribute sigma_Ixz : Real = 0.022566176940390956;
                                attribute Iyz : Real = -0.04858962275700097;
                                attribute sigma_Iyz : Real = 0.02209918015384651;
                            }
                            part <'C.1.2.1.2.4.1.2'> 'Part 805' {
                                attribute POIconv : String = "-";
                                attribute Ipoint : Boolean = false;
                                attribute mass : Real = 0.23963028427539393;
                                attribute sigma_mass : Real = 0.28909372274994966;
                                attribute Cx : Real = -75.16429228708148;
                                attribute sigma_Cx : Real = 28.721044428837228;
                                attribute Cy : Real = 16.32254645228386;
                                attribute sigma_Cy : Real = 28.23690002309109;
                                attribute Cz : Real = 20.508430479094386;
                                attribute sigma_Cz : Real = 29.057750463592832;
                                attribute Ixx : Real = 0.23867241040814213;
                                attribute sigma_Ixx : Real = 0.37074144170588635;
                                attribute Iyy : Real = 0.24458769615327913;
                                attribute sigma_Iyy : Real = 0.3723953238821935;
                                attribute Izz : Real = 0.256001055701629;
                                attribute sigma_Izz : Real = 0.37017423652493897;
                                attribute Ixy : Real = 0.006184236335142613;
                                attribute sigma_Ixy : Real = 0.02351283871158888;
                                attribute Ixz : Real = -0.0021676407206270626;
                                attribute sigma_Ixz : Real = 0.022566176940390956;
                                attribute Iyz : Real = 0.0012573111645372299;
                                attribute sigma_Iyz : Real = 0.02209918015384651;
                            }
                            part <'C.1.2.1.2.4.1.3'> 'Part 806' {
                                attribute POIconv : String = "+";
                                attribute Ipoint : Boolean = false;
                                attribute mass : Real = 0.3267420998723246;
                                attribute sigma_mass : Real = 0.28909372274994966;
                                attribute Cx : Real = -8.890654006972909;
                                attribute sigma_Cx : Real = 28.721044428837228;
                                attribute Cy : Real = -72.87516864016652;
                                attribute sigma_Cy : Real = 28.23690002309109;
                                attribute Cz : Real = -38.81826470606029;
                                attribute sigma_Cz : Real = 29.057750463592832;
                                attribute Ixx : Real = 0.49996237008511313;
                                attribute sigma_Ixx : Real = 0.37074144170588635;
                                attribute Iyy : Real = 0.5173728381077084;
                                attribute sigma_Iyy : Real = 0.3723953238821935;
                                attribute Izz : Real = 0.4843805826064876;
                                attribute sigma_Izz : Real = 0.37017423652493897;
                                attribute Ixy : Real = 0.012501945870505272;
                                attribute sigma_Ixy : Real = 0.02351283871158888;
                                attribute Ixz : Real = 0.0008661031078263801;
                                attribute sigma_Ixz : Real = 0.022566176940390956;
                                attribute Iyz : Real = -0.0019662385902962194;
                                attribute sigma_Iyz : Real = 0.02209918015384651;
                            }
                            part <'C.1.2.1.2.4.1.4'> 'Part 807' {
                                attribute POIconv : String = "+";
                                attribute Ipoint : Boolean = false;
                                attribute mass : Real = 0.7272897051302716;
                                attribute sigma_mass : Real = 0.28909372274994966;
                                attribute Cx : Real = -68.14796905964613;
                                attribute sigma_Cx : Real = 28.721044428837228;
                                attribute Cy : Real = 76.05666127055883;
                                attribute sigma_Cy : Real = 28.23690002309109;
                                attribute Cz : Real = -6.900419574230909;
                                attribute sigma_Cz : Real = 29.057750463592832;
                                attribute Ixx : Real = 0.9791768215990834;
                                attribute sigma_Ixx : Real = 0.37074144170588635;
                                attribute Iyy : Real = 0.8860704797712587;
                                attribute sigma_Iyy : Real = 0.3723953238821935;
                                attribute Izz : Real = 0.9374630954174443;
                                attribute sigma_Izz : Real = 0.37017423652493897;
                                attribute Ixy : Real = -0.0013869810325858574;
                                attribute sigma_Ixy : Real = 0.02351283871158888;
                                attribute Ixz : Real = -0.09247330388404815;
                                attribute sigma_Ixz : Real = 0.022566176940390956;
                                attribute Iyz : Real = 0.03117674101409234;
                                attribute sigma_Iyz : Real = 0.02209918015384651;
                            }
                            part <'C.1.2.1.2.4.1.5'> 'Part 808' {
                                attribute POIconv : String = "-";
                                attribute Ipoint : Boolean = false;
                                attribute mass : Real = 0.5658271773017477;
                                attribute sigma_mass : Real = 0.28909372274994966;
                                attribute Cx : Real = -83.25843545608222;
                                attribute sigma_Cx : Real = 28.721044428837228;
                                attribute Cy : Real = 76.97888850234449;
                                attribute sigma_Cy : Real = 28.23690002309109;
                                attribute Cz : Real = -78.31415301188827;
                                attribute sigma_Cz : Real = 29.057750463592832;
                                attribute Ixx : Real = 0.662750235422354;
                                attribute sigma_Ixx : Real = 0.37074144170588635;
                                attribute Iyy : Real = 0.6280813471229602;
                                attribute sigma_Iyy : Real = 0.3723953238821935;
                                attribute Izz : Real = 0.5957829620488266;
                                attribute sigma_Izz : Real = 0.37017423652493897;
                                attribute Ixy : Real = 0.048334660757939886;
                                attribute sigma_Ixy : Real = 0.02351283871158888;
                                attribute Ixz : Real = 0.05409607205209871;
                                attribute sigma_Ixz : Real = 0.022566176940390956;
                                attribute Iyz : Real = -0.08089780142635626;
                                attribute sigma_Iyz : Real = 0.02209918015384651;
                            }
                        }
                        part <'C.1.2.1.2.4.2'> 'Subassembly 229' {
                            attribute POIconv : String = "-";
                            attribute Ipoint : Boolean = false;
                            attribute mass : Real = 1.2322317018865143;
                            attribute sigma_mass : Real = 0.5781874454998993;
                            attribute Cx : Real = 12.452896513230334;
                            attribute sigma_Cx : Real = 28.66965888526476;
                            attribute Cy : Real = -8.63108678673314;
                            attribute sigma_Cy : Real = 19.14586739221737;
                            attribute Cz : Real = -43.498739596908194;
                            attribute sigma_Cz : Real = 21.039594441665557;
                            attribute Ixx : Real = 199.6917799452629;
                            attribute sigma_Ixx : Real = 615.3203817962707;
                            attribute Iyy : Real = 2203.566459219724;
                            attribute sigma_Iyy : Real = 2414.558563419733;
                            attribute Izz : Real = 2140.5981951782796;
                            attribute sigma_Izz : Real = 2307.184535675328;
                            attribute Ixy : Real = -140.93286978252996;
                            attribute sigma_Ixy : Real = 890.9107423811143;
                            attribute Ixz : Real = -441.6752879208724;
                            attribute sigma_Ixz : Real = 1001.461399312468;
                            attribute Iyz : Real = -26.59367293240262;
                            attribute sigma_Iyz : Real = 272.86506546057154;
                            part <'C.1.2.1.2.4.2.1'> 'Part 809' {
                                attribute POIconv : String = "+";
                                attribute Ipoint : Boolean = false;
                                attribute mass : Real = 0.7216553364193533;
                                attribute sigma_mass : Real = 0.28909372274994966;
                                attribute Cx : Real = 44.51233926229179;
                                attribute sigma_Cx : Real = 28.721044428837228;
                                attribute Cy : Real = -8.224520226940513;
                                attribute sigma_Cy : Real = 28.23690002309109;
                                attribute Cz : Real = -35.627303225919604;
                                attribute sigma_Cz : Real = 29.057750463592832;
                                attribute Ixx : Real = 0.666792743125651;
                                attribute sigma_Ixx : Real = 0.37074144170588635;
                                attribute Iyy : Real = 0.6557724275868243;
                                attribute sigma_Iyy : Real = 0.3723953238821935;
                                attribute Izz : Real = 0.6726569936945448;
                                attribute sigma_Izz : Real = 0.37017423652493897;
                                attribute Ixy : Real = -0.00043038234080768;
                                attribute sigma_Ixy : Real = 0.02351283871158888;
                                attribute Ixz : Real = 0.004284782359878392;
                                attribute sigma_Ixz : Real = 0.022566176940390956;
                                attribute Iyz : Real = 0.0020786959521412766;
                                attribute sigma_Iyz : Real = 0.02209918015384651;
                            }
                            part <'C.1.2.1.2.4.2.2'> 'Part 810' {
                                attribute POIconv : String = "+";
                                attribute Ipoint : Boolean = false;
                                attribute mass : Real = 0.01931958820275031;
                                attribute sigma_mass : Real = 0.28909372274994966;
                                attribute Cx : Real = 52.15042610652745;
                                attribute sigma_Cx : Real = 28.721044428837228;
                                attribute Cy : Real = 5.777149787172675;
                                attribute sigma_Cy : Real = 28.23690002309109;
                                attribute Cz : Real = -77.41399575024843;
                                attribute sigma_Cz : Real = 29.057750463592832;
                                attribute Ixx : Real = 0.017896556317728483;
                                attribute sigma_Ixx : Real = 0.37074144170588635;
                                attribute Iyy : Real = 0.01988321596731473;
                                attribute sigma_Iyy : Real = 0.3723953238821935;
                                attribute Izz : Real = 0.01947780938952731;
                                attribute sigma_Izz : Real = 0.37017423652493897;
                                attribute Ixy : Real = 0.000751949920685642;
                                attribute sigma_Ixy : Real = 0.02351283871158888;
                                attribute Ixz : Real = 0.0004743783020453926;
                                attribute sigma_Ixz : Real = 0.022566176940390956;
                                attribute Iyz : Real = -0.0002603821331912986;
                                attribute sigma_Iyz : Real = 0.02209918015384651;
                            }
                            part <'C.1.2.1.2.4.2.3'> 'Part 811' {
                                attribute POIconv : String = "-";
                                attribute Ipoint : Boolean = false;
                                attribute mass : Real = 0.2918663719270844;
                                attribute sigma_mass : Real = 0.28909372274994966;
                                attribute Cx : Real = -22.43285053409636;
                                attribute sigma_Cx : Real = 28.721044428837228;
                                attribute Cy : Real = -0.4365658853203058;
                                attribute sigma_Cy : Real = 28.23690002309109;
                                attribute Cz : Real = -49.58274313248694;
                                attribute sigma_Cz : Real = 29.057750463592832;
                                attribute Ixx : Real = 0.3453957261489187;
                                attribute sigma_Ixx : Real = 0.37074144170588635;
                                attribute Iyy : Real = 0.4168891183516289;
                                attribute sigma_Iyy : Real = 0.3723953238821935;
                                attribute Izz : Real = 0.35299767673283033;
                                attribute sigma_Izz : Real = 0.37017423652493897;
                                attribute Ixy : Real = 0.022476549351943383;
                                attribute sigma_Ixy : Real = 0.02351283871158888;
                                attribute Ixz : Real = 0.0017258267198888917;
                                attribute sigma_Ixz : Real = 0.022566176940390956;
                                attribute Iyz : Real = 0.02189942386670761;
                                attribute sigma_Iyz : Real = 0.02209918015384651;
                            }
                            part <'C.1.2.1.2.4.2.4'> 'Part 812' {
                                attribute POIconv : String = "-";
                                attribute Ipoint : Boolean = false;
                                attribute mass : Real = 0.19939040533732624;
                                attribute sigma_mass : Real = 0.28909372274994966;
                                attribute Cx : Real = -56.36100363917649;
                                attribute sigma_Cx : Real = 28.721044428837228;
                                attribute Cy : Real = -23.49372375756502;
                                attribute sigma_Cy : Real = 28.23690002309109;
                                attribute Cz : Real = -59.79600944556296;
                                attribute sigma_Cz : Real = 29.057750463592832;
                                attribute Ixx : Real = 0.19048126678535066;
                                attribute sigma_Ixx : Real = 0.37074144170588635;
                                attribute Iyy : Real = 0.21806339046888587;
                                attribute sigma_Iyy : Real = 0.3723953238821935;
                                attribute Izz : Real = 0.22083404888702535;
                                attribute sigma_Izz : Real = 0.37017423652493897;
                                attribute Ixy : Real = -0.007184577928820353;
                                attribute sigma_Ixy : Real = 0.02351283871158888;
                                attribute Ixz : Real = -0.011433031338499766;
                                attribute sigma_Ixz : Real = 0.022566176940390956;
                                attribute Iyz : Real = 0.00032399330677648796;
                                attribute sigma_Iyz : Real = 0.02209918015384651;
                            }
                        }
                        part <'C.1.2.1.2.4.3'> 'Subassembly 230' {
                            attribute POIconv : String = "-";
                            attribute Ipoint : Boolean = false;
                            attribute mass : Real = 3.10821857620473;
                            attribute sigma_mass : Real = 0.6464332159373649;
                            attribute Cx : Real = 7.345363849795261;
                            attribute sigma_Cx : Real = 15.378329300212021;
                            attribute Cy : Real = -58.7796518493155;
                            attribute sigma_Cy : Real = 14.008482104768685;
                            attribute Cz : Real = -3.900771004217439;
                            attribute sigma_Cz : Real = 18.191852090350523;
                            attribute Ixx : Real = 9559.295401086203;
                            attribute sigma_Ixx : Real = 5241.588832451838;
                            attribute Iyy : Real = 12357.71953167888;
                            attribute sigma_Iyy : Real = 6045.123552672272;
                            attribute Izz : Real = 5369.502800186948;
                            attribute sigma_Izz : Real = 3866.5362238433636;
                            attribute Ixy : Real = 2176.2386028840465;
                            attribute sigma_Ixy : Real = 1889.091068998655;
                            attribute Ixz : Real = 1385.9969950146606;
                            attribute sigma_Ixz : Real = 2737.7200179584256;
                            attribute Iyz : Real = -1362.7380450871492;
                            attribute sigma_Iyz : Real = 2245.194978552603;
                            part <'C.1.2.1.2.4.3.1'> 'Part 813' {
                                attribute POIconv : String = "+";
                                attribute Ipoint : Boolean = false;
                                attribute mass : Real = 0.8357904310591985;
                                attribute sigma_mass : Real = 0.28909372274994966;
                                attribute Cx : Real = 32.309469394385815;
                                attribute sigma_Cx : Real = 28.721044428837228;
                                attribute Cy : Real = -65.08840187452734;
                                attribute sigma_Cy : Real = 28.23690002309109;
                                attribute Cz : Real = 37.25717789493501;
                                attribute sigma_Cz : Real = 29.057750463592832;
                                attribute Ixx : Real = 0.9874327269102298;
                                attribute sigma_Ixx : Real = 0.37074144170588635;
                                attribute Iyy : Real = 1.0731532789619918;
                                attribute sigma_Iyy : Real = 0.3723953238821935;
                                attribute Izz : Real = 1.1380284466214423;
                                attribute sigma_Izz : Real = 0.37017423652493897;
                                attribute Ixy : Real = -0.046133088263470054;
                                attribute sigma_Ixy : Real = 0.02351283871158888;
                                attribute Ixz : Real = 0.07240316233168473;
                                attribute sigma_Ixz : Real = 0.022566176940390956;
                                attribute Iyz : Real = 0.09490695105118563;
                                attribute sigma_Iyz : Real = 0.02209918015384651;
                            }
                            part <'C.1.2.1.2.4.3.2'> 'Part 814' {
                                attribute POIconv : String = "+";
                                attribute Ipoint : Boolean = false;
                                attribute mass : Real = 0.5276788520901464;
                                attribute sigma_mass : Real = 0.28909372274994966;
                                attribute Cx : Real = 60.75677811168134;
                                attribute sigma_Cx : Real = 28.721044428837228;
                                attribute Cy : Real = -93.28174190595746;
                                attribute sigma_Cy : Real = 28.23690002309109;
                                attribute Cz : Real = -31.71930005773902;
                                attribute sigma_Cz : Real = 29.057750463592832;
                                attribute Ixx : Real = 0.6752545313641664;
                                attribute sigma_Ixx : Real = 0.37074144170588635;
                                attribute Iyy : Real = 0.6110967434861267;
                                attribute sigma_Iyy : Real = 0.3723953238821935;
                                attribute Izz : Real = 0.6282835263497757;
                                attribute sigma_Izz : Real = 0.37017423652493897;
                                attribute Ixy : Real = -0.06003160079778154;
                                attribute sigma_Ixy : Real = 0.02351283871158888;
                                attribute Ixz : Real = -0.005637790823054593;
                                attribute sigma_Ixz : Real = 0.022566176940390956;
                                attribute Iyz : Real = 0.05150892182210934;
                                attribute sigma_Iyz : Real = 0.02209918015384651;
                            }
                            part <'C.1.2.1.2.4.3.3'> 'Part 815' {
                                attribute POIconv : String = "-";
                                attribute Ipoint : Boolean = false;
                                attribute mass : Real = 0.2866579179561231;
                                attribute sigma_mass : Real = 0.28909372274994966;
                                attribute Cx : Real = 10.567488567903638;
                                attribute sigma_Cx : Real = 28.721044428837228;
                                attribute Cy : Real = -55.383821576833725;
                                attribute sigma_Cy : Real = 28.23690002309109;
                                attribute Cz : Real = -90.33429166302085;
                                attribute sigma_Cz : Real = 29.057750463592832;
                                attribute Ixx : Real = 0.2828717220816637;
                                attribute sigma_Ixx : Real = 0.37074144170588635;
                                attribute Iyy : Real = 0.2635401302214018;
                                attribute sigma_Iyy : Real = 0.3723953238821935;
                                attribute Izz : Real = 0.29447554542632004;
                                attribute sigma_Izz : Real = 0.37017423652493897;
                                attribute Ixy : Real = -0.005990270880614783;
                                attribute sigma_Ixy : Real = 0.02351283871158888;
                                attribute Ixz : Real = -0.007200619651265321;
                                attribute sigma_Ixz : Real = 0.022566176940390956;
                                attribute Iyz : Real = -0.006458395974597997;
                                attribute sigma_Iyz : Real = 0.02209918015384651;
                            }
                            part <'C.1.2.1.2.4.3.4'> 'Part 816' {
                                attribute POIconv : String = "+";
                                attribute Ipoint : Boolean = false;
                                attribute mass : Real = 0.8911068134093657;
                                attribute sigma_mass : Real = 0.28909372274994966;
                                attribute Cx : Real = -39.10878994502127;
                                attribute sigma_Cx : Real = 28.721044428837228;
                                attribute Cy : Real = -32.458433182910085;
                                attribute sigma_Cy : Real = 28.23690002309109;
                                attribute Cz : Real = 42.827041214331985;
                                attribute sigma_Cz : Real = 29.057750463592832;
                                attribute Ixx : Real = 1.100414917126418;
                                attribute sigma_Ixx : Real = 0.37074144170588635;
                                attribute Iyy : Real = 1.2747139134981942;
                                attribute sigma_Iyy : Real = 0.3723953238821935;
                                attribute Izz : Real = 1.0349239848879837;
                                attribute sigma_Izz : Real = 0.37017423652493897;
                                attribute Ixy : Real = -0.03431938115177424;
                                attribute sigma_Ixy : Real = 0.02351283871158888;
                                attribute Ixz : Real = -0.0012769543540904595;
                                attribute sigma_Ixz : Real = 0.022566176940390956;
                                attribute Iyz : Real = -0.03302775050662109;
                                attribute sigma_Iyz : Real = 0.02209918015384651;
                            }
                            part <'C.1.2.1.2.4.3.5'> 'Part 817' {
                                attribute POIconv : String = "-";
                                attribute Ipoint : Boolean = false;
                                attribute mass : Real = 0.5669845616898965;
                                attribute sigma_mass : Real = 0.28909372274994966;
                                attribute Cx : Real = -7.781800953671336;
                                attribute sigma_Cx : Real = 28.721044428837228;
                                attribute Cy : Real = -60.454552387818694;
                                attribute sigma_Cy : Real = 28.23690002309109;
                                attribute Cz : Real = -68.42243811115623;
                                attribute sigma_Cz : Real = 29.057750463592832;
                                attribute Ixx : Real = 0.7587028294971988;
                                attribute sigma_Ixx : Real = 0.37074144170588635;
                                attribute Iyy : Real = 0.7384174111092835;
                                attribute sigma_Iyy : Real = 0.3723953238821935;
                                attribute Izz : Real = 0.7963515283495621;
                                attribute sigma_Izz : Real = 0.37017423652493897;
                                attribute Ixy : Real = -0.016928491794814732;
                                attribute sigma_Ixy : Real = 0.02351283871158888;
                                attribute Ixz : Real = 0.014297663231862084;
                                attribute sigma_Ixz : Real = 0.022566176940390956;
                                attribute Iyz : Real = -0.03456291632365647;
                                attribute sigma_Iyz : Real = 0.02209918015384651;
                            }
                        }
                        part <'C.1.2.1.2.4.4'> 'Subassembly 231' {
                            attribute POIconv : String = "-";
                            attribute Ipoint : Boolean = false;
                            attribute mass : Real = 1.88018814456393;
                            attribute sigma_mass : Real = 0.5781874454998993;
                            attribute Cx : Real = -54.72220104146701;
                            attribute sigma_Cx : Real = 25.66777043954656;
                            attribute Cy : Real = 3.5194763987901583;
                            attribute sigma_Cy : Real = 24.668104683418232;
                            attribute Cz : Real = -28.588845616998366;
                            attribute sigma_Cz : Real = 29.34362261548106;
                            attribute Ixx : Real = 12264.621873871138;
                            attribute sigma_Ixx : Real = 7693.018570364764;
                            attribute Iyy : Real = 10714.295442715716;
                            attribute sigma_Iyy : Real = 7278.907694510936;
                            attribute Izz : Real = 3203.705987034672;
                            attribute sigma_Izz : Real = 4885.426646657656;
                            attribute Ixy : Real = 299.0759317071378;
                            attribute sigma_Ixy : Real = 1967.8371361689985;
                            attribute Ixz : Real = -251.8070289788851;
                            attribute sigma_Ixz : Real = 3018.9460196083114;
                            attribute Iyz : Real = -4532.732497876721;
                            attribute sigma_Iyz : Real = 3692.5011520203116;
                            part <'C.1.2.1.2.4.4.1'> 'Part 818' {
                                attribute POIconv : String = "-";
                                attribute Ipoint : Boolean = false;
                                attribute mass : Real = 0.02775987434736453;
                                attribute sigma_mass : Real = 0.28909372274994966;
                                attribute Cx : Real = -19.107882492244244;
                                attribute sigma_Cx : Real = 28.721044428837228;
                                attribute Cy : Real = 81.39040870591998;
                                attribute sigma_Cy : Real = 28.23690002309109;
                                attribute Cz : Real = 59.768469678238034;
                                attribute sigma_Cz : Real = 29.057750463592832;
                                attribute Ixx : Real = 0.03352117541400993;
                                attribute sigma_Ixx : Real = 0.37074144170588635;
                                attribute Iyy : Real = 0.0300113556906247;
                                attribute sigma_Iyy : Real = 0.3723953238821935;
                                attribute Izz : Real = 0.03371325362756814;
                                attribute sigma_Izz : Real = 0.37017423652493897;
                                attribute Ixy : Real = 0.000584289461273048;
                                attribute sigma_Ixy : Real = 0.02351283871158888;
                                attribute Ixz : Real = 1.557363225420622e-05;
                                attribute sigma_Ixz : Real = 0.022566176940390956;
                                attribute Iyz : Real = 0.00013984997185589767;
                                attribute sigma_Iyz : Real = 0.02209918015384651;
                            }
                            part <'C.1.2.1.2.4.4.2'> 'Part 819' {
                                attribute POIconv : String = "-";
                                attribute Ipoint : Boolean = false;
                                attribute mass : Real = 0.9975247924628202;
                                attribute sigma_mass : Real = 0.28909372274994966;
                                attribute Cx : Real = -58.52100886404514;
                                attribute sigma_Cx : Real = 28.721044428837228;
                                attribute Cy : Real = -26.248004660010338;
                                attribute sigma_Cy : Real = 28.23690002309109;
                                attribute Cz : Real = -96.36492184363306;
                                attribute sigma_Cz : Real = 29.057750463592832;
                                attribute Ixx : Real = 1.050472921541383;
                                attribute sigma_Ixx : Real = 0.37074144170588635;
                                attribute Iyy : Real = 1.050829997993463;
                                attribute sigma_Iyy : Real = 0.3723953238821935;
                                attribute Izz : Real = 1.1079224008382247;
                                attribute sigma_Izz : Real = 0.37017423652493897;
                                attribute Ixy : Real = 0.08026193042551114;
                                attribute sigma_Ixy : Real = 0.02351283871158888;
                                attribute Ixz : Real = -0.006639878179441545;
                                attribute sigma_Ixz : Real = 0.022566176940390956;
                                attribute Iyz : Real = 0.009955918427628926;
                                attribute sigma_Iyz : Real = 0.02209918015384651;
                            }
                            part <'C.1.2.1.2.4.4.3'> 'Part 820' {
                                attribute POIconv : String = "-";
                                attribute Ipoint : Boolean = false;
                                attribute mass : Real = 0.7841411937372759;
                                attribute sigma_mass : Real = 0.28909372274994966;
                                attribute Cx : Real = -60.44355579651892;
                                attribute sigma_Cx : Real = 28.721044428837228;
                                attribute Cy : Real = 42.51666353084147;
                                attribute sigma_Cy : Real = 28.23690002309109;
                                attribute Cz : Real = 51.213312428444624;
                                attribute sigma_Cz : Real = 29.057750463592832;
                                attribute Ixx : Real = 0.8011600518152019;
                                attribute sigma_Ixx : Real = 0.37074144170588635;
                                attribute Iyy : Real = 0.7446147060284282;
                                attribute sigma_Iyy : Real = 0.3723953238821935;
                                attribute Izz : Real = 0.8025036987373738;
                                attribute sigma_Izz : Real = 0.37017423652493897;
                                attribute Ixy : Real = 0.024794181776634387;
                                attribute sigma_Ixy : Real = 0.02351283871158888;
                                attribute Ixz : Real = -0.007208786809275782;
                                attribute sigma_Ixz : Real = 0.022566176940390956;
                                attribute Iyz : Real = 0.01855066335371411;
                                attribute sigma_Iyz : Real = 0.02209918015384651;
                            }
                            part <'C.1.2.1.2.4.4.4'> 'Part 821' {
                                attribute POIconv : String = "+";
                                attribute Ipoint : Boolean = false;
                                attribute mass : Real = 0.0707622840164695;
                                attribute sigma_mass : Real = 0.28909372274994966;
                                attribute Cx : Real = 48.25788256712258;
                                attribute sigma_Cx : Real = 28.721044428837228;
                                attribute Cy : Real = -39.542839117348194;
                                attribute sigma_Cy : Real = 28.23690002309109;
                                attribute Cz : Real = 7.862336887046695;
                                attribute sigma_Cz : Real = 29.057750463592832;
                                attribute Ixx : Real = 0.08701404964993782;
                                attribute sigma_Ixx : Real = 0.37074144170588635;
                                attribute Iyy : Real = 0.0881479928677735;
                                attribute sigma_Iyy : Real = 0.3723953238821935;
                                attribute Izz : Real = 0.0938627547885274;
                                attribute sigma_Izz : Real = 0.37017423652493897;
                                attribute Ixy : Real = -0.00366943115564693;
                                attribute sigma_Ixy : Real = 0.02351283871158888;
                                attribute Ixz : Real = 0.004602252210396301;
                                attribute sigma_Ixz : Real = 0.022566176940390956;
                                attribute Iyz : Real = 0.010378993873078925;
                                attribute sigma_Iyz : Real = 0.02209918015384651;
                            }
                        }
                        part <'C.1.2.1.2.4.5'> 'Subassembly 232' {
                            attribute POIconv : String = "-";
                            attribute Ipoint : Boolean = false;
                            attribute mass : Real = 2.433307824954856;
                            attribute sigma_mass : Real = 0.5781874454998993;
                            attribute Cx : Real = 11.846100863451245;
                            attribute sigma_Cx : Real = 22.186861923264686;
                            attribute Cy : Real = -4.673090231575793;
                            attribute sigma_Cy : Real = 22.684932950510095;
                            attribute Cz : Real = -33.92612501466142;
                            attribute sigma_Cz : Real = 19.228082154299834;
                            attribute Ixx : Real = 17677.733039925388;
                            attribute sigma_Ixx : Real = 8076.014074553498;
                            attribute Iyy : Real = 13504.930444508027;
                            attribute sigma_Iyy : Real = 6868.995028633386;
                            attribute Izz : Real = 20438.922015375847;
                            attribute sigma_Izz : Real = 8763.953023276876;
                            attribute Ixy : Real = -4866.3454860343;
                            attribute sigma_Ixy : Real = 4285.958902895114;
                            attribute Ixz : Real = -5570.535628690888;
                            attribute sigma_Ixz : Real = 3281.7797864023037;
                            attribute Iyz : Real = -6803.868044235048;
                            attribute sigma_Iyz : Real = 3955.836497410352;
                            part <'C.1.2.1.2.4.5.1'> 'Part 822' {
                                attribute POIconv : String = "+";
                                attribute Ipoint : Boolean = false;
                                attribute mass : Real = 0.4072078144229017;
                                attribute sigma_mass : Real = 0.28909372274994966;
                                attribute Cx : Real = 92.35317665152252;
                                attribute sigma_Cx : Real = 28.721044428837228;
                                attribute Cy : Real = -64.68316460959613;
                                attribute sigma_Cy : Real = 28.23690002309109;
                                attribute Cz : Real = -19.350315490737557;
                                attribute sigma_Cz : Real = 29.057750463592832;
                                attribute Ixx : Real = 0.5885837720038378;
                                attribute sigma_Ixx : Real = 0.37074144170588635;
                                attribute Iyy : Real = 0.5697786219384158;
                                attribute sigma_Iyy : Real = 0.3723953238821935;
                                attribute Izz : Real = 0.5984418258242137;
                                attribute sigma_Izz : Real = 0.37017423652493897;
                                attribute Ixy : Real = -0.017945362807275135;
                                attribute sigma_Ixy : Real = 0.02351283871158888;
                                attribute Ixz : Real = -0.0010926556153732828;
                                attribute sigma_Ixz : Real = 0.022566176940390956;
                                attribute Iyz : Real = 0.0026388096326256747;
                                attribute sigma_Iyz : Real = 0.02209918015384651;
                            }
                            part <'C.1.2.1.2.4.5.2'> 'Part 823' {
                                attribute POIconv : String = "+";
                                attribute Ipoint : Boolean = false;
                                attribute mass : Real = 0.9981345199504867;
                                attribute sigma_mass : Real = 0.28909372274994966;
                                attribute Cx : Real = 45.81385510973632;
                                attribute sigma_Cx : Real = 28.721044428837228;
                                attribute Cy : Real = 80.57540208101273;
                                attribute sigma_Cy : Real = 28.23690002309109;
                                attribute Cz : Real = 13.06322286836803;
                                attribute sigma_Cz : Real = 29.057750463592832;
                                attribute Ixx : Real = 1.192093828866941;
                                attribute sigma_Ixx : Real = 0.37074144170588635;
                                attribute Iyy : Real = 1.3392310748014664;
                                attribute sigma_Iyy : Real = 0.3723953238821935;
                                attribute Izz : Real = 1.2369976623306118;
                                attribute sigma_Izz : Real = 0.37017423652493897;
                                attribute Ixy : Real = -0.07465667576540179;
                                attribute sigma_Ixy : Real = 0.02351283871158888;
                                attribute Ixz : Real = 0.10022896612910404;
                                attribute sigma_Ixz : Real = 0.022566176940390956;
                                attribute Iyz : Real = 0.08967724443355796;
                                attribute sigma_Iyz : Real = 0.02209918015384651;
                            }
                            part <'C.1.2.1.2.4.5.3'> 'Part 824' {
                                attribute POIconv : String = "-";
                                attribute Ipoint : Boolean = false;
                                attribute mass : Real = 0.10764958786056376;
                                attribute sigma_mass : Real = 0.28909372274994966;
                                attribute Cx : Real = -42.19682705588639;
                                attribute sigma_Cx : Real = 28.721044428837228;
                                attribute Cy : Real = -56.996966851875186;
                                attribute sigma_Cy : Real = 28.23690002309109;
                                attribute Cz : Real = -30.298014730215073;
                                attribute sigma_Cz : Real = 29.057750463592832;
                                attribute Ixx : Real = 0.1513570280368388;
                                attribute sigma_Ixx : Real = 0.37074144170588635;
                                attribute Iyy : Real = 0.15423437224017236;
                                attribute sigma_Iyy : Real = 0.3723953238821935;
                                attribute Izz : Real = 0.148468888734851;
                                attribute sigma_Izz : Real = 0.37017423652493897;
                                attribute Ixy : Real = 0.010718228458854992;
                                attribute sigma_Ixy : Real = 0.02351283871158888;
                                attribute Ixz : Real = -0.007946938892291297;
                                attribute sigma_Ixz : Real = 0.022566176940390956;
                                attribute Iyz : Real = -0.009001581295385176;
                                attribute sigma_Iyz : Real = 0.02209918015384651;
                            }
                            part <'C.1.2.1.2.4.5.4'> 'Part 825' {
                                attribute POIconv : String = "-";
                                attribute Ipoint : Boolean = false;
                                attribute mass : Real = 0.920315902720904;
                                attribute sigma_mass : Real = 0.28909372274994966;
                                attribute Cx : Real = -54.29401402361691;
                                attribute sigma_Cx : Real = 28.721044428837228;
                                attribute Cy : Real = -64.4571793731302;
                                attribute sigma_Cy : Real = 28.23690002309109;
                                attribute Cz : Real = -91.76239422522485;
                                attribute sigma_Cz : Real = 29.057750463592832;
                                attribute Ixx : Real = 1.2570674329021974;
                                attribute sigma_Ixx : Real = 0.37074144170588635;
                                attribute Iyy : Real = 1.3000220753039593;
                                attribute sigma_Iyy : Real = 0.3723953238821935;
                                attribute Izz : Real = 1.4227641175875914;
                                attribute sigma_Izz : Real = 0.37017423652493897;
                                attribute Ixy : Real = -0.01764992457399503;
                                attribute sigma_Ixy : Real = 0.02351283871158888;
                                attribute Ixz : Real = -0.06822718357408744;
                                attribute sigma_Ixz : Real = 0.022566176940390956;
                                attribute Iyz : Real = 0.0788622042842433;
                                attribute sigma_Iyz : Real = 0.02209918015384651;
                            }
                        }
                    }
                    part <'C.1.2.1.2.5'> 'Assembly 67' {
                        attribute POIconv : String = "-";
                        attribute Ipoint : Boolean = false;
                        attribute mass : Real = 3.706382654022425;
                        attribute sigma_mass : Real = 0.8176805270198123;
                        attribute Cx : Real = -29.406529878165376;
                        attribute sigma_Cx : Real = 16.763325888546333;
                        attribute Cy : Real = -31.155402175000408;
                        attribute sigma_Cy : Real = 16.04661909553627;
                        attribute Cz : Real = -11.639893123997918;
                        attribute sigma_Cz : Real = 16.867761235704247;
                        attribute Ixx : Real = 24696.28622315402;
                        attribute sigma_Ixx : Real = 8972.868003213296;
                        attribute Iyy : Real = 23508.775361038024;
                        attribute sigma_Iyy : Real = 9044.953477729627;
                        attribute Izz : Real = 20147.333825740643;
                        attribute sigma_Izz : Real = 8655.031562687716;
                        attribute Ixy : Real = -2228.4134188011985;
                        attribute sigma_Ixy : Real = 3845.1150172403377;
                        attribute Ixz : Real = 2549.313390405372;
                        attribute sigma_Ixz : Real = 3798.177055752672;
                        attribute Iyz : Real = -7440.039925571411;
                        attribute sigma_Iyz : Real = 4301.340628520753;
                        part <'C.1.2.1.2.5.1'> 'Subassembly 233' {
                            attribute POIconv : String = "-";
                            attribute Ipoint : Boolean = false;
                            attribute mass : Real = 2.3394936493115965;
                            attribute sigma_mass : Real = 0.6464332159373649;
                            attribute Cx : Real = -45.428475970020386;
                            attribute sigma_Cx : Real = 21.39988523000233;
                            attribute Cy : Real = -51.09662637938301;
                            attribute sigma_Cy : Real = 16.734151400925988;
                            attribute Cz : Real = -13.358171808454925;
                            attribute sigma_Cz : Real = 19.162585364533747;
                            attribute Ixx : Real = 8539.813907887727;
                            attribute sigma_Ixx : Real = 4808.512465827036;
                            attribute Iyy : Real = 11375.890713608609;
                            attribute sigma_Iyy : Real = 6615.344264916563;
                            attribute Izz : Real = 9291.551077681972;
                            attribute sigma_Izz : Real = 6076.169342427909;
                            attribute Ixy : Real = -2785.2994062064968;
                            attribute sigma_Ixy : Real = 2393.4785686244654;
                            attribute Ixz : Real = 1408.6370174882416;
                            attribute sigma_Ixz : Real = 2668.822786394457;
                            attribute Iyz : Real = -2300.1579344129295;
                            attribute sigma_Iyz : Real = 2307.3463925932033;
                            part <'C.1.2.1.2.5.1.1'> 'Part 826' {
                                attribute POIconv : String = "-";
                                attribute Ipoint : Boolean = false;
                                attribute mass : Real = 0.35472945754113605;
                                attribute sigma_mass : Real = 0.28909372274994966;
                                attribute Cx : Real = -32.57354265078902;
                                attribute sigma_Cx : Real = 28.721044428837228;
                                attribute Cy : Real = -54.359632916748524;
                                attribute sigma_Cy : Real = 28.23690002309109;
                                attribute Cz : Real = -60.033038118854165;
                                attribute sigma_Cz : Real = 29.057750463592832;
                                attribute Ixx : Real = 0.39465533938161407;
                                attribute sigma_Ixx : Real = 0.37074144170588635;
                                attribute Iyy : Real = 0.3708428361104746;
                                attribute sigma_Iyy : Real = 0.3723953238821935;
                                attribute Izz : Real = 0.4016438495341792;
                                attribute sigma_Izz : Real = 0.37017423652493897;
                                attribute Ixy : Real = -0.00901885303641029;
                                attribute sigma_Ixy : Real = 0.02351283871158888;
                                attribute Ixz : Real = -0.008405056752999634;
                                attribute sigma_Ixz : Real = 0.022566176940390956;
                                attribute Iyz : Real = -0.039442214739952464;
                                attribute sigma_Iyz : Real = 0.02209918015384651;
                            }
                            part <'C.1.2.1.2.5.1.2'> 'Part 827' {
                                attribute POIconv : String = "+";
                                attribute Ipoint : Boolean = false;
                                attribute mass : Real = 0.31314228507853115;
                                attribute sigma_mass : Real = 0.28909372274994966;
                                attribute Cx : Real = 73.49771121516824;
                                attribute sigma_Cx : Real = 28.721044428837228;
                                attribute Cy : Real = -14.560205908492208;
                                attribute sigma_Cy : Real = 28.23690002309109;
                                attribute Cz : Real = -57.27238794788718;
                                attribute sigma_Cz : Real = 29.057750463592832;
                                attribute Ixx : Real = 0.3536357841739443;
                                attribute sigma_Ixx : Real = 0.37074144170588635;
                                attribute Iyy : Real = 0.38870651252086724;
                                attribute sigma_Iyy : Real = 0.3723953238821935;
                                attribute Izz : Real = 0.3836471681829062;
                                attribute sigma_Izz : Real = 0.37017423652493897;
                                attribute Ixy : Real = -0.003130433380554972;
                                attribute sigma_Ixy : Real = 0.02351283871158888;
                                attribute Ixz : Real = 0.001020412698138922;
                                attribute sigma_Ixz : Real = 0.022566176940390956;
                                attribute Iyz : Real = 0.029871025344772557;
                                attribute sigma_Iyz : Real = 0.02209918015384651;
                            }
                            part <'C.1.2.1.2.5.1.3'> 'Part 828' {
                                attribute POIconv : String = "+";
                                attribute Ipoint : Boolean = false;
                                attribute mass : Real = 0.7795113956751302;
                                attribute sigma_mass : Real = 0.28909372274994966;
                                attribute Cx : Real = -88.55164228007197;
                                attribute sigma_Cx : Real = 28.721044428837228;
                                attribute Cy : Real = -95.1529074460268;
                                attribute sigma_Cy : Real = 28.23690002309109;
                                attribute Cz : Real = -29.581688018515706;
                                attribute sigma_Cz : Real = 29.057750463592832;
                                attribute Ixx : Real = 1.1342216883989427;
                                attribute sigma_Ixx : Real = 0.37074144170588635;
                                attribute Iyy : Real = 1.0789138109344536;
                                attribute sigma_Iyy : Real = 0.3723953238821935;
                                attribute Izz : Real = 1.1353333188813315;
                                attribute sigma_Izz : Real = 0.37017423652493897;
                                attribute Ixy : Real = -0.02123559450439876;
                                attribute sigma_Ixy : Real = 0.02351283871158888;
                                attribute Ixz : Real = -0.003284069208180234;
                                attribute sigma_Ixz : Real = 0.022566176940390956;
                                attribute Iyz : Real = -0.02408775241072387;
                                attribute sigma_Iyz : Real = 0.02209918015384651;
                            }
                            part <'C.1.2.1.2.5.1.4'> 'Part 829' {
                                attribute POIconv : String = "+";
                                attribute Ipoint : Boolean = false;
                                attribute mass : Real = 0.20580471056792884;
                                attribute sigma_mass : Real = 0.28909372274994966;
                                attribute Cx : Real = -68.28695512376726;
                                attribute sigma_Cx : Real = 28.721044428837228;
                                attribute Cy : Real = -73.13819658011198;
                                attribute sigma_Cy : Real = 28.23690002309109;
                                attribute Cz : Real = -43.99308650754392;
                                attribute sigma_Cz : Real = 29.057750463592832;
                                attribute Ixx : Real = 0.27761592021355075;
                                attribute sigma_Ixx : Real = 0.37074144170588635;
                                attribute Iyy : Real = 0.29510629942027644;
                                attribute sigma_Iyy : Real = 0.3723953238821935;
                                attribute Izz : Real = 0.24858597897777807;
                                attribute sigma_Izz : Real = 0.37017423652493897;
                                attribute Ixy : Real = -0.013734226100615247;
                                attribute sigma_Ixy : Real = 0.02351283871158888;
                                attribute Ixz : Real = -0.0029774467758205787;
                                attribute sigma_Ixz : Real = 0.022566176940390956;
                                attribute Iyz : Real = -0.004131084819970121;
                                attribute sigma_Iyz : Real = 0.02209918015384651;
                            }
                            part <'C.1.2.1.2.5.1.5'> 'Part 830' {
                                attribute POIconv : String = "-";
                                attribute Ipoint : Boolean = false;
                                attribute mass : Real = 0.6863058004488702;
                                attribute sigma_mass : Real = 0.28909372274994966;
                                attribute Cx : Real = -50.50122821703553;
                                attribute sigma_Cx : Real = 28.721044428837228;
                                attribute Cy : Real = -9.431499196216464;
                                attribute sigma_Cy : Real = 28.23690002309109;
                                attribute Cz : Real = 58.41679130680859;
                                attribute sigma_Cz : Real = 29.057750463592832;
                                attribute Ixx : Real = 0.8655261883665156;
                                attribute sigma_Ixx : Real = 0.37074144170588635;
                                attribute Iyy : Real = 0.8530180555528631;
                                attribute sigma_Iyy : Real = 0.3723953238821935;
                                attribute Izz : Real = 0.8814957000538955;
                                attribute sigma_Izz : Real = 0.37017423652493897;
                                attribute Ixy : Real = 0.026716929532031388;
                                attribute sigma_Ixy : Real = 0.02351283871158888;
                                attribute Ixz : Real = -0.009397924121129757;
                                attribute sigma_Ixz : Real = 0.022566176940390956;
                                attribute Iyz : Real = 0.010086649848528272;
                                attribute sigma_Iyz : Real = 0.02209918015384651;
                            }
                        }
                        part <'C.1.2.1.2.5.2'> 'Subassembly 234' {
                            attribute POIconv : String = "-";
                            attribute Ipoint : Boolean = false;
                            attribute mass : Real = 1.3668890047108289;
                            attribute sigma_mass : Real = 0.5007250159521434;
                            attribute Cx : Real = -1.9842293092634524;
                            attribute sigma_Cx : Real = 23.79623585320264;
                            attribute Cy : Real = 2.9749238608881576;
                            attribute sigma_Cy : Real = 28.7687454409615;
                            attribute Cz : Real = -8.698979811958305;
                            attribute sigma_Cz : Real = 31.850143329585975;
                            attribute Ixx : Real = 13615.17699279403;
                            attribute sigma_Ixx : Real = 6873.555208647181;
                            attribute Iyy : Real = 10485.723978516166;
                            attribute sigma_Iyy : Real = 5659.487353249311;
                            attribute Izz : Real = 6704.785747775966;
                            attribute sigma_Izz : Real = 4635.767774976662;
                            attribute Ixy : Real = 2583.6629434158076;
                            attribute sigma_Ixy : Real = 2237.960097932383;
                            attribute Ixz : Real = 1315.3179899998033;
                            attribute sigma_Ixz : Real = 2311.675950980837;
                            attribute Iyz : Real = -4922.519654417632;
                            attribute sigma_Iyz : Real = 3185.861640886127;
                            part <'C.1.2.1.2.5.2.1'> 'Part 831' {
                                attribute POIconv : String = "-";
                                attribute Ipoint : Boolean = false;
                                attribute mass : Real = 0.5344961925768293;
                                attribute sigma_mass : Real = 0.28909372274994966;
                                attribute Cx : Real = 31.313461251556873;
                                attribute sigma_Cx : Real = 28.721044428837228;
                                attribute Cy : Real = -69.91904112510383;
                                attribute sigma_Cy : Real = 28.23690002309109;
                                attribute Cz : Real = -96.5362448245287;
                                attribute sigma_Cz : Real = 29.057750463592832;
                                attribute Ixx : Real = 0.5897612726838234;
                                attribute sigma_Ixx : Real = 0.37074144170588635;
                                attribute Iyy : Real = 0.5753336902253086;
                                attribute sigma_Iyy : Real = 0.3723953238821935;
                                attribute Izz : Real = 0.5716296806534101;
                                attribute sigma_Izz : Real = 0.37017423652493897;
                                attribute Ixy : Real = -0.03224629452045791;
                                attribute sigma_Ixy : Real = 0.02351283871158888;
                                attribute Ixz : Real = -0.01831237160975026;
                                attribute sigma_Ixz : Real = 0.022566176940390956;
                                attribute Iyz : Real = -0.01580900411041409;
                                attribute sigma_Iyz : Real = 0.02209918015384651;
                            }
                            part <'C.1.2.1.2.5.2.2'> 'Part 832' {
                                attribute POIconv : String = "+";
                                attribute Ipoint : Boolean = false;
                                attribute mass : Real = 0.5820001744835172;
                                attribute sigma_mass : Real = 0.28909372274994966;
                                attribute Cx : Real = -2.857040846720338;
                                attribute sigma_Cx : Real = 28.721044428837228;
                                attribute Cy : Real = 38.35672647692263;
                                attribute sigma_Cy : Real = 28.23690002309109;
                                attribute Cz : Real = 79.24908045679331;
                                attribute sigma_Cz : Real = 29.057750463592832;
                                attribute Ixx : Real = 0.7097826186053038;
                                attribute sigma_Ixx : Real = 0.37074144170588635;
                                attribute Iyy : Real = 0.7219674236698198;
                                attribute sigma_Iyy : Real = 0.3723953238821935;
                                attribute Izz : Real = 0.7318502106340017;
                                attribute sigma_Izz : Real = 0.37017423652493897;
                                attribute Ixy : Real = 0.005117095709049087;
                                attribute sigma_Ixy : Real = 0.02351283871158888;
                                attribute Ixz : Real = 0.029877279594565147;
                                attribute sigma_Ixz : Real = 0.022566176940390956;
                                attribute Iyz : Real = 0.020985204599652585;
                                attribute sigma_Iyz : Real = 0.02209918015384651;
                            }
                            part <'C.1.2.1.2.5.2.3'> 'Part 833' {
                                attribute POIconv : String = "+";
                                attribute Ipoint : Boolean = false;
                                attribute mass : Real = 0.25039263765048236;
                                attribute sigma_mass : Real = 0.28909372274994966;
                                attribute Cx : Real = -71.0338328499347;
                                attribute sigma_Cx : Real = 28.721044428837228;
                                attribute Cy : Real = 76.33703076280653;
                                attribute sigma_Cy : Real = 28.23690002309109;
                                attribute Cz : Real = -25.62081404030323;
                                attribute sigma_Cz : Real = 29.057750463592832;
                                attribute Ixx : Real = 0.3791176394540979;
                                attribute sigma_Ixx : Real = 0.37074144170588635;
                                attribute Iyy : Real = 0.29990790383627103;
                                attribute sigma_Iyy : Real = 0.3723953238821935;
                                attribute Izz : Real = 0.3254716396937155;
                                attribute sigma_Izz : Real = 0.37017423652493897;
                                attribute Ixy : Real = -0.002602383852669089;
                                attribute sigma_Ixy : Real = 0.02351283871158888;
                                attribute Ixz : Real = 0.021845858598623;
                                attribute sigma_Ixz : Real = 0.022566176940390956;
                                attribute Iyz : Real = 0.0045430762067803394;
                                attribute sigma_Iyz : Real = 0.02209918015384651;
                            }
                        }
                    }
                }
                part <'C.1.2.1.3'> 'Subsystem 18' {
                    attribute POIconv : String = "-";
                    attribute Ipoint : Boolean = false;
                    attribute mass : Real = 16.18946447349456;
                    attribute sigma_mass : Real = 1.7103015285819825;
                    attribute Cx : Real = 24.18579265803798;
                    attribute sigma_Cx : Real = 9.778470115375985;
                    attribute Cy : Real = -7.771077430653669;
                    attribute sigma_Cy : Real = 8.918071312776583;
                    attribute Cz : Real = 7.952915301635902;
                    attribute sigma_Cz : Real = 8.15322276938106;
                    attribute Ixx : Real = 78007.57761923368;
                    attribute sigma_Ixx : Real = 20070.504927397233;
                    attribute Iyy : Real = 97791.84230552563;
                    attribute sigma_Iyy : Real = 26232.998182818632;
                    attribute Izz : Real = 105367.17052046918;
                    attribute sigma_Izz : Real = 27309.788197456317;
                    attribute Ixy : Real = 11979.892311565854;
                    attribute sigma_Ixy : Real = 10896.323980002748;
                    attribute Ixz : Real = -10704.517295047994;
                    attribute sigma_Ixz : Real = 11055.397363175834;
                    attribute Iyz : Real = 3891.594795173729;
                    attribute sigma_Iyz : Real = 8839.600117026475;
                    part <'C.1.2.1.3.1'> 'Assembly 68' {
                        attribute POIconv : String = "-";
                        attribute Ipoint : Boolean = false;
                        attribute mass : Real = 7.827890161456773;
                        attribute sigma_mass : Real = 1.1919639546010696;
                        attribute Cx : Real = 14.097945043591125;
                        attribute sigma_Cx : Real = 15.74790020875971;
                        attribute Cy : Real = 5.983626884111243;
                        attribute sigma_Cy : Real = 10.371417219059364;
                        attribute Cz : Real = 21.32592046471569;
                        attribute sigma_Cz : Real = 11.7888311498923;
                        attribute Ixx : Real = 28559.69322168283;
                        attribute sigma_Ixx : Real = 10554.6018099285;
                        attribute Iyy : Real = 53345.54503314096;
                        attribute sigma_Iyy : Real = 22898.37061438697;
                        attribute Izz : Real = 50266.58075605352;
                        attribute sigma_Izz : Real = 21029.315373818878;
                        attribute Ixy : Real = -250.76126760894158;
                        attribute sigma_Ixy : Real = 7456.832914569532;
                        attribute Ixz : Real = -6300.827245809456;
                        attribute sigma_Ixz : Real = 9141.962706029346;
                        attribute Iyz : Real = 1178.8828668944252;
                        attribute sigma_Iyz : Real = 4479.1441689614285;
                        part <'C.1.2.1.3.1.1'> 'Subassembly 235' {
                            attribute POIconv : String = "-";
                            attribute Ipoint : Boolean = false;
                            attribute mass : Real = 2.3524774633238557;
                            attribute sigma_mass : Real = 0.5781874454998993;
                            attribute Cx : Real = -41.87184291115601;
                            attribute sigma_Cx : Real = 18.304419421381404;
                            attribute Cy : Real = -1.304624600518564;
                            attribute sigma_Cy : Real = 17.954591450523253;
                            attribute Cz : Real = 31.4331658543563;
                            attribute sigma_Cz : Real = 17.005247534748307;
                            attribute Ixx : Real = 5985.2883657610155;
                            attribute sigma_Ixx : Real = 3915.214570811361;
                            attribute Iyy : Real = 7031.11714871175;
                            attribute sigma_Iyy : Real = 4408.543021292006;
                            attribute Izz : Real = 9576.714484900443;
                            attribute sigma_Izz : Real = 5352.394051271844;
                            attribute Ixy : Real = -3673.1191709993186;
                            attribute sigma_Ixy : Real = 2631.2982387098587;
                            attribute Ixz : Real = 1160.43588199468;
                            attribute sigma_Ixz : Real = 2090.0247407908837;
                            attribute Iyz : Real = 29.246756582030628;
                            attribute sigma_Iyz : Real = 1879.337437394427;
                            part <'C.1.2.1.3.1.1.1'> 'Part 834' {
                                attribute POIconv : String = "+";
                                attribute Ipoint : Boolean = false;
                                attribute mass : Real = 0.40099378614360465;
                                attribute sigma_mass : Real = 0.28909372274994966;
                                attribute Cx : Real = -63.31187314353883;
                                attribute sigma_Cx : Real = 28.721044428837228;
                                attribute Cy : Real = 24.416656279936433;
                                attribute sigma_Cy : Real = 28.23690002309109;
                                attribute Cz : Real = 20.430675148963928;
                                attribute sigma_Cz : Real = 29.057750463592832;
                                attribute Ixx : Real = 0.43389863714674715;
                                attribute sigma_Ixx : Real = 0.37074144170588635;
                                attribute Iyy : Real = 0.4136057863438934;
                                attribute sigma_Iyy : Real = 0.3723953238821935;
                                attribute Izz : Real = 0.4511421402189289;
                                attribute sigma_Izz : Real = 0.37017423652493897;
                                attribute Ixy : Real = -0.033465300315132056;
                                attribute sigma_Ixy : Real = 0.02351283871158888;
                                attribute Ixz : Real = -0.0071074181250441355;
                                attribute sigma_Ixz : Real = 0.022566176940390956;
                                attribute Iyz : Real = 0.003935043067827086;
                                attribute sigma_Iyz : Real = 0.02209918015384651;
                            }
                            part <'C.1.2.1.3.1.1.2'> 'Part 835' {
                                attribute POIconv : String = "+";
                                attribute Ipoint : Boolean = false;
                                attribute mass : Real = 0.3965485842186026;
                                attribute sigma_mass : Real = 0.28909372274994966;
                                attribute Cx : Real = -37.19825576990843;
                                attribute sigma_Cx : Real = 28.721044428837228;
                                attribute Cy : Real = 35.98375837318599;
                                attribute sigma_Cy : Real = 28.23690002309109;
                                attribute Cz : Real = 85.53113783709705;
                                attribute sigma_Cz : Real = 29.057750463592832;
                                attribute Ixx : Real = 0.4887816802310661;
                                attribute sigma_Ixx : Real = 0.37074144170588635;
                                attribute Iyy : Real = 0.4759077769836566;
                                attribute sigma_Iyy : Real = 0.3723953238821935;
                                attribute Izz : Real = 0.47835749363910546;
                                attribute sigma_Izz : Real = 0.37017423652493897;
                                attribute Ixy : Real = -0.02665996960369591;
                                attribute sigma_Ixy : Real = 0.02351283871158888;
                                attribute Ixz : Real = -0.034850689630659654;
                                attribute sigma_Ixz : Real = 0.022566176940390956;
                                attribute Iyz : Real = 0.026177675493291808;
                                attribute sigma_Iyz : Real = 0.02209918015384651;
                            }
                            part <'C.1.2.1.3.1.1.3'> 'Part 836' {
                                attribute POIconv : String = "-";
                                attribute Ipoint : Boolean = false;
                                attribute mass : Real = 0.8315259313513524;
                                attribute sigma_mass : Real = 0.28909372274994966;
                                attribute Cx : Real = 15.8177703153342;
                                attribute sigma_Cx : Real = 28.721044428837228;
                                attribute Cy : Real = 23.80897239781916;
                                attribute sigma_Cy : Real = 28.23690002309109;
                                attribute Cz : Real = 7.037206087261438;
                                attribute sigma_Cz : Real = 29.057750463592832;
                                attribute Ixx : Real = 0.9275314361620922;
                                attribute sigma_Ixx : Real = 0.37074144170588635;
                                attribute Iyy : Real = 1.0193814559402556;
                                attribute sigma_Iyy : Real = 0.3723953238821935;
                                attribute Izz : Real = 1.056605242268911;
                                attribute sigma_Izz : Real = 0.37017423652493897;
                                attribute Ixy : Real = 0.07547228895137376;
                                attribute sigma_Ixy : Real = 0.02351283871158888;
                                attribute Ixz : Real = -0.0022189472138;
                                attribute sigma_Ixz : Real = 0.022566176940390956;
                                attribute Iyz : Real = 0.04228784251264097;
                                attribute sigma_Iyz : Real = 0.02209918015384651;
                            }
                            part <'C.1.2.1.3.1.1.4'> 'Part 837' {
                                attribute POIconv : String = "+";
                                attribute Ipoint : Boolean = false;
                                attribute mass : Real = 0.723409161610296;
                                attribute sigma_mass : Real = 0.28909372274994966;
                                attribute Cx : Real = -98.86088455095887;
                                attribute sigma_Cx : Real = 28.721044428837228;
                                attribute Cy : Real = -64.86939382739365;
                                attribute sigma_Cy : Real = 28.23690002309109;
                                attribute Cz : Real = 35.91932603158057;
                                attribute sigma_Cz : Real = 29.057750463592832;
                                attribute Ixx : Real = 0.8889606265451537;
                                attribute sigma_Ixx : Real = 0.37074144170588635;
                                attribute Iyy : Real = 0.8428181531060767;
                                attribute sigma_Iyy : Real = 0.3723953238821935;
                                attribute Izz : Real = 0.8737200009732881;
                                attribute sigma_Izz : Real = 0.37017423652493897;
                                attribute Ixy : Real = 0.026297500605374745;
                                attribute sigma_Ixy : Real = 0.02351283871158888;
                                attribute Ixz : Real = -0.015683970796338036;
                                attribute sigma_Ixz : Real = 0.022566176940390956;
                                attribute Iyz : Real = 0.05770215468870961;
                                attribute sigma_Iyz : Real = 0.02209918015384651;
                            }
                        }
                        part <'C.1.2.1.3.1.2'> 'Subassembly 236' {
                            attribute POIconv : String = "-";
                            attribute Ipoint : Boolean = false;
                            attribute mass : Real = 1.1083677228069864;
                            attribute sigma_mass : Real = 0.5007250159521434;
                            attribute Cx : Real = 82.32265535911407;
                            attribute sigma_Cx : Real = 53.06077576777315;
                            attribute Cy : Real = -21.206846372745552;
                            attribute sigma_Cy : Real = 29.972336917475147;
                            attribute Cz : Real = 50.44212703423485;
                            attribute sigma_Cz : Real = 24.14512531014511;
                            attribute Ixx : Real = 338.915219299952;
                            attribute sigma_Ixx : Real = 1559.050320442253;
                            attribute Iyy : Real = 2035.752693116231;
                            attribute sigma_Iyy : Real = 9151.200478485604;
                            attribute Izz : Real = 2242.5046874275035;
                            attribute sigma_Izz : Real = 10636.283052536623;
                            attribute Ixy : Real = 465.774881712775;
                            attribute sigma_Ixy : Real = 3737.216673263092;
                            attribute Ixz : Real = 141.98057834137165;
                            attribute sigma_Ixz : Real = 648.0672176608928;
                            attribute Iyz : Real = 60.945885432794555;
                            attribute sigma_Iyz : Real = 214.28591174939604;
                            part <'C.1.2.1.3.1.2.1'> 'Part 838' {
                                attribute POIconv : String = "-";
                                attribute Ipoint : Boolean = false;
                                attribute mass : Real = 0.18060214138007724;
                                attribute sigma_mass : Real = 0.28909372274994966;
                                attribute Cx : Real = 40.98220723681152;
                                attribute sigma_Cx : Real = 28.721044428837228;
                                attribute Cy : Real = -36.13418573513627;
                                attribute sigma_Cy : Real = 28.23690002309109;
                                attribute Cz : Real = 67.83918738365173;
                                attribute sigma_Cz : Real = 29.057750463592832;
                                attribute Ixx : Real = 0.17763309127981006;
                                attribute sigma_Ixx : Real = 0.37074144170588635;
                                attribute Iyy : Real = 0.1833857910489603;
                                attribute sigma_Iyy : Real = 0.3723953238821935;
                                attribute Izz : Real = 0.17439103717133309;
                                attribute sigma_Izz : Real = 0.37017423652493897;
                                attribute Ixy : Real = 0.007774736480611695;
                                attribute sigma_Ixy : Real = 0.02351283871158888;
                                attribute Ixz : Real = 0.0036302044481339012;
                                attribute sigma_Ixz : Real = 0.022566176940390956;
                                attribute Iyz : Real = 0.005082938168061955;
                                attribute sigma_Iyz : Real = 0.02209918015384651;
                            }
                            part <'C.1.2.1.3.1.2.2'> 'Part 839' {
                                attribute POIconv : String = "-";
                                attribute Ipoint : Boolean = false;
                                attribute mass : Real = 0.04448513200553134;
                                attribute sigma_mass : Real = 0.28909372274994966;
                                attribute Cx : Real = -94.68534686602652;
                                attribute sigma_Cx : Real = 28.721044428837228;
                                attribute Cy : Real = 50.96291727386415;
                                attribute sigma_Cy : Real = 28.23690002309109;
                                attribute Cz : Real = 45.531967328861356;
                                attribute sigma_Cz : Real = 29.057750463592832;
                                attribute Ixx : Real = 0.048070007514982596;
                                attribute sigma_Ixx : Real = 0.37074144170588635;
                                attribute Iyy : Real = 0.05155913239151727;
                                attribute sigma_Iyy : Real = 0.3723953238821935;
                                attribute Izz : Real = 0.04919815742735186;
                                attribute sigma_Izz : Real = 0.37017423652493897;
                                attribute Ixy : Real = -0.0003405101173115414;
                                attribute sigma_Ixy : Real = 0.02351283871158888;
                                attribute Ixz : Real = 0.0002667001804250943;
                                attribute sigma_Ixz : Real = 0.022566176940390956;
                                attribute Iyz : Real = -0.0011680604355123628;
                                attribute sigma_Iyz : Real = 0.02209918015384651;
                            }
                            part <'C.1.2.1.3.1.2.3'> 'Part 840' {
                                attribute POIconv : String = "+";
                                attribute Ipoint : Boolean = false;
                                attribute mass : Real = 0.8832804494213778;
                                attribute sigma_mass : Real = 0.28909372274994966;
                                attribute Cx : Real = 99.69018320553005;
                                attribute sigma_Cx : Real = 28.721044428837228;
                                attribute Cy : Real = -21.789415599778295;
                                attribute sigma_Cy : Real = 28.23690002309109;
                                attribute Cz : Real = 47.132286708801985;
                                attribute sigma_Cz : Real = 29.057750463592832;
                                attribute Ixx : Real = 1.037771344959049;
                                attribute sigma_Ixx : Real = 0.37074144170588635;
                                attribute Iyy : Real = 1.227757984799689;
                                attribute sigma_Iyy : Real = 0.3723953238821935;
                                attribute Izz : Real = 1.1584179282114149;
                                attribute sigma_Izz : Real = 0.37017423652493897;
                                attribute Ixy : Real = 0.00020116007688728452;
                                attribute sigma_Ixy : Real = 0.02351283871158888;
                                attribute Ixz : Real = 0.023356926861564535;
                                attribute sigma_Ixz : Real = 0.022566176940390956;
                                attribute Iyz : Real = 0.01975443995295485;
                                attribute sigma_Iyz : Real = 0.02209918015384651;
                            }
                        }
                        part <'C.1.2.1.3.1.3'> 'Subassembly 237' {
                            attribute POIconv : String = "-";
                            attribute Ipoint : Boolean = false;
                            attribute mass : Real = 2.104327304575825;
                            attribute sigma_mass : Real = 0.5781874454998993;
                            attribute Cx : Real = 21.380528758409724;
                            attribute sigma_Cx : Real = 21.238643720263923;
                            attribute Cy : Real = 9.604329705685014;
                            attribute sigma_Cy : Real = 18.053885039450638;
                            attribute Cz : Real = -23.49402365985307;
                            attribute sigma_Cz : Real = 20.386101863252186;
                            attribute Ixx : Real = 8302.191025267604;
                            attribute sigma_Ixx : Real = 4701.279669443848;
                            attribute Iyy : Real = 12068.66069547745;
                            attribute sigma_Iyy : Real = 6221.552478207257;
                            attribute Izz : Real = 8674.210901148504;
                            attribute sigma_Izz : Real = 4849.299880513259;
                            attribute Ixy : Real = -101.23365377986318;
                            attribute sigma_Ixy : Real = 2208.1973773863356;
                            attribute Ixz : Real = -3946.148552180775;
                            attribute sigma_Ixz : Real = 3051.687572356248;
                            attribute Iyz : Real = -1655.8505204233038;
                            attribute sigma_Iyz : Real = 2063.430574107076;
                            part <'C.1.2.1.3.1.3.1'> 'Part 841' {
                                attribute POIconv : String = "-";
                                attribute Ipoint : Boolean = false;
                                attribute mass : Real = 0.6974133238613139;
                                attribute sigma_mass : Real = 0.28909372274994966;
                                attribute Cx : Real = 58.90536648221314;
                                attribute sigma_Cx : Real = 28.721044428837228;
                                attribute Cy : Real = 11.541157588362694;
                                attribute sigma_Cy : Real = 28.23690002309109;
                                attribute Cz : Real = 42.282070592045784;
                                attribute sigma_Cz : Real = 29.057750463592832;
                                attribute Ixx : Real = 0.7733964985157729;
                                attribute sigma_Ixx : Real = 0.37074144170588635;
                                attribute Iyy : Real = 0.9014774039244129;
                                attribute sigma_Iyy : Real = 0.3723953238821935;
                                attribute Izz : Real = 0.8169174212999276;
                                attribute sigma_Izz : Real = 0.37017423652493897;
                                attribute Ixy : Real = 0.0870349451067998;
                                attribute sigma_Ixy : Real = 0.02351283871158888;
                                attribute Ixz : Real = 0.02392171970335654;
                                attribute sigma_Ixz : Real = 0.022566176940390956;
                                attribute Iyz : Real = 0.02333493268479006;
                                attribute sigma_Iyz : Real = 0.02209918015384651;
                            }
                            part <'C.1.2.1.3.1.3.2'> 'Part 842' {
                                attribute POIconv : String = "-";
                                attribute Ipoint : Boolean = false;
                                attribute mass : Real = 0.4710435666393023;
                                attribute sigma_mass : Real = 0.28909372274994966;
                                attribute Cx : Real = -61.673590913414955;
                                attribute sigma_Cx : Real = 28.721044428837228;
                                attribute Cy : Real = -27.983535081148148;
                                attribute sigma_Cy : Real = 28.23690002309109;
                                attribute Cz : Real = -97.16738099232316;
                                attribute sigma_Cz : Real = 29.057750463592832;
                                attribute Ixx : Real = 0.5614294522864547;
                                attribute sigma_Ixx : Real = 0.37074144170588635;
                                attribute Iyy : Real = 0.5569097222664281;
                                attribute sigma_Iyy : Real = 0.3723953238821935;
                                attribute Izz : Real = 0.6337890002713044;
                                attribute sigma_Izz : Real = 0.37017423652493897;
                                attribute Ixy : Real = 0.0037484803960846948;
                                attribute sigma_Ixy : Real = 0.02351283871158888;
                                attribute Ixz : Real = 0.0024649904939099583;
                                attribute sigma_Ixz : Real = 0.022566176940390956;
                                attribute Iyz : Real = -0.0064300217386122575;
                                attribute sigma_Iyz : Real = 0.02209918015384651;
                            }
                            part <'C.1.2.1.3.1.3.3'> 'Part 843' {
                                attribute POIconv : String = "-";
                                attribute Ipoint : Boolean = false;
                                attribute mass : Real = 0.5676760180015117;
                                attribute sigma_mass : Real = 0.28909372274994966;
                                attribute Cx : Real = 70.62185569666326;
                                attribute sigma_Cx : Real = 28.721044428837228;
                                attribute Cy : Real = -5.148091074079275;
                                attribute sigma_Cy : Real = 28.23690002309109;
                                attribute Cz : Real = -45.27322403155267;
                                attribute sigma_Cz : Real = 29.057750463592832;
                                attribute Ixx : Real = 0.6506581121627749;
                                attribute sigma_Ixx : Real = 0.37074144170588635;
                                attribute Iyy : Real = 0.6773699207006573;
                                attribute sigma_Iyy : Real = 0.3723953238821935;
                                attribute Izz : Real = 0.8307662490023936;
                                attribute sigma_Izz : Real = 0.37017423652493897;
                                attribute Ixy : Real = -0.03918493957988709;
                                attribute sigma_Ixy : Real = 0.02351283871158888;
                                attribute Ixz : Real = 0.01553861912446197;
                                attribute sigma_Ixz : Real = 0.022566176940390956;
                                attribute Iyz : Real = -0.02922590426635077;
                                attribute sigma_Iyz : Real = 0.02209918015384651;
                            }
                            part <'C.1.2.1.3.1.3.4'> 'Part 844' {
                                attribute POIconv : String = "-";
                                attribute Ipoint : Boolean = false;
                                attribute mass : Real = 0.36819439607369714;
                                attribute sigma_mass : Real = 0.28909372274994966;
                                attribute Cx : Real = -19.362441822886467;
                                attribute sigma_Cx : Real = 28.721044428837228;
                                attribute Cy : Real = 76.76816508173943;
                                attribute sigma_Cy : Real = 28.23690002309109;
                                attribute Cz : Real = -20.25180640630424;
                                attribute sigma_Cz : Real = 29.057750463592832;
                                attribute Ixx : Real = 0.40684972322174673;
                                attribute sigma_Ixx : Real = 0.37074144170588635;
                                attribute Iyy : Real = 0.3816103408811263;
                                attribute sigma_Iyy : Real = 0.3723953238821935;
                                attribute Izz : Real = 0.40004719993120336;
                                attribute sigma_Izz : Real = 0.37017423652493897;
                                attribute Ixy : Real = -0.00459355852336243;
                                attribute sigma_Ixy : Real = 0.02351283871158888;
                                attribute Ixz : Real = 0.01398166946070881;
                                attribute sigma_Ixz : Real = 0.022566176940390956;
                                attribute Iyz : Real = 0.005299486149481961;
                                attribute sigma_Iyz : Real = 0.02209918015384651;
                            }
                        }
                        part <'C.1.2.1.3.1.4'> 'Subassembly 238' {
                            attribute POIconv : String = "-";
                            attribute Ipoint : Boolean = false;
                            attribute mass : Real = 1.433358836344676;
                            attribute sigma_mass : Real = 0.5781874454998993;
                            attribute Cx : Real = 2.912087410263373;
                            attribute sigma_Cx : Real = 29.715299611854416;
                            attribute Cy : Real = 13.3872700102777;
                            attribute sigma_Cy : Real = 25.041800791429022;
                            attribute Cz : Real = 42.4961194439372;
                            attribute sigma_Cz : Real = 26.614163737643832;
                            attribute Ixx : Real = 4442.628289532793;
                            attribute sigma_Ixx : Real = 4177.335450633407;
                            attribute Iyy : Real = 5822.517900519395;
                            attribute sigma_Iyy : Real = 4696.62484083651;
                            attribute Izz : Real = 8594.729832201638;
                            attribute sigma_Izz : Real = 5184.287796865258;
                            attribute Ixy : Real = 3476.201950547108;
                            attribute sigma_Ixy : Real = 2322.4318151122293;
                            attribute Ixz : Real = -1580.1185855129406;
                            attribute sigma_Ixz : Real = 1675.1969119621995;
                            attribute Iyz : Real = 1557.535411662467;
                            attribute sigma_Iyz : Real = 1753.9648569196409;
                            part <'C.1.2.1.3.1.4.1'> 'Part 845' {
                                attribute POIconv : String = "-";
                                attribute Ipoint : Boolean = false;
                                attribute mass : Real = 0.17836986341816374;
                                attribute sigma_mass : Real = 0.28909372274994966;
                                attribute Cx : Real = -84.28431488573551;
                                attribute sigma_Cx : Real = 28.721044428837228;
                                attribute Cy : Real = 11.25832605175674;
                                attribute sigma_Cy : Real = 28.23690002309109;
                                attribute Cz : Real = 36.66739072650671;
                                attribute sigma_Cz : Real = 29.057750463592832;
                                attribute Ixx : Real = 0.20491633877743987;
                                attribute sigma_Ixx : Real = 0.37074144170588635;
                                attribute Iyy : Real = 0.21112120229710843;
                                attribute sigma_Iyy : Real = 0.3723953238821935;
                                attribute Izz : Real = 0.20690681109857711;
                                attribute sigma_Izz : Real = 0.37017423652493897;
                                attribute Ixy : Real = 0.006710751585280946;
                                attribute sigma_Ixy : Real = 0.02351283871158888;
                                attribute Ixz : Real = -0.015210111434240042;
                                attribute sigma_Ixz : Real = 0.022566176940390956;
                                attribute Iyz : Real = -0.002353009527986966;
                                attribute sigma_Iyz : Real = 0.02209918015384651;
                            }
                            part <'C.1.2.1.3.1.4.2'> 'Part 846' {
                                attribute POIconv : String = "-";
                                attribute Ipoint : Boolean = false;
                                attribute mass : Real = 0.025595546347554773;
                                attribute sigma_mass : Real = 0.28909372274994966;
                                attribute Cx : Real = 6.225353619083762;
                                attribute sigma_Cx : Real = 28.721044428837228;
                                attribute Cy : Real = 45.47065733931959;
                                attribute sigma_Cy : Real = 28.23690002309109;
                                attribute Cz : Real = -46.5387755073607;
                                attribute sigma_Cz : Real = 29.057750463592832;
                                attribute Ixx : Real = 0.036601651673853056;
                                attribute sigma_Ixx : Real = 0.37074144170588635;
                                attribute Iyy : Real = 0.03465495501650911;
                                attribute sigma_Iyy : Real = 0.3723953238821935;
                                attribute Izz : Real = 0.036434757713451886;
                                attribute sigma_Izz : Real = 0.37017423652493897;
                                attribute Ixy : Real = 0.0006698178929613933;
                                attribute sigma_Ixy : Real = 0.02351283871158888;
                                attribute Ixz : Real = 6.956095830493443e-05;
                                attribute sigma_Ixz : Real = 0.022566176940390956;
                                attribute Iyz : Real = -9.337699946537705e-05;
                                attribute sigma_Iyz : Real = 0.02209918015384651;
                            }
                            part <'C.1.2.1.3.1.4.3'> 'Part 847' {
                                attribute POIconv : String = "-";
                                attribute Ipoint : Boolean = false;
                                attribute mass : Real = 0.7577999298607465;
                                attribute sigma_mass : Real = 0.28909372274994966;
                                attribute Cx : Real = 57.1947630494833;
                                attribute sigma_Cx : Real = 28.721044428837228;
                                attribute Cy : Real = -29.537076270207763;
                                attribute sigma_Cy : Real = 28.23690002309109;
                                attribute Cz : Real = 62.86085303872824;
                                attribute sigma_Cz : Real = 29.057750463592832;
                                attribute Ixx : Real = 0.8989543317891859;
                                attribute sigma_Ixx : Real = 0.37074144170588635;
                                attribute Iyy : Real = 0.93669153846115;
                                attribute sigma_Iyy : Real = 0.3723953238821935;
                                attribute Izz : Real = 0.9273691313152126;
                                attribute sigma_Izz : Real = 0.37017423652493897;
                                attribute Ixy : Real = 0.006974220493670368;
                                attribute sigma_Ixy : Real = 0.02351283871158888;
                                attribute Ixz : Real = -0.0015070331325996455;
                                attribute sigma_Ixz : Real = 0.022566176940390956;
                                attribute Iyz : Real = -0.004893940154830681;
                                attribute sigma_Iyz : Real = 0.02209918015384651;
                            }
                            part <'C.1.2.1.3.1.4.4'> 'Part 848' {
                                attribute POIconv : String = "+";
                                attribute Ipoint : Boolean = false;
                                attribute mass : Real = 0.4715934967182111;
                                attribute sigma_mass : Real = 0.28909372274994966;
                                attribute Cx : Real = -51.51402843184769;
                                attribute sigma_Cx : Real = 28.721044428837228;
                                attribute Cy : Real = 81.42598224803805;
                                attribute sigma_Cy : Real = 28.23690002309109;
                                attribute Cz : Real = 16.80910838767886;
                                attribute sigma_Cz : Real = 29.057750463592832;
                                attribute Ixx : Real = 0.5489609593213219;
                                attribute sigma_Ixx : Real = 0.37074144170588635;
                                attribute Iyy : Real = 0.5693346421181444;
                                attribute sigma_Iyy : Real = 0.3723953238821935;
                                attribute Izz : Real = 0.6659487347226564;
                                attribute sigma_Izz : Real = 0.37017423652493897;
                                attribute Ixy : Real = 0.03993464009478294;
                                attribute sigma_Ixy : Real = 0.02351283871158888;
                                attribute Ixz : Real = -0.023106712773182526;
                                attribute sigma_Ixz : Real = 0.022566176940390956;
                                attribute Iyz : Real = -0.006797290756618564;
                                attribute sigma_Iyz : Real = 0.02209918015384651;
                            }
                        }
                        part <'C.1.2.1.3.1.5'> 'Subassembly 239' {
                            attribute POIconv : String = "-";
                            attribute Ipoint : Boolean = false;
                            attribute mass : Real = 0.8293588344054297;
                            attribute sigma_mass : Real = 0.40884026350990615;
                            attribute Cx : Real = 82.5339509631965;
                            attribute sigma_Cx : Real = 66.2062602483355;
                            attribute Cy : Real = 41.01221521038887;
                            attribute sigma_Cy : Real = 28.044047945693688;
                            attribute Cz : Real = 30.878854056942203;
                            attribute sigma_Cz : Real = 51.445536895340695;
                            attribute Ixx : Real = 1297.231307123743;
                            attribute sigma_Ixx : Real = 4889.494686415715;
                            attribute Iyy : Real = 3558.5628831325585;
                            attribute sigma_Iyy : Real = 13318.073117725033;
                            attribute Izz : Real = 2406.565294528259;
                            attribute sigma_Izz : Real = 9023.398371066703;
                            attribute Ixy : Real = 410.08545164764723;
                            attribute sigma_Ixy : Real = 1607.8179081961848;
                            attribute Ixz : Real = -1690.1493582373184;
                            attribute sigma_Ixz : Real = 6330.172543065857;
                            attribute Iyz : Real = 296.93075602093813;
                            attribute sigma_Iyz : Real = 1166.1680693832768;
                            part <'C.1.2.1.3.1.5.1'> 'Part 849' {
                                attribute POIconv : String = "-";
                                attribute Ipoint : Boolean = false;
                                attribute mass : Real = 0.7584273910708725;
                                attribute sigma_mass : Real = 0.28909372274994966;
                                attribute Cx : Real = 98.75570465810597;
                                attribute sigma_Cx : Real = 28.721044428837228;
                                attribute Cy : Real = 38.16164047457278;
                                attribute sigma_Cy : Real = 28.23690002309109;
                                attribute Cz : Real = 42.628013947978616;
                                attribute sigma_Cz : Real = 29.057750463592832;
                                attribute Ixx : Real = 0.9456711438455622;
                                attribute sigma_Ixx : Real = 0.37074144170588635;
                                attribute Iyy : Real = 0.8135015464339254;
                                attribute sigma_Iyy : Real = 0.3723953238821935;
                                attribute Izz : Real = 0.9009828819031636;
                                attribute sigma_Izz : Real = 0.37017423652493897;
                                attribute Ixy : Real = 0.025686869040586;
                                attribute sigma_Ixy : Real = 0.02351283871158888;
                                attribute Ixz : Real = -0.0025239344307033413;
                                attribute sigma_Ixz : Real = 0.022566176940390956;
                                attribute Iyz : Real = -0.06813605856113383;
                                attribute sigma_Iyz : Real = 0.02209918015384651;
                            }
                            part <'C.1.2.1.3.1.5.2'> 'Part 850' {
                                attribute POIconv : String = "-";
                                attribute Ipoint : Boolean = false;
                                attribute mass : Real = 0.07093144333455711;
                                attribute sigma_mass : Real = 0.28909372274994966;
                                attribute Cx : Real = -90.91553427278996;
                                attribute sigma_Cx : Real = 28.721044428837228;
                                attribute Cy : Real = 71.49170157499611;
                                attribute sigma_Cy : Real = 28.23690002309109;
                                attribute Cz : Real = -94.74786752834916;
                                attribute sigma_Cz : Real = 29.057750463592832;
                                attribute Ixx : Real = 0.08694027832231106;
                                attribute sigma_Ixx : Real = 0.37074144170588635;
                                attribute Iyy : Real = 0.07925489046836325;
                                attribute sigma_Iyy : Real = 0.3723953238821935;
                                attribute Izz : Real = 0.07676549023377613;
                                attribute sigma_Izz : Real = 0.37017423652493897;
                                attribute Ixy : Real = -0.0007213143040008382;
                                attribute sigma_Ixy : Real = 0.02351283871158888;
                                attribute Ixz : Real = -0.008296425753552775;
                                attribute sigma_Ixz : Real = 0.022566176940390956;
                                attribute Iyz : Real = -0.0014388781583278211;
                                attribute sigma_Iyz : Real = 0.02209918015384651;
                            }
                        }
                    }
                    part <'C.1.2.1.3.2'> 'Assembly 69' {
                        attribute POIconv : String = "-";
                        attribute Ipoint : Boolean = false;
                        attribute mass : Real = 8.361574312037789;
                        attribute sigma_mass : Real = 1.2265207905297184;
                        attribute Cx : Real = 33.6297753513113;
                        attribute sigma_Cx : Real = 11.709620314980825;
                        attribute Cy : Real = -20.647876770257348;
                        attribute sigma_Cy : Real = 14.016468805210513;
                        attribute Cz : Real = -4.56654713912436;
                        attribute sigma_Cz : Real = 10.972279629803818;
                        attribute Ixx : Real = 43869.97596816995;
                        attribute sigma_Ixx : Real = 16297.525478764319;
                        attribute Iyy : Real = 40193.449708904125;
                        attribute sigma_Iyy : Real = 11943.917251165161;
                        attribute Izz : Real = 50690.80587794497;
                        attribute sigma_Izz : Real = 16723.345746738232;
                        attribute Ixy : Real = 10127.65526563315;
                        attribute sigma_Ixy : Real = 7530.971253247689;
                        attribute Ixz : Real = -6448.3292258693;
                        attribute sigma_Ixz : Real = 5723.800294990026;
                        attribute Iyz : Real = 5500.5620604189735;
                        attribute sigma_Iyz : Real = 7186.803894501291;
                        part <'C.1.2.1.3.2.1'> 'Subassembly 240' {
                            attribute POIconv : String = "-";
                            attribute Ipoint : Boolean = false;
                            attribute mass : Real = 1.7743090828824788;
                            attribute sigma_mass : Real = 0.5007250159521434;
                            attribute Cx : Real = 58.338575913221064;
                            attribute sigma_Cx : Real = 19.904728119605174;
                            attribute Cy : Real = -42.01789432124054;
                            attribute sigma_Cy : Real = 19.7565991394489;
                            attribute Cz : Real = -51.603076331240516;
                            attribute sigma_Cz : Real = 19.775219073255048;
                            attribute Ixx : Real = 2548.195843320399;
                            attribute sigma_Ixx : Real = 2657.3163600620915;
                            attribute Iyy : Real = 2110.851677776517;
                            attribute sigma_Iyy : Real = 2404.5600492123967;
                            attribute Izz : Real = 2679.5545265015144;
                            attribute sigma_Izz : Real = 2693.452111480065;
                            attribute Ixy : Real = 1269.9057803563555;
                            attribute sigma_Ixy : Real = 1346.6984674305447;
                            attribute Ixz : Real = -1017.8920738288006;
                            attribute sigma_Ixz : Real = 1200.8610513315916;
                            attribute Iyz : Real = 1240.6404554793205;
                            attribute sigma_Iyz : Real = 1334.4564329857978;
                            part <'C.1.2.1.3.2.1.1'> 'Part 851' {
                                attribute POIconv : String = "-";
                                attribute Ipoint : Boolean = false;
                                attribute mass : Real = 0.16698747498332522;
                                attribute sigma_mass : Real = 0.28909372274994966;
                                attribute Cx : Real = 79.75233374163508;
                                attribute sigma_Cx : Real = 28.721044428837228;
                                attribute Cy : Real = -42.011516727507114;
                                attribute sigma_Cy : Real = 28.23690002309109;
                                attribute Cz : Real = -50.059696519747376;
                                attribute sigma_Cz : Real = 29.057750463592832;
                                attribute Ixx : Real = 0.2446022948140927;
                                attribute sigma_Ixx : Real = 0.37074144170588635;
                                attribute Iyy : Real = 0.24626061312165018;
                                attribute sigma_Iyy : Real = 0.3723953238821935;
                                attribute Izz : Real = 0.23472495987538344;
                                attribute sigma_Izz : Real = 0.37017423652493897;
                                attribute Ixy : Real = -0.002972235633421123;
                                attribute sigma_Ixy : Real = 0.02351283871158888;
                                attribute Ixz : Real = 0.0029887339776154863;
                                attribute sigma_Ixz : Real = 0.022566176940390956;
                                attribute Iyz : Real = 0.013387998794383862;
                                attribute sigma_Iyz : Real = 0.02209918015384651;
                            }
                            part <'C.1.2.1.3.2.1.2'> 'Part 852' {
                                attribute POIconv : String = "-";
                                attribute Ipoint : Boolean = false;
                                attribute mass : Real = 0.8872344696600921;
                                attribute sigma_mass : Real = 0.28909372274994966;
                                attribute Cx : Real = 33.247135719284415;
                                attribute sigma_Cx : Real = 28.721044428837228;
                                attribute Cy : Real = -13.975840294733644;
                                attribute sigma_Cy : Real = 28.23690002309109;
                                attribute Cz : Real = -74.10353431478143;
                                attribute sigma_Cz : Real = 29.057750463592832;
                                attribute Ixx : Real = 1.0351687186330198;
                                attribute sigma_Ixx : Real = 0.37074144170588635;
                                attribute Iyy : Real = 1.0173308018021852;
                                attribute sigma_Iyy : Real = 0.3723953238821935;
                                attribute Izz : Real = 1.1655502162221663;
                                attribute sigma_Izz : Real = 0.37017423652493897;
                                attribute Ixy : Real = -0.00015872870575983403;
                                attribute sigma_Ixy : Real = 0.02351283871158888;
                                attribute Ixz : Real = -0.10618243061171033;
                                attribute sigma_Ixz : Real = 0.022566176940390956;
                                attribute Iyz : Real = -0.02182010108579728;
                                attribute sigma_Iyz : Real = 0.02209918015384651;
                            }
                            part <'C.1.2.1.3.2.1.3'> 'Part 853' {
                                attribute POIconv : String = "-";
                                attribute Ipoint : Boolean = false;
                                attribute mass : Real = 0.7200871382390615;
                                attribute sigma_mass : Real = 0.28909372274994966;
                                attribute Cx : Real = 84.28843710571527;
                                attribute sigma_Cx : Real = 28.721044428837228;
                                attribute Cy : Real = -76.57057633623481;
                                attribute sigma_Cy : Real = 28.23690002309109;
                                attribute Cz : Real = -24.23769822344184;
                                attribute sigma_Cz : Real = 29.057750463592832;
                                attribute Ixx : Real = 0.7041585712206068;
                                attribute sigma_Ixx : Real = 0.37074144170588635;
                                attribute Iyy : Real = 0.7016647586513276;
                                attribute sigma_Iyy : Real = 0.3723953238821935;
                                attribute Izz : Real = 0.7074755072409198;
                                attribute sigma_Izz : Real = 0.37017423652493897;
                                attribute Ixy : Real = 0.0027835058640887454;
                                attribute sigma_Ixy : Real = 0.02351283871158888;
                                attribute Ixz : Real = -0.011163511440675228;
                                attribute sigma_Ixz : Real = 0.022566176940390956;
                                attribute Iyz : Real = -0.034477368700925395;
                                attribute sigma_Iyz : Real = 0.02209918015384651;
                            }
                        }
                        part <'C.1.2.1.3.2.2'> 'Subassembly 241' {
                            attribute POIconv : String = "-";
                            attribute Ipoint : Boolean = false;
                            attribute mass : Real = 1.7344175181372556;
                            attribute sigma_mass : Real = 0.5781874454998993;
                            attribute Cx : Real = -13.013821306216093;
                            attribute sigma_Cx : Real = 22.99441873485875;
                            attribute Cy : Real = -59.528492493438414;
                            attribute sigma_Cy : Real = 25.8000782155719;
                            attribute Cz : Real = 7.776774881890079;
                            attribute sigma_Cz : Real = 20.18452749405551;
                            attribute Ixx : Real = 4005.9083240460404;
                            attribute sigma_Ixx : Real = 4768.102402022156;
                            attribute Iyy : Real = 3803.9780162106426;
                            attribute sigma_Iyy : Real = 3315.6449641169975;
                            attribute Izz : Real = 5731.016619127888;
                            attribute sigma_Izz : Real = 5178.60408828764;
                            attribute Ixy : Real = 1083.0387665154494;
                            attribute sigma_Ixy : Real = 2272.2230896704023;
                            attribute Ixz : Real = 863.896673864529;
                            attribute sigma_Ixz : Real = 1539.2676986401434;
                            attribute Iyz : Real = -798.0803241341987;
                            attribute sigma_Iyz : Real = 2127.0368618951143;
                            part <'C.1.2.1.3.2.2.1'> 'Part 854' {
                                attribute POIconv : String = "+";
                                attribute Ipoint : Boolean = false;
                                attribute mass : Real = 0.06637552624614909;
                                attribute sigma_mass : Real = 0.28909372274994966;
                                attribute Cx : Real = -65.73344920761883;
                                attribute sigma_Cx : Real = 28.721044428837228;
                                attribute Cy : Real = 42.837348533794284;
                                attribute sigma_Cy : Real = 28.23690002309109;
                                attribute Cz : Real = -47.21266976557672;
                                attribute sigma_Cz : Real = 29.057750463592832;
                                attribute Ixx : Real = 0.07601141126649608;
                                attribute sigma_Ixx : Real = 0.37074144170588635;
                                attribute Iyy : Real = 0.07311074736691542;
                                attribute sigma_Iyy : Real = 0.3723953238821935;
                                attribute Izz : Real = 0.07816037962959646;
                                attribute sigma_Izz : Real = 0.37017423652493897;
                                attribute Ixy : Real = -0.003240559665272272;
                                attribute sigma_Ixy : Real = 0.02351283871158888;
                                attribute Ixz : Real = 0.0005301398026383039;
                                attribute sigma_Ixz : Real = 0.022566176940390956;
                                attribute Iyz : Real = 0.00023359646076289906;
                                attribute sigma_Iyz : Real = 0.02209918015384651;
                            }
                            part <'C.1.2.1.3.2.2.2'> 'Part 855' {
                                attribute POIconv : String = "-";
                                attribute Ipoint : Boolean = false;
                                attribute mass : Real = 0.651910930801183;
                                attribute sigma_mass : Real = 0.28909372274994966;
                                attribute Cx : Real = 30.22468676790595;
                                attribute sigma_Cx : Real = 28.721044428837228;
                                attribute Cy : Real = -98.74559822492301;
                                attribute sigma_Cy : Real = 28.23690002309109;
                                attribute Cz : Real = -17.42980726994574;
                                attribute sigma_Cz : Real = 29.057750463592832;
                                attribute Ixx : Real = 0.8577564852089625;
                                attribute sigma_Ixx : Real = 0.37074144170588635;
                                attribute Iyy : Real = 0.7401335690513332;
                                attribute sigma_Iyy : Real = 0.3723953238821935;
                                attribute Izz : Real = 0.8739325202977855;
                                attribute sigma_Izz : Real = 0.37017423652493897;
                                attribute Ixy : Real = -0.05112854812300843;
                                attribute sigma_Ixy : Real = 0.02351283871158888;
                                attribute Ixz : Real = 0.005699994729036106;
                                attribute sigma_Ixz : Real = 0.022566176940390956;
                                attribute Iyz : Real = 0.016233382108483515;
                                attribute sigma_Iyz : Real = 0.02209918015384651;
                            }
                            part <'C.1.2.1.3.2.2.3'> 'Part 856' {
                                attribute POIconv : String = "-";
                                attribute Ipoint : Boolean = false;
                                attribute mass : Real = 0.7030004933588206;
                                attribute sigma_mass : Real = 0.28909372274994966;
                                attribute Cx : Real = -19.05247075483203;
                                attribute sigma_Cx : Real = 28.721044428837228;
                                attribute Cy : Real = -20.96820971928537;
                                attribute sigma_Cy : Real = 28.23690002309109;
                                attribute Cz : Real = 30.952070746570826;
                                attribute sigma_Cz : Real = 29.057750463592832;
                                attribute Ixx : Real = 0.7477947201232356;
                                attribute sigma_Ixx : Real = 0.37074144170588635;
                                attribute Iyy : Real = 0.7509087750921246;
                                attribute sigma_Iyy : Real = 0.3723953238821935;
                                attribute Izz : Real = 0.6083553538837135;
                                attribute sigma_Izz : Real = 0.37017423652493897;
                                attribute Ixy : Real = 0.004966556991600009;
                                attribute sigma_Ixy : Real = 0.02351283871158888;
                                attribute Ixz : Real = -0.024876684771466758;
                                attribute sigma_Ixz : Real = 0.022566176940390956;
                                attribute Iyz : Real = 0.02692203311809019;
                                attribute sigma_Iyz : Real = 0.02209918015384651;
                            }
                            part <'C.1.2.1.3.2.2.4'> 'Part 857' {
                                attribute POIconv : String = "-";
                                attribute Ipoint : Boolean = false;
                                attribute mass : Real = 0.3131305677311029;
                                attribute sigma_mass : Real = 0.28909372274994966;
                                attribute Cx : Real = -78.30029143951833;
                                attribute sigma_Cx : Real = 28.721044428837228;
                                attribute Cy : Real = -86.1513308249414;
                                attribute sigma_Cy : Real = 28.23690002309109;
                                attribute Cz : Real = 19.880848145112395;
                                attribute sigma_Cz : Real = 29.057750463592832;
                                attribute Ixx : Real = 0.47021226519225606;
                                attribute sigma_Ixx : Real = 0.37074144170588635;
                                attribute Iyy : Real = 0.47282941316419513;
                                attribute sigma_Iyy : Real = 0.3723953238821935;
                                attribute Izz : Real = 0.49582818660291456;
                                attribute sigma_Izz : Real = 0.37017423652493897;
                                attribute Ixy : Real = -0.004039362404676732;
                                attribute sigma_Ixy : Real = 0.02351283871158888;
                                attribute Ixz : Real = -0.0029216016162537327;
                                attribute sigma_Ixz : Real = 0.022566176940390956;
                                attribute Iyz : Real = 0.008060700605007121;
                                attribute sigma_Iyz : Real = 0.02209918015384651;
                            }
                        }
                        part <'C.1.2.1.3.2.3'> 'Subassembly 242' {
                            attribute POIconv : String = "-";
                            attribute Ipoint : Boolean = false;
                            attribute mass : Real = 1.6229139549075624;
                            attribute sigma_mass : Real = 0.5781874454998993;
                            attribute Cx : Real = 17.275570194886182;
                            attribute sigma_Cx : Real = 28.739693936862786;
                            attribute Cy : Real = 55.727707185318685;
                            attribute sigma_Cy : Real = 20.749305330295968;
                            attribute Cz : Real = 7.93886450274938;
                            attribute sigma_Cz : Real = 21.81640967140961;
                            attribute Ixx : Real = 1907.1408130970894;
                            attribute sigma_Ixx : Real = 2994.946097891086;
                            attribute Iyy : Real = 9218.442199926625;
                            attribute sigma_Iyy : Real = 5484.2868923178785;
                            attribute Izz : Real = 7655.617836811482;
                            attribute sigma_Izz : Real = 5211.576774839862;
                            attribute Ixy : Real = 801.1332760803264;
                            attribute sigma_Ixy : Real = 2307.532309690992;
                            attribute Ixz : Real = -3210.237107523966;
                            attribute sigma_Ixz : Real = 2581.1514268087376;
                            attribute Iyz : Real = 309.9569843929422;
                            attribute sigma_Iyz : Real = 1423.7972271038082;
                            part <'C.1.2.1.3.2.3.1'> 'Part 858' {
                                attribute POIconv : String = "-";
                                attribute Ipoint : Boolean = false;
                                attribute mass : Real = 0.00933534731529653;
                                attribute sigma_mass : Real = 0.28909372274994966;
                                attribute Cx : Real = -47.66736491583288;
                                attribute sigma_Cx : Real = 28.721044428837228;
                                attribute Cy : Real = -14.171905443072319;
                                attribute sigma_Cy : Real = 28.23690002309109;
                                attribute Cz : Real = 61.94947957992554;
                                attribute sigma_Cz : Real = 29.057750463592832;
                                attribute Ixx : Real = 0.012872223157351688;
                                attribute sigma_Ixx : Real = 0.37074144170588635;
                                attribute Iyy : Real = 0.011692039029950179;
                                attribute sigma_Iyy : Real = 0.3723953238821935;
                                attribute Izz : Real = 0.012112301882123434;
                                attribute sigma_Izz : Real = 0.37017423652493897;
                                attribute Ixy : Real = -0.00085968288171009;
                                attribute sigma_Ixy : Real = 0.02351283871158888;
                                attribute Ixz : Real = -0.0013162378460921578;
                                attribute sigma_Ixz : Real = 0.022566176940390956;
                                attribute Iyz : Real = 0.00023031250823094397;
                                attribute sigma_Iyz : Real = 0.02209918015384651;
                            }
                            part <'C.1.2.1.3.2.3.2'> 'Part 859' {
                                attribute POIconv : String = "-";
                                attribute Ipoint : Boolean = false;
                                attribute mass : Real = 0.4648861519698985;
                                attribute sigma_mass : Real = 0.28909372274994966;
                                attribute Cx : Real = 69.58614005707204;
                                attribute sigma_Cx : Real = 28.721044428837228;
                                attribute Cy : Real = 56.126068299636245;
                                attribute sigma_Cy : Real = 28.23690002309109;
                                attribute Cz : Real = 48.7769422121346;
                                attribute sigma_Cz : Real = 29.057750463592832;
                                attribute Ixx : Real = 0.5964410415207153;
                                attribute sigma_Ixx : Real = 0.37074144170588635;
                                attribute Iyy : Real = 0.4803773995355326;
                                attribute sigma_Iyy : Real = 0.3723953238821935;
                                attribute Izz : Real = 0.6377796703367564;
                                attribute sigma_Izz : Real = 0.37017423652493897;
                                attribute Ixy : Real = 0.003160270056478289;
                                attribute sigma_Ixy : Real = 0.02351283871158888;
                                attribute Ixz : Real = 0.019801128400824486;
                                attribute sigma_Ixz : Real = 0.022566176940390956;
                                attribute Iyz : Real = 0.005662558371979268;
                                attribute sigma_Iyz : Real = 0.02209918015384651;
                            }
                            part <'C.1.2.1.3.2.3.3'> 'Part 860' {
                                attribute POIconv : String = "-";
                                attribute Ipoint : Boolean = false;
                                attribute mass : Real = 0.5012732081627473;
                                attribute sigma_mass : Real = 0.28909372274994966;
                                attribute Cx : Real = 76.55848963186145;
                                attribute sigma_Cx : Real = 28.721044428837228;
                                attribute Cy : Real = 44.267522636801004;
                                attribute sigma_Cy : Real = 28.23690002309109;
                                attribute Cz : Real = 16.963543090969324;
                                attribute sigma_Cz : Real = 29.057750463592832;
                                attribute Ixx : Real = 0.6205684414365252;
                                attribute sigma_Ixx : Real = 0.37074144170588635;
                                attribute Iyy : Real = 0.6257512516446063;
                                attribute sigma_Iyy : Real = 0.3723953238821935;
                                attribute Izz : Real = 0.6233369809397908;
                                attribute sigma_Izz : Real = 0.37017423652493897;
                                attribute Ixy : Real = 0.0028794879059003088;
                                attribute sigma_Ixy : Real = 0.02351283871158888;
                                attribute Ixz : Real = -0.003101390170643961;
                                attribute sigma_Ixz : Real = 0.022566176940390956;
                                attribute Iyz : Real = 0.0004958489557705843;
                                attribute sigma_Iyz : Real = 0.02209918015384651;
                            }
                            part <'C.1.2.1.3.2.3.4'> 'Part 861' {
                                attribute POIconv : String = "-";
                                attribute Ipoint : Boolean = false;
                                attribute mass : Real = 0.6474192474596202;
                                attribute sigma_mass : Real = 0.28909372274994966;
                                attribute Cx : Real = -65.2507589198649;
                                attribute sigma_Cx : Real = 28.721044428837228;
                                attribute Cy : Real = 65.32276957295835;
                                attribute sigma_Cy : Real = 28.23690002309109;
                                attribute Cz : Real = -29.151621041819453;
                                attribute sigma_Cz : Real = 29.057750463592832;
                                attribute Ixx : Real = 0.7558995706929647;
                                attribute sigma_Ixx : Real = 0.37074144170588635;
                                attribute Iyy : Real = 0.7928488191668013;
                                attribute sigma_Iyy : Real = 0.3723953238821935;
                                attribute Izz : Real = 0.7165132914075537;
                                attribute sigma_Izz : Real = 0.37017423652493897;
                                attribute Ixy : Real = -0.024177475921984385;
                                attribute sigma_Ixy : Real = 0.02351283871158888;
                                attribute Ixz : Real = 0.020254634278347613;
                                attribute sigma_Ixz : Real = 0.022566176940390956;
                                attribute Iyz : Real = 0.01851132812549184;
                                attribute sigma_Iyz : Real = 0.02209918015384651;
                            }
                        }
                        part <'C.1.2.1.3.2.4'> 'Subassembly 243' {
                            attribute POIconv : String = "-";
                            attribute Ipoint : Boolean = false;
                            attribute mass : Real = 1.4099292425618042;
                            attribute sigma_mass : Real = 0.40884026350990615;
                            attribute Cx : Real = 13.90483996309208;
                            attribute sigma_Cx : Real = 22.871512220155246;
                            attribute Cy : Real = 22.806717694890622;
                            attribute sigma_Cy : Real = 24.426867058722664;
                            attribute Cz : Real = -44.740762071344214;
                            attribute sigma_Cz : Real = 22.649205865650273;
                            attribute Ixx : Real = 1743.572768446439;
                            attribute sigma_Ixx : Real = 2008.1755881851768;
                            attribute Iyy : Real = 681.691208011069;
                            attribute sigma_Iyy : Real = 1198.075270390512;
                            attribute Izz : Real = 1998.0082142617412;
                            attribute sigma_Izz : Real = 2180.5564265959033;
                            attribute Ixy : Real = 845.3862056231452;
                            attribute sigma_Ixy : Real = 1065.0373149464433;
                            attribute Ixz : Real = 315.23868388212685;
                            attribute sigma_Ixz : Real = 598.0160801268256;
                            attribute Iyz : Real = -570.088425652902;
                            attribute sigma_Iyz : Real = 966.6539784987212;
                            part <'C.1.2.1.3.2.4.1'> 'Part 862' {
                                attribute POIconv : String = "+";
                                attribute Ipoint : Boolean = false;
                                attribute mass : Real = 0.4121293020050507;
                                attribute sigma_mass : Real = 0.28909372274994966;
                                attribute Cx : Real = -14.421700173988938;
                                attribute sigma_Cx : Real = 28.721044428837228;
                                attribute Cy : Real = 74.04830218292773;
                                attribute sigma_Cy : Real = 28.23690002309109;
                                attribute Cz : Real = -25.63537247478962;
                                attribute sigma_Cz : Real = 29.057750463592832;
                                attribute Ixx : Real = 0.538959382654313;
                                attribute sigma_Ixx : Real = 0.37074144170588635;
                                attribute Iyy : Real = 0.5400639859835994;
                                attribute sigma_Iyy : Real = 0.3723953238821935;
                                attribute Izz : Real = 0.4226073905186561;
                                attribute sigma_Izz : Real = 0.37017423652493897;
                                attribute Ixy : Real = 0.0015989473031791206;
                                attribute sigma_Ixy : Real = 0.02351283871158888;
                                attribute Ixz : Real = 0.0019416072073452939;
                                attribute sigma_Ixz : Real = 0.022566176940390956;
                                attribute Iyz : Real = 0.0017356833858610727;
                                attribute sigma_Iyz : Real = 0.02209918015384651;
                            }
                            part <'C.1.2.1.3.2.4.2'> 'Part 863' {
                                attribute POIconv : String = "+";
                                attribute Ipoint : Boolean = false;
                                attribute mass : Real = 0.9977999405567535;
                                attribute sigma_mass : Real = 0.28909372274994966;
                                attribute Cx : Real = 25.604777736589313;
                                attribute sigma_Cx : Real = 28.721044428837228;
                                attribute Cy : Real = 1.6419955994933844;
                                attribute sigma_Cy : Real = 28.23690002309109;
                                attribute Cz : Real = -52.63201417401433;
                                attribute sigma_Cz : Real = 29.057750463592832;
                                attribute Ixx : Real = 1.3773431124218019;
                                attribute sigma_Ixx : Real = 0.37074144170588635;
                                attribute Iyy : Real = 1.3055362404790645;
                                attribute sigma_Iyy : Real = 0.3723953238821935;
                                attribute Izz : Real = 1.2207548115469578;
                                attribute sigma_Izz : Real = 0.37017423652493897;
                                attribute Ixy : Real = -0.10230191196398598;
                                attribute sigma_Ixy : Real = 0.02351283871158888;
                                attribute Ixz : Real = -0.07650615223409113;
                                attribute sigma_Ixz : Real = 0.022566176940390956;
                                attribute Iyz : Real = -0.03266701715737544;
                                attribute sigma_Iyz : Real = 0.02209918015384651;
                            }
                        }
                        part <'C.1.2.1.3.2.5'> 'Subassembly 244' {
                            attribute POIconv : String = "-";
                            attribute Ipoint : Boolean = false;
                            attribute mass : Real = 1.8200045135486873;
                            attribute sigma_mass : Real = 0.6464332159373649;
                            attribute Cx : Real = 83.8552842379113;
                            attribute sigma_Cx : Real = 20.88150764661123;
                            attribute Cy : Real = -64.53055212239343;
                            attribute sigma_Cy : Real = 36.83461957041515;
                            attribute Cz : Real = 49.497308010424426;
                            attribute sigma_Cz : Real = 21.548347280144373;
                            attribute Ixx : Real = 2560.1157079357436;
                            attribute sigma_Ixx : Real = 8651.647678168238;
                            attribute Iyy : Real = 1909.1406053210458;
                            attribute sigma_Iyy : Real = 2244.3856206478995;
                            attribute Izz : Real = 3129.954732773771;
                            attribute sigma_Izz : Real = 8214.472633029287;
                            attribute Ixy : Real = 1089.7589542401;
                            attribute sigma_Ixy : Real = 1348.5048365059838;
                            attribute Ixz : Real = -732.6585250677476;
                            attribute sigma_Ixz : Real = 1004.408964096311;
                            attribute Iyz : Real = 1040.0120048863735;
                            attribute sigma_Iyz : Real = 2453.5947676724;
                            part <'C.1.2.1.3.2.5.1'> 'Part 864' {
                                attribute POIconv : String = "-";
                                attribute Ipoint : Boolean = false;
                                attribute mass : Real = 0.5356775743139442;
                                attribute sigma_mass : Real = 0.28909372274994966;
                                attribute Cx : Real = 95.3914912417531;
                                attribute sigma_Cx : Real = 28.721044428837228;
                                attribute Cy : Real = -94.64962691999972;
                                attribute sigma_Cy : Real = 28.23690002309109;
                                attribute Cz : Real = 70.65375722013414;
                                attribute sigma_Cz : Real = 29.057750463592832;
                                attribute Ixx : Real = 0.5065910577528606;
                                attribute sigma_Ixx : Real = 0.37074144170588635;
                                attribute Iyy : Real = 0.6666737058866342;
                                attribute sigma_Iyy : Real = 0.3723953238821935;
                                attribute Izz : Real = 0.6209295219931377;
                                attribute sigma_Izz : Real = 0.37017423652493897;
                                attribute Ixy : Real = 0.013106678148177375;
                                attribute sigma_Ixy : Real = 0.02351283871158888;
                                attribute Ixz : Real = -0.06445713535372527;
                                attribute sigma_Ixz : Real = 0.022566176940390956;
                                attribute Iyz : Real = 0.009277910904441102;
                                attribute sigma_Iyz : Real = 0.02209918015384651;
                            }
                            part <'C.1.2.1.3.2.5.2'> 'Part 865' {
                                attribute POIconv : String = "-";
                                attribute Ipoint : Boolean = false;
                                attribute mass : Real = 0.9789306758067104;
                                attribute sigma_mass : Real = 0.28909372274994966;
                                attribute Cx : Real = 94.38720103353262;
                                attribute sigma_Cx : Real = 28.721044428837228;
                                attribute Cy : Real = -67.743732733652;
                                attribute sigma_Cy : Real = 28.23690002309109;
                                attribute Cz : Real = 49.35169564560056;
                                attribute sigma_Cz : Real = 29.057750463592832;
                                attribute Ixx : Real = 1.1316552003076614;
                                attribute sigma_Ixx : Real = 0.37074144170588635;
                                attribute Iyy : Real = 1.2492147928009492;
                                attribute sigma_Iyy : Real = 0.3723953238821935;
                                attribute Izz : Real = 1.0228918812757202;
                                attribute sigma_Izz : Real = 0.37017423652493897;
                                attribute Ixy : Real = -0.028851869426001063;
                                attribute sigma_Ixy : Real = 0.02351283871158888;
                                attribute Ixz : Real = 0.07290580738775347;
                                attribute sigma_Ixz : Real = 0.022566176940390956;
                                attribute Iyz : Real = -0.07001034554191826;
                                attribute sigma_Iyz : Real = 0.02209918015384651;
                            }
                            part <'C.1.2.1.3.2.5.3'> 'Part 866' {
                                attribute POIconv : String = "+";
                                attribute Ipoint : Boolean = false;
                                attribute mass : Real = 0.2665159461244475;
                                attribute sigma_mass : Real = 0.28909372274994966;
                                attribute Cx : Real = 20.90835776180029;
                                attribute sigma_Cx : Real = 28.721044428837228;
                                attribute Cy : Real = -10.535001801326871;
                                attribute sigma_Cy : Real = 28.23690002309109;
                                attribute Cz : Real = 12.772182933986187;
                                attribute sigma_Cz : Real = 29.057750463592832;
                                attribute Ixx : Real = 0.34417945419279855;
                                attribute sigma_Ixx : Real = 0.37074144170588635;
                                attribute Iyy : Real = 0.35010805416529395;
                                attribute sigma_Iyy : Real = 0.3723953238821935;
                                attribute Izz : Real = 0.3961672255533621;
                                attribute sigma_Izz : Real = 0.37017423652493897;
                                attribute Ixy : Real = 0.00011508781543481677;
                                attribute sigma_Ixy : Real = 0.02351283871158888;
                                attribute Ixz : Real = 0.0004253799259685243;
                                attribute sigma_Ixz : Real = 0.022566176940390956;
                                attribute Iyz : Real = -0.0029131415057917854;
                                attribute sigma_Iyz : Real = 0.02209918015384651;
                            }
                            part <'C.1.2.1.3.2.5.4'> 'Part 867' {
                                attribute POIconv : String = "+";
                                attribute Ipoint : Boolean = false;
                                attribute mass : Real = 0.0030841485098935663;
                                attribute sigma_mass : Real = 0.28909372274994966;
                                attribute Cx : Real = 81.85773957520723;
                                attribute sigma_Cx : Real = 28.721044428837228;
                                attribute Cy : Real = 83.96136229857802;
                                attribute sigma_Cy : Real = 28.23690002309109;
                                attribute Cz : Real = 88.07933288626373;
                                attribute sigma_Cz : Real = 29.057750463592832;
                                attribute Ixx : Real = 0.003597133464721806;
                                attribute sigma_Ixx : Real = 0.37074144170588635;
                                attribute Iyy : Real = 0.003748139705033749;
                                attribute sigma_Iyy : Real = 0.3723953238821935;
                                attribute Izz : Real = 0.0040511232916386;
                                attribute sigma_Izz : Real = 0.37017423652493897;
                                attribute Ixy : Real = 4.35008819557647e-05;
                                attribute sigma_Ixy : Real = 0.02351283871158888;
                                attribute Ixz : Real = 4.662714983698157e-05;
                                attribute sigma_Ixz : Real = 0.022566176940390956;
                                attribute Iyz : Real = -0.00032771128475900236;
                                attribute sigma_Iyz : Real = 0.02209918015384651;
                            }
                            part <'C.1.2.1.3.2.5.5'> 'Part 868' {
                                attribute POIconv : String = "+";
                                attribute Ipoint : Boolean = false;
                                attribute mass : Real = 0.035796168793691324;
                                attribute sigma_mass : Real = 0.28909372274994966;
                                attribute Cx : Real = 92.03539369627833;
                                attribute sigma_Cx : Real = 28.721044428837228;
                                attribute Cy : Real = 59.25218351185322;
                                attribute sigma_Cy : Real = 28.23690002309109;
                                attribute Cz : Real = 6.988506857305765;
                                attribute sigma_Cz : Real = 29.057750463592832;
                                attribute Ixx : Real = 0.044401768379264066;
                                attribute sigma_Ixx : Real = 0.37074144170588635;
                                attribute Iyy : Real = 0.04714700625441354;
                                attribute sigma_Iyy : Real = 0.3723953238821935;
                                attribute Izz : Real = 0.04463445237186242;
                                attribute sigma_Izz : Real = 0.37017423652493897;
                                attribute Ixy : Real = -0.00249347545891977;
                                attribute sigma_Ixy : Real = 0.02351283871158888;
                                attribute Ixz : Real = -0.001406768059127789;
                                attribute sigma_Ixz : Real = 0.022566176940390956;
                                attribute Iyz : Real = -0.002809141600363138;
                                attribute sigma_Iyz : Real = 0.02209918015384651;
                            }
                        }
                    }
                }
                part <'C.1.2.1.4'> 'Subsystem 19' {
                    attribute POIconv : String = "-";
                    attribute Ipoint : Boolean = false;
                    attribute mass : Real = 23.83098124597548;
                    attribute sigma_mass : Real = 1.960729023740287;
                    attribute Cx : Real = 0.6582123773076003;
                    attribute sigma_Cx : Real = 7.0548772084635;
                    attribute Cy : Real = 12.682302479715474;
                    attribute sigma_Cy : Real = 6.811922022467333;
                    attribute Cz : Real = 3.4811510404587294;
                    attribute sigma_Cz : Real = 7.166067088984612;
                    attribute Ixx : Real = 144854.8244506546;
                    attribute sigma_Ixx : Real = 24161.895404981333;
                    attribute Iyy : Real = 158401.5303504495;
                    attribute sigma_Iyy : Real = 25088.127368791567;
                    attribute Izz : Real = 148515.93253028565;
                    attribute sigma_Izz : Real = 23523.09190904202;
                    attribute Ixy : Real = -5043.200834170149;
                    attribute sigma_Ixy : Real = 11557.961128345225;
                    attribute Ixz : Real = 11589.495131165138;
                    attribute sigma_Ixz : Real = 12262.935170527815;
                    attribute Iyz : Real = -240.3560399778935;
                    attribute sigma_Iyz : Real = 11836.645440783965;
                    part <'C.1.2.1.4.1'> 'Assembly 70' {
                        attribute POIconv : String = "-";
                        attribute Ipoint : Boolean = false;
                        attribute mass : Real = 4.4195060484020505;
                        attribute sigma_mass : Real = 0.7648700959862225;
                        attribute Cx : Real = -11.657212901492894;
                        attribute sigma_Cx : Real = 16.043901338892862;
                        attribute Cy : Real = 44.02368704424483;
                        attribute sigma_Cy : Real = 13.422643561915036;
                        attribute Cz : Real = 29.041366581124038;
                        attribute sigma_Cz : Real = 15.078621505891599;
                        attribute Ixx : Real = 14636.769712281688;
                        attribute sigma_Ixx : Real = 6915.782946531758;
                        attribute Iyy : Real = 22873.61897025906;
                        attribute sigma_Iyy : Real = 9197.546927177216;
                        attribute Izz : Real = 23188.228727544643;
                        attribute sigma_Izz : Real = 8574.608203709538;
                        attribute Ixy : Real = -3678.4072543070615;
                        attribute sigma_Ixy : Real = 3993.788705350255;
                        attribute Ixz : Real = -405.60488346872893;
                        attribute sigma_Ixz : Real = 4673.86500570238;
                        attribute Iyz : Real = -1761.9302158894968;
                        attribute sigma_Iyz : Real = 3100.427047785865;
                        part <'C.1.2.1.4.1.1'> 'Subassembly 245' {
                            attribute POIconv : String = "-";
                            attribute Ipoint : Boolean = false;
                            attribute mass : Real = 1.1050177654705475;
                            attribute sigma_mass : Real = 0.40884026350990615;
                            attribute Cx : Real = 58.41402381282766;
                            attribute sigma_Cx : Real = 23.567265078124205;
                            attribute Cy : Real = 80.10380122615605;
                            attribute sigma_Cy : Real = 23.238775292295152;
                            attribute Cz : Real = 25.53800061010521;
                            attribute sigma_Cz : Real = 38.60402338349189;
                            attribute Ixx : Real = 4761.123572160082;
                            attribute sigma_Ixx : Real = 4610.68546702164;
                            attribute Iyy : Real = 4751.622094393267;
                            attribute sigma_Iyy : Real = 4603.96968832194;
                            attribute Izz : Real = 361.91822979427593;
                            attribute sigma_Izz : Real = 751.0193944407209;
                            attribute Ixy : Real = 180.31536559904777;
                            attribute sigma_Ixy : Real = 375.6315943203719;
                            attribute Ixz : Real = 896.2341146693481;
                            attribute sigma_Ixz : Real = 1459.367017842;
                            attribute Iyz : Real = -919.772587729766;
                            attribute sigma_Iyz : Real = 1452.2167521445126;
                            part <'C.1.2.1.4.1.1.1'> 'Part 869' {
                                attribute POIconv : String = "+";
                                attribute Ipoint : Boolean = false;
                                attribute mass : Real = 0.27223217856604603;
                                attribute sigma_mass : Real = 0.28909372274994966;
                                attribute Cx : Real = 80.46283801086247;
                                attribute sigma_Cx : Real = 28.721044428837228;
                                attribute Cy : Real = 57.47569045051932;
                                attribute sigma_Cy : Real = 28.23690002309109;
                                attribute Cz : Real = -86.99930654838681;
                                attribute sigma_Cz : Real = 29.057750463592832;
                                attribute Ixx : Real = 0.3961942194821377;
                                attribute sigma_Ixx : Real = 0.37074144170588635;
                                attribute Iyy : Real = 0.34880401745538203;
                                attribute sigma_Iyy : Real = 0.3723953238821935;
                                attribute Izz : Real = 0.3581649715034036;
                                attribute sigma_Izz : Real = 0.37017423652493897;
                                attribute Ixy : Real = -0.01663236375212988;
                                attribute sigma_Ixy : Real = 0.02351283871158888;
                                attribute Ixz : Real = 0.027185724562474915;
                                attribute sigma_Ixz : Real = 0.022566176940390956;
                                attribute Iyz : Real = 0.0040272209932980165;
                                attribute sigma_Iyz : Real = 0.02209918015384651;
                            }
                            part <'C.1.2.1.4.1.1.2'> 'Part 870' {
                                attribute POIconv : String = "-";
                                attribute Ipoint : Boolean = false;
                                attribute mass : Real = 0.8327855869045016;
                                attribute sigma_mass : Real = 0.28909372274994966;
                                attribute Cx : Real = 51.206410210579634;
                                attribute sigma_Cx : Real = 28.721044428837228;
                                attribute Cy : Real = 87.50078310258687;
                                attribute sigma_Cy : Real = 28.23690002309109;
                                attribute Cz : Real = 62.32571257278323;
                                attribute sigma_Cz : Real = 29.057750463592832;
                                attribute Ixx : Real = 1.0072639413371467;
                                attribute sigma_Ixx : Real = 0.37074144170588635;
                                attribute Iyy : Real = 0.9020600361509343;
                                attribute sigma_Iyy : Real = 0.3723953238821935;
                                attribute Izz : Real = 0.993808398604382;
                                attribute sigma_Izz : Real = 0.37017423652493897;
                                attribute Ixy : Real = 0.07621546486115519;
                                attribute sigma_Ixy : Real = 0.02351283871158888;
                                attribute Ixz : Real = -0.046705179633531935;
                                attribute sigma_Ixz : Real = 0.022566176940390956;
                                attribute Iyz : Real = 0.08847384438793632;
                                attribute sigma_Iyz : Real = 0.02209918015384651;
                            }
                        }
                        part <'C.1.2.1.4.1.2'> 'Subassembly 246' {
                            attribute POIconv : String = "-";
                            attribute Ipoint : Boolean = false;
                            attribute mass : Real = 1.7162988954770846;
                            attribute sigma_mass : Real = 0.5007250159521434;
                            attribute Cx : Real = -6.089862759634571;
                            attribute sigma_Cx : Real = 25.22438827887967;
                            attribute Cy : Real = 52.70979361468894;
                            attribute sigma_Cy : Real = 21.341417413947998;
                            attribute Cz : Real = 25.918077700795283;
                            attribute sigma_Cz : Real = 22.328968461568937;
                            attribute Ixx : Real = 5760.684179252831;
                            attribute sigma_Ixx : Real = 3910.256442547341;
                            attribute Iyy : Real = 6968.533272943628;
                            attribute sigma_Iyy : Real = 5300.196800388728;
                            attribute Izz : Real = 8269.659522990922;
                            attribute sigma_Izz : Real = 5018.2776436607155;
                            attribute Ixy : Real = 1572.247691996349;
                            attribute sigma_Ixy : Real = 2170.93647132992;
                            attribute Ixz : Real = -1707.8175815971795;
                            attribute sigma_Ixz : Real = 2586.802230232626;
                            attribute Iyz : Real = -1636.0315294469094;
                            attribute sigma_Iyz : Real = 1799.048872180451;
                            part <'C.1.2.1.4.1.2.1'> 'Part 871' {
                                attribute POIconv : String = "-";
                                attribute Ipoint : Boolean = false;
                                attribute mass : Real = 0.2949817116728518;
                                attribute sigma_mass : Real = 0.28909372274994966;
                                attribute Cx : Real = 86.81539348326623;
                                attribute sigma_Cx : Real = 28.721044428837228;
                                attribute Cy : Real = 76.32933091372252;
                                attribute sigma_Cy : Real = 28.23690002309109;
                                attribute Cz : Real = 99.27633125334978;
                                attribute sigma_Cz : Real = 29.057750463592832;
                                attribute Ixx : Real = 0.34408543131221214;
                                attribute sigma_Ixx : Real = 0.37074144170588635;
                                attribute Iyy : Real = 0.4071461575395191;
                                attribute sigma_Iyy : Real = 0.3723953238821935;
                                attribute Izz : Real = 0.35501415697126604;
                                attribute sigma_Izz : Real = 0.37017423652493897;
                                attribute Ixy : Real = 0.0134424292994893;
                                attribute sigma_Ixy : Real = 0.02351283871158888;
                                attribute Ixz : Real = -0.0034219645196100993;
                                attribute sigma_Ixz : Real = 0.022566176940390956;
                                attribute Iyz : Real = -0.01589020465438252;
                                attribute sigma_Iyz : Real = 0.02209918015384651;
                            }
                            part <'C.1.2.1.4.1.2.2'> 'Part 872' {
                                attribute POIconv : String = "+";
                                attribute Ipoint : Boolean = false;
                                attribute mass : Real = 0.7826816371108871;
                                attribute sigma_mass : Real = 0.28909372274994966;
                                attribute Cx : Real = -56.27164328470826;
                                attribute sigma_Cx : Real = 28.721044428837228;
                                attribute Cy : Real = 91.53945492580533;
                                attribute sigma_Cy : Real = 28.23690002309109;
                                attribute Cz : Real = 24.067642632871866;
                                attribute sigma_Cz : Real = 29.057750463592832;
                                attribute Ixx : Real = 0.9778478964809706;
                                attribute sigma_Ixx : Real = 0.37074144170588635;
                                attribute Iyy : Real = 0.9496995845322196;
                                attribute sigma_Iyy : Real = 0.3723953238821935;
                                attribute Izz : Real = 0.6957101008845437;
                                attribute sigma_Izz : Real = 0.37017423652493897;
                                attribute Ixy : Real = 0.0023040540404262056;
                                attribute sigma_Ixy : Real = 0.02351283871158888;
                                attribute Ixz : Real = 0.039310745442766484;
                                attribute sigma_Ixz : Real = 0.022566176940390956;
                                attribute Iyz : Real = 0.01361643285858351;
                                attribute sigma_Iyz : Real = 0.02209918015384651;
                            }
                            part <'C.1.2.1.4.1.2.3'> 'Part 873' {
                                attribute POIconv : String = "+";
                                attribute Ipoint : Boolean = false;
                                attribute mass : Real = 0.6386355466933455;
                                attribute sigma_mass : Real = 0.28909372274994966;
                                attribute Cx : Real = 12.498214095830917;
                                attribute sigma_Cx : Real = 28.721044428837228;
                                attribute Cy : Real = -5.787724442780018;
                                attribute sigma_Cy : Real = 28.23690002309109;
                                attribute Cz : Real = -5.697828670963645;
                                attribute sigma_Cz : Real = 29.057750463592832;
                                attribute Ixx : Real = 0.8671067831517091;
                                attribute sigma_Ixx : Real = 0.37074144170588635;
                                attribute Iyy : Real = 0.9959601496049392;
                                attribute sigma_Iyy : Real = 0.3723953238821935;
                                attribute Izz : Real = 0.8581832902650786;
                                attribute sigma_Izz : Real = 0.37017423652493897;
                                attribute Ixy : Real = -0.02616752523860597;
                                attribute sigma_Ixy : Real = 0.02351283871158888;
                                attribute Ixz : Real = 0.0004076729359052414;
                                attribute sigma_Ixz : Real = 0.022566176940390956;
                                attribute Iyz : Real = 0.0019840933129517506;
                                attribute sigma_Iyz : Real = 0.02209918015384651;
                            }
                        }
                        part <'C.1.2.1.4.1.3'> 'Subassembly 247' {
                            attribute POIconv : String = "-";
                            attribute Ipoint : Boolean = false;
                            attribute mass : Real = 1.5981893874544184;
                            attribute sigma_mass : Real = 0.40884026350990615;
                            attribute Cx : Real = -66.08455361583161;
                            attribute sigma_Cx : Real = 21.233543105949117;
                            attribute Cy : Real = 9.749199493482326;
                            attribute sigma_Cy : Real = 20.611497725236212;
                            attribute Cz : Real = 34.81776515125168;
                            attribute sigma_Cz : Real = 21.14893488704114;
                            attribute Ixx : Real = 585.8966435345199;
                            attribute sigma_Ixx : Real = 1228.2132209143756;
                            attribute Iyy : Real = 856.648740005861;
                            attribute sigma_Iyy : Real = 1503.0036389520099;
                            attribute Izz : Real = 898.0334589421627;
                            attribute sigma_Izz : Real = 1525.81575559429;
                            attribute Ixy : Real = 427.0824399830485;
                            attribute sigma_Ixy : Real = 758.1080768381495;
                            attribute Ixz : Real = -397.5918488462862;
                            attribute sigma_Ixz : Real = 753.2818456381834;
                            attribute Iyz : Real = 291.22127664247284;
                            attribute sigma_Iyz : Real = 615.3072129534725;
                            part <'C.1.2.1.4.1.3.1'> 'Part 874' {
                                attribute POIconv : String = "+";
                                attribute Ipoint : Boolean = false;
                                attribute mass : Real = 0.9408222606582567;
                                attribute sigma_mass : Real = 0.28909372274994966;
                                attribute Cx : Real = -82.05497930757701;
                                attribute sigma_Cx : Real = 28.721044428837228;
                                attribute Cy : Real = 21.43986476585269;
                                attribute sigma_Cy : Real = 28.23690002309109;
                                attribute Cz : Real = 23.9314301405102;
                                attribute sigma_Cz : Real = 29.057750463592832;
                                attribute Ixx : Real = 1.3638283437191279;
                                attribute sigma_Ixx : Real = 0.37074144170588635;
                                attribute Iyy : Real = 1.2896698188481333;
                                attribute sigma_Iyy : Real = 0.3723953238821935;
                                attribute Izz : Real = 1.1927794239794551;
                                attribute sigma_Izz : Real = 0.37017423652493897;
                                attribute Ixy : Real = -0.08440370084619134;
                                attribute sigma_Ixy : Real = 0.02351283871158888;
                                attribute Ixz : Real = -0.0765637423114574;
                                attribute sigma_Ixz : Real = 0.022566176940390956;
                                attribute Iyz : Real = -0.03919185966259717;
                                attribute sigma_Iyz : Real = 0.02209918015384651;
                            }
                            part <'C.1.2.1.4.1.3.2'> 'Part 875' {
                                attribute POIconv : String = "-";
                                attribute Ipoint : Boolean = false;
                                attribute mass : Real = 0.6573671267961617;
                                attribute sigma_mass : Real = 0.28909372274994966;
                                attribute Cx : Real = -43.227718537673354;
                                attribute sigma_Cx : Real = 28.721044428837228;
                                attribute Cy : Real = -6.98245270177722;
                                attribute sigma_Cy : Real = 28.23690002309109;
                                attribute Cz : Real = 50.39826179854572;
                                attribute sigma_Cz : Real = 29.057750463592832;
                                attribute Ixx : Real = 0.844242415430575;
                                attribute sigma_Ixx : Real = 0.37074144170588635;
                                attribute Iyy : Real = 0.8904826876670747;
                                attribute sigma_Iyy : Real = 0.3723953238821935;
                                attribute Izz : Real = 0.8357265737891564;
                                attribute sigma_Izz : Real = 0.37017423652493897;
                                attribute Ixy : Real = -0.056719963109132895;
                                attribute sigma_Ixy : Real = 0.02351283871158888;
                                attribute Ixz : Real = 0.004520140436816887;
                                attribute sigma_Ixz : Real = 0.022566176940390956;
                                attribute Iyz : Real = 0.07768755813589966;
                                attribute sigma_Iyz : Real = 0.02209918015384651;
                            }
                        }
                    }
                    part <'C.1.2.1.4.2'> 'Assembly 71' {
                        attribute POIconv : String = "-";
                        attribute Ipoint : Boolean = false;
                        attribute mass : Real = 3.6752851213405373;
                        attribute sigma_mass : Real = 0.8672811682498489;
                        attribute Cx : Real = -4.374218688684126;
                        attribute sigma_Cx : Real = 19.54218865838233;
                        attribute Cy : Real = -14.698211192901924;
                        attribute sigma_Cy : Real = 14.815016088409903;
                        attribute Cz : Real = -10.757297378932742;
                        attribute sigma_Cz : Real = 17.86806034933769;
                        attribute Ixx : Real = 16356.832270301262;
                        attribute sigma_Ixx : Real = 7736.286063972844;
                        attribute Iyy : Real = 24366.13172250597;
                        attribute sigma_Iyy : Real = 9756.263986085209;
                        attribute Izz : Real = 19630.444339672227;
                        attribute sigma_Izz : Real = 8196.306535319121;
                        attribute Ixy : Real = -2525.553023554751;
                        attribute sigma_Ixy : Real = 3925.63699718916;
                        attribute Ixz : Real = -5160.927295064665;
                        attribute sigma_Ixz : Real = 4754.5307788865275;
                        attribute Iyz : Real = -4534.52565001109;
                        attribute sigma_Iyz : Real = 3632.4880124060564;
                        part <'C.1.2.1.4.2.1'> 'Subassembly 248' {
                            attribute POIconv : String = "-";
                            attribute Ipoint : Boolean = false;
                            attribute mass : Real = 1.3133947800062598;
                            attribute sigma_mass : Real = 0.40884026350990615;
                            attribute Cx : Real = -28.80786956887845;
                            attribute sigma_Cx : Real = 25.880813781291536;
                            attribute Cy : Real = -16.884945114439358;
                            attribute sigma_Cy : Real = 23.293153486082605;
                            attribute Cz : Real = 10.082701418904671;
                            attribute sigma_Cz : Real = 27.36667137384839;
                            attribute Ixx : Real = 2451.1641058264377;
                            attribute sigma_Ixx : Real = 2547.790760932772;
                            attribute Iyy : Real = 3397.0242371919658;
                            attribute sigma_Iyy : Real = 3201.362976076653;
                            attribute Izz : Real = 1875.384939416179;
                            attribute sigma_Izz : Real = 2116.64730909788;
                            attribute Ixy : Real = 808.5942274859046;
                            attribute sigma_Ixy : Real = 1009.97808711243;
                            attribute Ixz : Real = 1673.0621728259916;
                            attribute sigma_Ixz : Real = 1588.8109978340472;
                            attribute Iyz : Real = -959.6542344374611;
                            attribute sigma_Iyz : Real = 1167.000762705173;
                            part <'C.1.2.1.4.2.1.1'> 'Part 876' {
                                attribute POIconv : String = "-";
                                attribute Ipoint : Boolean = false;
                                attribute mass : Real = 0.3450348290752154;
                                attribute sigma_mass : Real = 0.28909372274994966;
                                attribute Cx : Real = 26.07601834461093;
                                attribute sigma_Cx : Real = 28.721044428837228;
                                attribute Cy : Real = -48.367415415123105;
                                attribute sigma_Cy : Real = 28.23690002309109;
                                attribute Cz : Real = -55.055674351751804;
                                attribute sigma_Cz : Real = 29.057750463592832;
                                attribute Ixx : Real = 0.40830853274365597;
                                attribute sigma_Ixx : Real = 0.37074144170588635;
                                attribute Iyy : Real = 0.40658366946626634;
                                attribute sigma_Iyy : Real = 0.3723953238821935;
                                attribute Izz : Real = 0.5182531799146531;
                                attribute sigma_Izz : Real = 0.37017423652493897;
                                attribute Ixy : Real = -0.0004167074262375955;
                                attribute sigma_Ixy : Real = 0.02351283871158888;
                                attribute Ixz : Real = -0.013953812759018238;
                                attribute sigma_Ixz : Real = 0.022566176940390956;
                                attribute Iyz : Real = 0.003962769157415912;
                                attribute sigma_Iyz : Real = 0.02209918015384651;
                            }
                            part <'C.1.2.1.4.2.1.2'> 'Part 877' {
                                attribute POIconv : String = "+";
                                attribute Ipoint : Boolean = false;
                                attribute mass : Real = 0.9683599509310443;
                                attribute sigma_mass : Real = 0.28909372274994966;
                                attribute Cx : Real = -48.36346236988902;
                                attribute sigma_Cx : Real = 28.721044428837228;
                                attribute Cy : Real = -5.667475052177906;
                                attribute sigma_Cy : Real = 28.23690002309109;
                                attribute Cz : Real = 33.29205485060811;
                                attribute sigma_Cz : Real = 29.057750463592832;
                                attribute Ixx : Real = 1.3096615421195466;
                                attribute sigma_Ixx : Real = 0.37074144170588635;
                                attribute Iyy : Real = 1.3522068302386205;
                                attribute sigma_Iyy : Real = 0.3723953238821935;
                                attribute Izz : Real = 1.3870068925175236;
                                attribute sigma_Izz : Real = 0.37017423652493897;
                                attribute Ixy : Real = 0.007844667177271513;
                                attribute sigma_Ixy : Real = 0.02351283871158888;
                                attribute Ixz : Real = -0.04817599092855786;
                                attribute sigma_Ixz : Real = 0.022566176940390956;
                                attribute Iyz : Real = -0.023319006418379376;
                                attribute sigma_Iyz : Real = 0.02209918015384651;
                            }
                        }
                        part <'C.1.2.1.4.2.2'> 'Subassembly 249' {
                            attribute POIconv : String = "-";
                            attribute Ipoint : Boolean = false;
                            attribute mass : Real = 1.5014131515964402;
                            attribute sigma_mass : Real = 0.5781874454998993;
                            attribute Cx : Real = -27.70727555382631;
                            attribute sigma_Cx : Real = 28.91045960314836;
                            attribute Cy : Real = -5.784846550073736;
                            attribute sigma_Cy : Real = 24.362204641717465;
                            attribute Cz : Real = -40.429435258483274;
                            attribute sigma_Cz : Real = 29.739299316294318;
                            attribute Ixx : Real = 9519.851221522105;
                            attribute sigma_Ixx : Real = 6167.760108805537;
                            attribute Iyy : Real = 11265.528129268423;
                            attribute sigma_Iyy : Real = 6917.400812157756;
                            attribute Izz : Real = 9293.637968960344;
                            attribute sigma_Izz : Real = 5927.9536385554975;
                            attribute Ixy : Real = -4142.499670673285;
                            attribute sigma_Ixy : Real = 2897.828552781678;
                            attribute Ixz : Real = -5000.413947769135;
                            attribute sigma_Ixz : Real = 3395.4300293003757;
                            attribute Iyz : Real = -3500.608442782811;
                            attribute sigma_Iyz : Real = 2965.3500089766035;
                            part <'C.1.2.1.4.2.2.1'> 'Part 878' {
                                attribute POIconv : String = "+";
                                attribute Ipoint : Boolean = false;
                                attribute mass : Real = 0.32665915898117237;
                                attribute sigma_mass : Real = 0.28909372274994966;
                                attribute Cx : Real = 59.33857928030193;
                                attribute sigma_Cx : Real = 28.721044428837228;
                                attribute Cy : Real = 75.91856541112065;
                                attribute sigma_Cy : Real = 28.23690002309109;
                                attribute Cz : Real = 58.514846256002784;
                                attribute sigma_Cz : Real = 29.057750463592832;
                                attribute Ixx : Real = 0.32790540412752905;
                                attribute sigma_Ixx : Real = 0.37074144170588635;
                                attribute Iyy : Real = 0.3886392247945744;
                                attribute sigma_Iyy : Real = 0.3723953238821935;
                                attribute Izz : Real = 0.39209893694157205;
                                attribute sigma_Izz : Real = 0.37017423652493897;
                                attribute Ixy : Real = 0.02817494455285071;
                                attribute sigma_Ixy : Real = 0.02351283871158888;
                                attribute Ixz : Real = 0.032126219191795966;
                                attribute sigma_Ixz : Real = 0.022566176940390956;
                                attribute Iyz : Real = 0.0047057567483918625;
                                attribute sigma_Iyz : Real = 0.02209918015384651;
                            }
                            part <'C.1.2.1.4.2.2.2'> 'Part 879' {
                                attribute POIconv : String = "+";
                                attribute Ipoint : Boolean = false;
                                attribute mass : Real = 0.1723956700002309;
                                attribute sigma_mass : Real = 0.28909372274994966;
                                attribute Cx : Real = 34.508997248485684;
                                attribute sigma_Cx : Real = 28.721044428837228;
                                attribute Cy : Real = -12.193138571456075;
                                attribute sigma_Cy : Real = 28.23690002309109;
                                attribute Cz : Real = 21.78624365478754;
                                attribute sigma_Cz : Real = 29.057750463592832;
                                attribute Ixx : Real = 0.2364483067339139;
                                attribute sigma_Ixx : Real = 0.37074144170588635;
                                attribute Iyy : Real = 0.2300038769012629;
                                attribute sigma_Iyy : Real = 0.3723953238821935;
                                attribute Izz : Real = 0.19061696205901213;
                                attribute sigma_Izz : Real = 0.37017423652493897;
                                attribute Ixy : Real = -0.01936783134201921;
                                attribute sigma_Ixy : Real = 0.02351283871158888;
                                attribute Ixz : Real = 0.0015651232361137085;
                                attribute sigma_Ixz : Real = 0.022566176940390956;
                                attribute Iyz : Real = -0.00505840643941757;
                                attribute sigma_Iyz : Real = 0.02209918015384651;
                            }
                            part <'C.1.2.1.4.2.2.3'> 'Part 880' {
                                attribute POIconv : String = "-";
                                attribute Ipoint : Boolean = false;
                                attribute mass : Real = 0.49579794705542735;
                                attribute sigma_mass : Real = 0.28909372274994966;
                                attribute Cx : Real = -96.14929696545005;
                                attribute sigma_Cx : Real = 28.721044428837228;
                                attribute Cy : Real = -62.139587150886655;
                                attribute sigma_Cy : Real = 28.23690002309109;
                                attribute Cz : Real = -77.74973716586828;
                                attribute sigma_Cz : Real = 29.057750463592832;
                                attribute Ixx : Real = 0.5187867401552515;
                                attribute sigma_Ixx : Real = 0.37074144170588635;
                                attribute Iyy : Real = 0.6038550697233149;
                                attribute sigma_Iyy : Real = 0.3723953238821935;
                                attribute Izz : Real = 0.517129027971741;
                                attribute sigma_Izz : Real = 0.37017423652493897;
                                attribute Ixy : Real = -0.023769010484124015;
                                attribute sigma_Ixy : Real = 0.02351283871158888;
                                attribute Ixz : Real = 0.0021216731298101497;
                                attribute sigma_Ixz : Real = 0.022566176940390956;
                                attribute Iyz : Real = -0.00037679636179241253;
                                attribute sigma_Iyz : Real = 0.02209918015384651;
                            }
                            part <'C.1.2.1.4.2.2.4'> 'Part 881' {
                                attribute POIconv : String = "-";
                                attribute Ipoint : Boolean = false;
                                attribute mass : Real = 0.5065603755596094;
                                attribute sigma_mass : Real = 0.28909372274994966;
                                attribute Cx : Real = -38.02535077556968;
                                attribute sigma_Cx : Real = 28.721044428837228;
                                attribute Cy : Real = -1.133557641878724;
                                attribute sigma_Cy : Real = 28.23690002309109;
                                attribute Cz : Real = -88.88060031458735;
                                attribute sigma_Cz : Real = 29.057750463592832;
                                attribute Ixx : Real = 0.5506132929822533;
                                attribute sigma_Ixx : Real = 0.37074144170588635;
                                attribute Iyy : Real = 0.49463721108655295;
                                attribute sigma_Iyy : Real = 0.3723953238821935;
                                attribute Izz : Real = 0.5082754194049325;
                                attribute sigma_Izz : Real = 0.37017423652493897;
                                attribute Ixy : Real = -0.022121695050827107;
                                attribute sigma_Ixy : Real = 0.02351283871158888;
                                attribute Ixz : Real = -0.008213365103601874;
                                attribute sigma_Ixz : Real = 0.022566176940390956;
                                attribute Iyz : Real = -0.009709987028756221;
                                attribute sigma_Iyz : Real = 0.02209918015384651;
                            }
                        }
                        part <'C.1.2.1.4.2.3'> 'Subassembly 250' {
                            attribute POIconv : String = "-";
                            attribute Ipoint : Boolean = false;
                            attribute mass : Real = 0.8604771897378376;
                            attribute sigma_mass : Real = 0.5007250159521434;
                            attribute Cx : Real = 73.63318088836365;
                            attribute sigma_Cx : Real = 20.511053666068918;
                            attribute Cy : Real = -26.913059078770154;
                            attribute sigma_Cy : Real = 29.07923816863242;
                            attribute Cz : Real = 9.207197458121133;
                            attribute sigma_Cz : Real = 27.503646982255436;
                            attribute Ixx : Real = 1896.584427122979;
                            attribute sigma_Ixx : Real = 1981.6016020544416;
                            attribute Iyy : Real = 630.6427322263755;
                            attribute sigma_Iyy : Real = 1042.0276152543495;
                            attribute Izz : Real = 1369.817064037452;
                            attribute sigma_Izz : Real = 1536.831321010163;
                            attribute Ixy : Real = -253.6354218866898;
                            attribute sigma_Ixy : Real = 672.1591690838065;
                            attribute Ixz : Real = -122.77310695281689;
                            attribute sigma_Ixz : Real = 436.82128058770064;
                            attribute Iyz : Real = -741.0467898826323;
                            attribute sigma_Iyz : Real = 958.6436202560024;
                            part <'C.1.2.1.4.2.3.1'> 'Part 882' {
                                attribute POIconv : String = "-";
                                attribute Ipoint : Boolean = false;
                                attribute mass : Real = 0.050590304508339616;
                                attribute sigma_mass : Real = 0.28909372274994966;
                                attribute Cx : Real = 62.426201067864895;
                                attribute sigma_Cx : Real = 28.721044428837228;
                                attribute Cy : Real = -50.291696889325976;
                                attribute sigma_Cy : Real = 28.23690002309109;
                                attribute Cz : Real = 50.19796080887318;
                                attribute sigma_Cz : Real = 29.057750463592832;
                                attribute Ixx : Real = 0.06874078058828009;
                                attribute sigma_Ixx : Real = 0.37074144170588635;
                                attribute Iyy : Real = 0.06490268322578027;
                                attribute sigma_Iyy : Real = 0.3723953238821935;
                                attribute Izz : Real = 0.07600627149522667;
                                attribute sigma_Izz : Real = 0.37017423652493897;
                                attribute Ixy : Real = -0.0008540706664279351;
                                attribute sigma_Ixy : Real = 0.02351283871158888;
                                attribute Ixz : Real = -0.0023882023017479316;
                                attribute sigma_Ixz : Real = 0.022566176940390956;
                                attribute Iyz : Real = 0.0004652158540353906;
                                attribute sigma_Iyz : Real = 0.02209918015384651;
                            }
                            part <'C.1.2.1.4.2.3.2'> 'Part 883' {
                                attribute POIconv : String = "+";
                                attribute Ipoint : Boolean = false;
                                attribute mass : Real = 0.5100211774855852;
                                attribute sigma_mass : Real = 0.28909372274994966;
                                attribute Cx : Real = 80.02120340242982;
                                attribute sigma_Cx : Real = 28.721044428837228;
                                attribute Cy : Real = 5.123272677883506;
                                attribute sigma_Cy : Real = 28.23690002309109;
                                attribute Cz : Real = 25.464348448440433;
                                attribute sigma_Cz : Real = 29.057750463592832;
                                attribute Ixx : Real = 0.8123473071364197;
                                attribute sigma_Ixx : Real = 0.37074144170588635;
                                attribute Iyy : Real = 0.7761243942042328;
                                attribute sigma_Iyy : Real = 0.3723953238821935;
                                attribute Izz : Real = 0.8058108417780543;
                                attribute sigma_Izz : Real = 0.37017423652493897;
                                attribute Ixy : Real = -0.011232746683602125;
                                attribute sigma_Ixy : Real = 0.02351283871158888;
                                attribute Ixz : Real = 0.030361710838555822;
                                attribute sigma_Ixz : Real = 0.022566176940390956;
                                attribute Iyz : Real = 0.006308870912483725;
                                attribute sigma_Iyz : Real = 0.02209918015384651;
                            }
                            part <'C.1.2.1.4.2.3.3'> 'Part 884' {
                                attribute POIconv : String = "+";
                                attribute Ipoint : Boolean = false;
                                attribute mass : Real = 0.2998657077439129;
                                attribute sigma_mass : Real = 0.28909372274994966;
                                attribute Cx : Real = 64.65895618312061;
                                attribute sigma_Cx : Real = 28.721044428837228;
                                attribute Cy : Real = -77.45726886205375;
                                attribute sigma_Cy : Real = 28.23690002309109;
                                attribute Cz : Real = -25.359030766412616;
                                attribute sigma_Cz : Real = 29.057750463592832;
                                attribute Ixx : Real = 0.4455265326663298;
                                attribute sigma_Ixx : Real = 0.37074144170588635;
                                attribute Iyy : Real = 0.39840045803022395;
                                attribute sigma_Iyy : Real = 0.3723953238821935;
                                attribute Izz : Real = 0.4477280357967806;
                                attribute sigma_Izz : Real = 0.37017423652493897;
                                attribute Ixy : Real = -0.0018984741520829875;
                                attribute sigma_Ixy : Real = 0.02351283871158888;
                                attribute Ixz : Real = -0.0054391085791179695;
                                attribute sigma_Ixz : Real = 0.022566176940390956;
                                attribute Iyz : Real = -0.009097553900918872;
                                attribute sigma_Iyz : Real = 0.02209918015384651;
                            }
                        }
                    }
                    part <'C.1.2.1.4.3'> 'Assembly 72' {
                        attribute POIconv : String = "-";
                        attribute Ipoint : Boolean = false;
                        attribute mass : Real = 3.980435287952423;
                        attribute sigma_mass : Real = 0.7648700959862226;
                        attribute Cx : Real = -16.533187969356604;
                        attribute sigma_Cx : Real = 16.814765793511196;
                        attribute Cy : Real = 10.472029395477222;
                        attribute sigma_Cy : Real = 15.535387145720234;
                        attribute Cz : Real = 3.5108946397235012;
                        attribute sigma_Cz : Real = 15.449002355590281;
                        attribute Ixx : Real = 21365.957654034813;
                        attribute sigma_Ixx : Real = 8195.3877464377;
                        attribute Iyy : Real = 25312.230331244828;
                        attribute sigma_Iyy : Real = 8974.883418754522;
                        attribute Izz : Real = 25127.214283585425;
                        attribute sigma_Izz : Real = 9026.15698654749;
                        attribute Ixy : Real = -2755.6061061540536;
                        attribute sigma_Ixy : Real = 4410.36296533068;
                        attribute Ixz : Real = 7066.305443558745;
                        attribute sigma_Ixz : Real = 4367.078499741777;
                        attribute Iyz : Real = 8181.389788336053;
                        attribute sigma_Iyz : Real = 4085.0684639818437;
                        part <'C.1.2.1.4.3.1'> 'Subassembly 251' {
                            attribute POIconv : String = "-";
                            attribute Ipoint : Boolean = false;
                            attribute mass : Real = 1.4489720894189086;
                            attribute sigma_mass : Real = 0.40884026350990615;
                            attribute Cx : Real = -59.802735175884955;
                            attribute sigma_Cx : Real = 21.33411978956682;
                            attribute Cy : Real = 43.5268666869883;
                            attribute sigma_Cy : Real = 21.095035833575658;
                            attribute Cz : Real = 11.176095962610457;
                            attribute sigma_Cz : Real = 24.15847892622921;
                            attribute Ixx : Real = 3757.7771659585383;
                            attribute sigma_Ixx : Real = 3193.685415491731;
                            attribute Iyy : Real = 3691.4233815054504;
                            attribute sigma_Iyy : Real = 3172.9622477154926;
                            attribute Izz : Real = 1601.6513353623104;
                            attribute sigma_Izz : Real = 1989.625314491455;
                            attribute Ixy : Real = 799.1191209614908;
                            attribute sigma_Ixy : Real = 995.4343500946943;
                            attribute Ixz : Real = -1496.8727387981378;
                            attribute sigma_Ixz : Real = 1546.9870549185282;
                            attribute Iyz : Real = 1560.3918645125004;
                            attribute sigma_Iyz : Real = 1546.3036503736405;
                            part <'C.1.2.1.4.3.1.1'> 'Part 885' {
                                attribute POIconv : String = "+";
                                attribute Ipoint : Boolean = false;
                                attribute mass : Real = 0.7491437257248909;
                                attribute sigma_mass : Real = 0.28909372274994966;
                                attribute Cx : Real = -82.03398082405329;
                                attribute sigma_Cx : Real = 28.721044428837228;
                                attribute Cy : Real = 66.7016813531518;
                                attribute sigma_Cy : Real = 28.23690002309109;
                                attribute Cz : Real = -32.23336827941239;
                                attribute sigma_Cz : Real = 29.057750463592832;
                                attribute Ixx : Real = 0.9855565016923363;
                                attribute sigma_Ixx : Real = 0.37074144170588635;
                                attribute Iyy : Real = 0.9921624877944623;
                                attribute sigma_Iyy : Real = 0.3723953238821935;
                                attribute Izz : Real = 0.9669671789260723;
                                attribute sigma_Izz : Real = 0.37017423652493897;
                                attribute Ixy : Real = -0.003268591755477613;
                                attribute sigma_Ixy : Real = 0.02351283871158888;
                                attribute Ixz : Real = 0.0013095174335343777;
                                attribute sigma_Ixz : Real = 0.022566176940390956;
                                attribute Iyz : Real = 0.0008691981100164805;
                                attribute sigma_Iyz : Real = 0.02209918015384651;
                            }
                            part <'C.1.2.1.4.3.1.2'> 'Part 886' {
                                attribute POIconv : String = "+";
                                attribute Ipoint : Boolean = false;
                                attribute mass : Real = 0.6998283636940178;
                                attribute sigma_mass : Real = 0.28909372274994966;
                                attribute Cx : Real = -36.004902655258775;
                                attribute sigma_Cx : Real = 28.721044428837228;
                                attribute Cy : Real = 18.71897391974926;
                                attribute sigma_Cy : Real = 28.23690002309109;
                                attribute Cz : Real = 57.644529454410076;
                                attribute sigma_Cz : Real = 29.057750463592832;
                                attribute Ixx : Real = 0.9282714449993907;
                                attribute sigma_Ixx : Real = 0.37074144170588635;
                                attribute Iyy : Real = 1.021879984634578;
                                attribute sigma_Iyy : Real = 0.3723953238821935;
                                attribute Izz : Real = 1.0571767025242786;
                                attribute sigma_Izz : Real = 0.37017423652493897;
                                attribute Ixy : Real = 0.007263574339031811;
                                attribute sigma_Ixy : Real = 0.02351283871158888;
                                attribute Ixz : Real = 0.009131728147379236;
                                attribute sigma_Ixz : Real = 0.022566176940390956;
                                attribute Iyz : Real = 0.001446424153335739;
                                attribute sigma_Iyz : Real = 0.02209918015384651;
                            }
                        }
                        part <'C.1.2.1.4.3.2'> 'Subassembly 252' {
                            attribute POIconv : String = "-";
                            attribute Ipoint : Boolean = false;
                            attribute mass : Real = 2.5314631985335145;
                            attribute sigma_mass : Real = 0.6464332159373649;
                            attribute Cx : Real = 8.23366080820955;
                            attribute sigma_Cx : Real = 21.472911013479965;
                            attribute Cy : Real = -8.448070522794914;
                            attribute sigma_Cy : Real = 19.97681312732007;
                            attribute Cz : Real = -0.8765532137843919;
                            attribute sigma_Cz : Real = 19.902024080817775;
                            attribute Ixx : Real = 14984.94826780092;
                            attribute sigma_Ixx : Real = 6960.971163546203;
                            attribute Iyy : Real = 17221.307440588498;
                            attribute sigma_Iyy : Real = 7402.749036588129;
                            attribute Izz : Real = 16770.560638731615;
                            attribute sigma_Izz : Real = 7314.227006001939;
                            attribute Ixy : Real = -6813.3649248922975;
                            attribute sigma_Ixy : Real = 3550.632553119197;
                            attribute Ixz : Real = 7807.520875623594;
                            attribute sigma_Ixz : Real = 3562.4054145797836;
                            attribute Iyz : Real = 7198.266024249658;
                            attribute sigma_Iyz : Real = 3454.204608410513;
                            part <'C.1.2.1.4.3.2.1'> 'Part 887' {
                                attribute POIconv : String = "-";
                                attribute Ipoint : Boolean = false;
                                attribute mass : Real = 0.10775876299384982;
                                attribute sigma_mass : Real = 0.28909372274994966;
                                attribute Cx : Real = -58.45392211340368;
                                attribute sigma_Cx : Real = 28.721044428837228;
                                attribute Cy : Real = 45.44548690319061;
                                attribute sigma_Cy : Real = 28.23690002309109;
                                attribute Cz : Real = 15.222681732848287;
                                attribute sigma_Cz : Real = 29.057750463592832;
                                attribute Ixx : Real = 0.14406637367684322;
                                attribute sigma_Ixx : Real = 0.37074144170588635;
                                attribute Iyy : Real = 0.14100496678242813;
                                attribute sigma_Iyy : Real = 0.3723953238821935;
                                attribute Izz : Real = 0.15616785894719315;
                                attribute sigma_Izz : Real = 0.37017423652493897;
                                attribute Ixy : Real = 0.00547566011066585;
                                attribute sigma_Ixy : Real = 0.02351283871158888;
                                attribute Ixz : Real = 0.00559854859800277;
                                attribute sigma_Ixz : Real = 0.022566176940390956;
                                attribute Iyz : Real = -0.0069062261422062066;
                                attribute sigma_Iyz : Real = 0.02209918015384651;
                            }
                            part <'C.1.2.1.4.3.2.2'> 'Part 888' {
                                attribute POIconv : String = "+";
                                attribute Ipoint : Boolean = false;
                                attribute mass : Real = 0.865055982094258;
                                attribute sigma_mass : Real = 0.28909372274994966;
                                attribute Cx : Real = -44.30886339396238;
                                attribute sigma_Cx : Real = 28.721044428837228;
                                attribute Cy : Real = -53.615461522713304;
                                attribute sigma_Cy : Real = 28.23690002309109;
                                attribute Cz : Real = 42.18867253512144;
                                attribute sigma_Cz : Real = 29.057750463592832;
                                attribute Ixx : Real = 0.9418215373310636;
                                attribute sigma_Ixx : Real = 0.37074144170588635;
                                attribute Iyy : Real = 0.7608142694735102;
                                attribute sigma_Iyy : Real = 0.3723953238821935;
                                attribute Izz : Real = 0.922507610945533;
                                attribute sigma_Izz : Real = 0.37017423652493897;
                                attribute Ixy : Real = 0.003954190996576758;
                                attribute sigma_Ixy : Real = 0.02351283871158888;
                                attribute Ixz : Real = -0.0070787821950095;
                                attribute sigma_Ixz : Real = 0.022566176940390956;
                                attribute Iyz : Real = 0.04187183472708235;
                                attribute sigma_Iyz : Real = 0.02209918015384651;
                            }
                            part <'C.1.2.1.4.3.2.3'> 'Part 889' {
                                attribute POIconv : String = "+";
                                attribute Ipoint : Boolean = false;
                                attribute mass : Real = 0.3976534101071302;
                                attribute sigma_mass : Real = 0.28909372274994966;
                                attribute Cx : Real = -51.677533937618136;
                                attribute sigma_Cx : Real = 28.721044428837228;
                                attribute Cy : Real = -73.42608482576907;
                                attribute sigma_Cy : Real = 28.23690002309109;
                                attribute Cz : Real = 67.81320073641837;
                                attribute sigma_Cz : Real = 29.057750463592832;
                                attribute Ixx : Real = 0.5600971354308069;
                                attribute sigma_Ixx : Real = 0.37074144170588635;
                                attribute Iyy : Real = 0.5396715266257596;
                                attribute sigma_Iyy : Real = 0.3723953238821935;
                                attribute Izz : Real = 0.4744866499202376;
                                attribute sigma_Izz : Real = 0.37017423652493897;
                                attribute Ixy : Real = 0.007534120957154927;
                                attribute sigma_Ixy : Real = 0.02351283871158888;
                                attribute Ixz : Real = -0.017460491659828672;
                                attribute sigma_Ixz : Real = 0.022566176940390956;
                                attribute Iyz : Real = 0.033087381637155536;
                                attribute sigma_Iyz : Real = 0.02209918015384651;
                            }
                            part <'C.1.2.1.4.3.2.4'> 'Part 890' {
                                attribute POIconv : String = "-";
                                attribute Ipoint : Boolean = false;
                                attribute mass : Real = 0.555115302071441;
                                attribute sigma_mass : Real = 0.28909372274994966;
                                attribute Cx : Real = 61.39585142955184;
                                attribute sigma_Cx : Real = 28.721044428837228;
                                attribute Cy : Real = 64.13843552581966;
                                attribute sigma_Cy : Real = 28.23690002309109;
                                attribute Cz : Real = -77.88812830112875;
                                attribute sigma_Cz : Real = 29.057750463592832;
                                attribute Ixx : Real = 0.6611942778411626;
                                attribute sigma_Ixx : Real = 0.37074144170588635;
                                attribute Iyy : Real = 0.6738151119641261;
                                attribute sigma_Iyy : Real = 0.3723953238821935;
                                attribute Izz : Real = 0.7929114094951272;
                                attribute sigma_Izz : Real = 0.37017423652493897;
                                attribute Ixy : Real = -0.000509362731094902;
                                attribute sigma_Ixy : Real = 0.02351283871158888;
                                attribute Ixz : Real = 0.0057383556083115995;
                                attribute sigma_Ixz : Real = 0.022566176940390956;
                                attribute Iyz : Real = -0.04000901188237635;
                                attribute sigma_Iyz : Real = 0.02209918015384651;
                            }
                            part <'C.1.2.1.4.3.2.5'> 'Part 891' {
                                attribute POIconv : String = "-";
                                attribute Ipoint : Boolean = false;
                                attribute mass : Real = 0.6058797412668355;
                                attribute sigma_mass : Real = 0.28909372274994966;
                                attribute Cx : Real = 85.72617047466338;
                                attribute sigma_Cx : Real = 28.721044428837228;
                                attribute Cy : Real = 22.597145475447178;
                                attribute sigma_Cy : Real = 28.23690002309109;
                                attribute Cz : Real = -39.75072959437966;
                                attribute sigma_Cz : Real = 29.057750463592832;
                                attribute Ixx : Real = 0.7779372659849757;
                                attribute sigma_Ixx : Real = 0.37074144170588635;
                                attribute Iyy : Real = 0.842547680294552;
                                attribute sigma_Iyy : Real = 0.3723953238821935;
                                attribute Izz : Real = 0.7815172456056424;
                                attribute sigma_Izz : Real = 0.37017423652493897;
                                attribute Ixy : Real = 0.06006724028695434;
                                attribute sigma_Ixy : Real = 0.02351283871158888;
                                attribute Ixz : Real = 0.03884631353718987;
                                attribute sigma_Ixz : Real = 0.022566176940390956;
                                attribute Iyz : Real = 0.06444937135160092;
                                attribute sigma_Iyz : Real = 0.02209918015384651;
                            }
                        }
                    }
                    part <'C.1.2.1.4.4'> 'Assembly 73' {
                        attribute POIconv : String = "-";
                        attribute Ipoint : Boolean = false;
                        attribute mass : Real = 5.955993725442095;
                        attribute sigma_mass : Real = 0.914194621147077;
                        attribute Cx : Real = -0.20568933681228224;
                        attribute sigma_Cx : Real = 13.143151521038144;
                        attribute Cy : Real = 12.912401002329522;
                        attribute sigma_Cy : Real = 13.411933635982207;
                        attribute Cz : Real = 17.920793268073403;
                        attribute sigma_Cz : Real = 14.70493575258007;
                        attribute Ixx : Real = 32613.879181346903;
                        attribute sigma_Ixx : Real = 12414.46395293064;
                        attribute Iyy : Real = 37183.47845077222;
                        attribute sigma_Iyy : Real = 12326.825508726288;
                        attribute Izz : Real = 26492.554953247203;
                        attribute sigma_Izz : Real = 9825.489647454162;
                        attribute Ixy : Real = 3145.4023495927786;
                        attribute sigma_Ixy : Real = 4705.7054063530495;
                        attribute Ixz : Real = -4784.321115179401;
                        attribute sigma_Ixz : Real = 5799.43626314167;
                        attribute Iyz : Real = 1561.630186853215;
                        attribute sigma_Iyz : Real = 5894.95150082046;
                        part <'C.1.2.1.4.4.1'> 'Subassembly 253' {
                            attribute POIconv : String = "-";
                            attribute Ipoint : Boolean = false;
                            attribute mass : Real = 2.3664501827547793;
                            attribute sigma_mass : Real = 0.5007250159521434;
                            attribute Cx : Real = -33.16525169893915;
                            attribute sigma_Cx : Real = 18.93183927140394;
                            attribute Cy : Real = 32.71509775593276;
                            attribute sigma_Cy : Real = 18.101203186385263;
                            attribute Cz : Real = -21.64002047119488;
                            attribute sigma_Cz : Real = 22.553244887089573;
                            attribute Ixx : Real = 11001.007485220758;
                            attribute sigma_Ixx : Real = 6191.665012269797;
                            attribute Iyy : Real = 11298.561931250246;
                            attribute sigma_Iyy : Real = 6334.9431991446945;
                            attribute Izz : Real = 3296.583937610246;
                            attribute sigma_Izz : Real = 2990.1170673108454;
                            attribute Ixy : Real = 1445.166068233224;
                            attribute sigma_Ixy : Real = 1471.0921358276528;
                            attribute Ixz : Real = 3539.0392372160773;
                            attribute sigma_Ixz : Real = 3026.3925818620023;
                            attribute Iyz : Real = -3767.889193699643;
                            attribute sigma_Iyz : Real = 2879.127910186344;
                            part <'C.1.2.1.4.4.1.1'> 'Part 892' {
                                attribute POIconv : String = "+";
                                attribute Ipoint : Boolean = false;
                                attribute mass : Real = 0.9839543643093203;
                                attribute sigma_mass : Real = 0.28909372274994966;
                                attribute Cx : Real = -8.969714026898146;
                                attribute sigma_Cx : Real = 28.721044428837228;
                                attribute Cy : Real = 3.772946447134018;
                                attribute sigma_Cy : Real = 28.23690002309109;
                                attribute Cz : Real = -95.32698071561754;
                                attribute sigma_Cz : Real = 29.057750463592832;
                                attribute Ixx : Real = 1.0476112449192303;
                                attribute sigma_Ixx : Real = 0.37074144170588635;
                                attribute Iyy : Real = 1.0957999013834414;
                                attribute sigma_Iyy : Real = 0.3723953238821935;
                                attribute Izz : Real = 1.1519422399144252;
                                attribute sigma_Izz : Real = 0.37017423652493897;
                                attribute Ixy : Real = 0.004691518554134694;
                                attribute sigma_Ixy : Real = 0.02351283871158888;
                                attribute Ixz : Real = -0.009787090024304276;
                                attribute sigma_Ixz : Real = 0.022566176940390956;
                                attribute Iyz : Real = -0.03499389460194705;
                                attribute sigma_Iyz : Real = 0.02209918015384651;
                            }
                            part <'C.1.2.1.4.4.1.2'> 'Part 893' {
                                attribute POIconv : String = "-";
                                attribute Ipoint : Boolean = false;
                                attribute mass : Real = 0.9674728149638977;
                                attribute sigma_mass : Real = 0.28909372274994966;
                                attribute Cx : Real = -34.53551633283496;
                                attribute sigma_Cx : Real = 28.721044428837228;
                                attribute Cy : Real = 48.11259317211807;
                                attribute sigma_Cy : Real = 28.23690002309109;
                                attribute Cz : Real = 20.308606885373592;
                                attribute sigma_Cz : Real = 29.057750463592832;
                                attribute Ixx : Real = 1.298959936817941;
                                attribute sigma_Ixx : Real = 0.37074144170588635;
                                attribute Iyy : Real = 1.1970174149185824;
                                attribute sigma_Iyy : Real = 0.3723953238821935;
                                attribute Izz : Real = 1.2442993808244205;
                                attribute sigma_Izz : Real = 0.37017423652493897;
                                attribute Ixy : Real = 0.0010835452257832892;
                                attribute sigma_Ixy : Real = 0.02351283871158888;
                                attribute Ixz : Real = 0.01743985679662994;
                                attribute sigma_Ixz : Real = 0.022566176940390956;
                                attribute Iyz : Real = -0.049229822046473096;
                                attribute sigma_Iyz : Real = 0.02209918015384651;
                            }
                            part <'C.1.2.1.4.4.1.3'> 'Part 894' {
                                attribute POIconv : String = "-";
                                attribute Ipoint : Boolean = false;
                                attribute mass : Real = 0.4150230034815613;
                                attribute sigma_mass : Real = 0.28909372274994966;
                                attribute Cx : Real = -87.33480595983565;
                                attribute sigma_Cx : Real = 28.721044428837228;
                                attribute Cy : Real = 65.438820887357;
                                attribute sigma_Cy : Real = 28.23690002309109;
                                attribute Cz : Real = 55.272462125867605;
                                attribute sigma_Cz : Real = 29.057750463592832;
                                attribute Ixx : Real = 0.4833654988359504;
                                attribute sigma_Ixx : Real = 0.37074144170588635;
                                attribute Iyy : Real = 0.4284578636487586;
                                attribute sigma_Iyy : Real = 0.3723953238821935;
                                attribute Izz : Real = 0.5189108504499969;
                                attribute sigma_Izz : Real = 0.37017423652493897;
                                attribute Ixy : Real = 0.04067450610915517;
                                attribute sigma_Ixy : Real = 0.02351283871158888;
                                attribute Ixz : Real = -0.0034760958638650474;
                                attribute sigma_Ixz : Real = 0.022566176940390956;
                                attribute Iyz : Real = 0.014641128303072837;
                                attribute sigma_Iyz : Real = 0.02209918015384651;
                            }
                        }
                        part <'C.1.2.1.4.4.2'> 'Subassembly 254' {
                            attribute POIconv : String = "-";
                            attribute Ipoint : Boolean = false;
                            attribute mass : Real = 0.2890749436072074;
                            attribute sigma_mass : Real = 0.40884026350990615;
                            attribute Cx : Real = -46.14924764934686;
                            attribute sigma_Cx : Real = 48.42296656038124;
                            attribute Cy : Real = -69.10226274544848;
                            attribute sigma_Cy : Real = 26.729914169156356;
                            attribute Cz : Real = -34.53756077277195;
                            attribute sigma_Cz : Real = 43.57937527592399;
                            attribute Ixx : Real = 141.6012939688856;
                            attribute sigma_Ixx : Real = 474.10457444799135;
                            attribute Iyy : Real = 284.3618976760483;
                            attribute sigma_Iyy : Real = 896.0184564233878;
                            attribute Izz : Real = 182.07619875134196;
                            attribute sigma_Izz : Real = 593.1062833972983;
                            attribute Ixy : Real = -56.20749979330978;
                            attribute sigma_Ixy : Real = 208.19738855292974;
                            attribute Ixz : Real = 140.54476917824897;
                            attribute sigma_Ixz : Real = 444.12124989464274;
                            attribute Iyz : Real = 48.68034269335476;
                            attribute sigma_Iyz : Real = 181.67554009252765;
                            part <'C.1.2.1.4.4.2.1'> 'Part 895' {
                                attribute POIconv : String = "+";
                                attribute Ipoint : Boolean = false;
                                attribute mass : Real = 0.21539932430023329;
                                attribute sigma_mass : Real = 0.28909372274994966;
                                attribute Cx : Real = -60.005019744858146;
                                attribute sigma_Cx : Real = 28.721044428837228;
                                attribute Cy : Real = -73.90226856805384;
                                attribute sigma_Cy : Real = 28.23690002309109;
                                attribute Cz : Real = -22.535437997430563;
                                attribute sigma_Cz : Real = 29.057750463592832;
                                attribute Ixx : Real = 0.28205077494830033;
                                attribute sigma_Ixx : Real = 0.37074144170588635;
                                attribute Iyy : Real = 0.2805262765242215;
                                attribute sigma_Iyy : Real = 0.3723953238821935;
                                attribute Izz : Real = 0.2682207295553417;
                                attribute sigma_Izz : Real = 0.37017423652493897;
                                attribute Ixy : Real = 0.0012811378256245706;
                                attribute sigma_Ixy : Real = 0.02351283871158888;
                                attribute Ixz : Real = 0.002118327299968095;
                                attribute sigma_Ixz : Real = 0.022566176940390956;
                                attribute Iyz : Real = 0.006586046086165365;
                                attribute sigma_Iyz : Real = 0.02209918015384651;
                            }
                            part <'C.1.2.1.4.4.2.2'> 'Part 896' {
                                attribute POIconv : String = "+";
                                attribute Ipoint : Boolean = false;
                                attribute mass : Real = 0.07367561930697411;
                                attribute sigma_mass : Real = 0.28909372274994966;
                                attribute Cx : Real = -5.640270933508873;
                                attribute sigma_Cx : Real = 28.721044428837228;
                                attribute Cy : Real = -55.06888208910823;
                                attribute sigma_Cy : Real = 28.23690002309109;
                                attribute Cz : Real = -69.62717603892088;
                                attribute sigma_Cz : Real = 29.057750463592832;
                                attribute Ixx : Real = 0.10319062508449083;
                                attribute sigma_Ixx : Real = 0.37074144170588635;
                                attribute Iyy : Real = 0.08460161430152588;
                                attribute sigma_Iyy : Real = 0.3723953238821935;
                                attribute Izz : Real = 0.08290583454514729;
                                attribute sigma_Izz : Real = 0.37017423652493897;
                                attribute Ixy : Real = -0.00247429462184856;
                                attribute sigma_Ixy : Real = 0.02351283871158888;
                                attribute Ixz : Real = -0.00046761340291356647;
                                attribute sigma_Ixz : Real = 0.022566176940390956;
                                attribute Iyz : Real = 0.0020673827736758647;
                                attribute sigma_Iyz : Real = 0.02209918015384651;
                            }
                        }
                        part <'C.1.2.1.4.4.3'> 'Subassembly 255' {
                            attribute POIconv : String = "-";
                            attribute Ipoint : Boolean = false;
                            attribute mass : Real = 3.300468599080108;
                            attribute sigma_mass : Real = 0.6464332159373649;
                            attribute Cx : Real = 27.450472557630142;
                            attribute sigma_Cx : Real = 16.539709916137813;
                            attribute Cy : Real = 5.897121093227476;
                            attribute sigma_Cy : Real = 17.254946604901626;
                            attribute Cz : Real = 50.880685893509394;
                            attribute sigma_Cz : Real = 17.55543043448157;
                            attribute Ixx : Real = 10351.799629649862;
                            attribute sigma_Ixx : Real = 7729.893665812618;
                            attribute Iyy : Real = 11810.602591136627;
                            attribute sigma_Iyy : Real = 7085.814981213371;
                            attribute Izz : Real = 14273.691971375214;
                            attribute sigma_Izz : Real = 6982.312939086226;
                            attribute Ixy : Real = 660.7943821165773;
                            attribute sigma_Ixy : Real = 3254.036246028274;
                            attribute Ixz : Real = -1673.0448427766232;
                            attribute sigma_Ixz : Real = 3101.257406640091;
                            attribute Iyz : Real = 3907.4953992442106;
                            attribute sigma_Iyz : Real = 3774.758900831475;
                            part <'C.1.2.1.4.4.3.1'> 'Part 897' {
                                attribute POIconv : String = "-";
                                attribute Ipoint : Boolean = false;
                                attribute mass : Real = 0.18614264408056624;
                                attribute sigma_mass : Real = 0.28909372274994966;
                                attribute Cx : Real = 72.10570042952895;
                                attribute sigma_Cx : Real = 28.721044428837228;
                                attribute Cy : Real = 97.81113904900849;
                                attribute sigma_Cy : Real = 28.23690002309109;
                                attribute Cz : Real = -63.903958862647414;
                                attribute sigma_Cz : Real = 29.057750463592832;
                                attribute Ixx : Real = 0.22739184197252096;
                                attribute sigma_Ixx : Real = 0.37074144170588635;
                                attribute Iyy : Real = 0.22077749649485345;
                                attribute sigma_Iyy : Real = 0.3723953238821935;
                                attribute Izz : Real = 0.17139875844780797;
                                attribute sigma_Izz : Real = 0.37017423652493897;
                                attribute Ixy : Real = 0.00018407312316736938;
                                attribute sigma_Ixy : Real = 0.02351283871158888;
                                attribute Ixz : Real = 0.005989788758016578;
                                attribute sigma_Ixz : Real = 0.022566176940390956;
                                attribute Iyz : Real = 0.01380473445709085;
                                attribute sigma_Iyz : Real = 0.02209918015384651;
                            }
                            part <'C.1.2.1.4.4.3.2'> 'Part 898' {
                                attribute POIconv : String = "+";
                                attribute Ipoint : Boolean = false;
                                attribute mass : Real = 0.659777350923745;
                                attribute sigma_mass : Real = 0.28909372274994966;
                                attribute Cx : Real = 31.922034500166774;
                                attribute sigma_Cx : Real = 28.721044428837228;
                                attribute Cy : Real = 69.23373588360846;
                                attribute sigma_Cy : Real = 28.23690002309109;
                                attribute Cz : Real = 39.722401136532426;
                                attribute sigma_Cz : Real = 29.057750463592832;
                                attribute Ixx : Real = 0.8985933368900464;
                                attribute sigma_Ixx : Real = 0.37074144170588635;
                                attribute Iyy : Real = 0.7896529321151579;
                                attribute sigma_Iyy : Real = 0.3723953238821935;
                                attribute Izz : Real = 0.746699741519373;
                                attribute sigma_Izz : Real = 0.37017423652493897;
                                attribute Ixy : Real = 0.016804329216767125;
                                attribute sigma_Ixy : Real = 0.02351283871158888;
                                attribute Ixz : Real = 0.016468893058255885;
                                attribute sigma_Ixz : Real = 0.022566176940390956;
                                attribute Iyz : Real = -0.011405131987001174;
                                attribute sigma_Iyz : Real = 0.02209918015384651;
                            }
                            part <'C.1.2.1.4.4.3.3'> 'Part 899' {
                                attribute POIconv : String = "+";
                                attribute Ipoint : Boolean = false;
                                attribute mass : Real = 0.8913685550305527;
                                attribute sigma_mass : Real = 0.28909372274994966;
                                attribute Cx : Real = -17.91359605267644;
                                attribute sigma_Cx : Real = 28.721044428837228;
                                attribute Cy : Real = -19.816756481304765;
                                attribute sigma_Cy : Real = 28.23690002309109;
                                attribute Cz : Real = 50.54476298391819;
                                attribute sigma_Cz : Real = 29.057750463592832;
                                attribute Ixx : Real = 1.1596795829030486;
                                attribute sigma_Ixx : Real = 0.37074144170588635;
                                attribute Iyy : Real = 1.1055662569799072;
                                attribute sigma_Iyy : Real = 0.3723953238821935;
                                attribute Izz : Real = 1.1761322989736598;
                                attribute sigma_Izz : Real = 0.37017423652493897;
                                attribute Ixy : Real = 0.050428461875966245;
                                attribute sigma_Ixy : Real = 0.02351283871158888;
                                attribute Ixz : Real = 0.10270566284548288;
                                attribute sigma_Ixz : Real = 0.022566176940390956;
                                attribute Iyz : Real = -0.07918629919857945;
                                attribute sigma_Iyz : Real = 0.02209918015384651;
                            }
                            part <'C.1.2.1.4.4.3.4'> 'Part 900' {
                                attribute POIconv : String = "+";
                                attribute Ipoint : Boolean = false;
                                attribute mass : Real = 0.7228929672855884;
                                attribute sigma_mass : Real = 0.28909372274994966;
                                attribute Cx : Real = -15.475675417110324;
                                attribute sigma_Cx : Real = 28.721044428837228;
                                attribute Cy : Real = 6.788926990702748;
                                attribute sigma_Cy : Real = 28.23690002309109;
                                attribute Cz : Real = 44.040646962821484;
                                attribute sigma_Cz : Real = 29.057750463592832;
                                attribute Ixx : Real = 1.1257810632924674;
                                attribute sigma_Ixx : Real = 0.37074144170588635;
                                attribute Iyy : Real = 1.0887673715194335;
                                attribute sigma_Iyy : Real = 0.3723953238821935;
                                attribute Izz : Real = 1.10291969637122;
                                attribute sigma_Izz : Real = 0.37017423652493897;
                                attribute Ixy : Real = -0.009399960292215643;
                                attribute sigma_Ixy : Real = 0.02351283871158888;
                                attribute Ixz : Real = 0.004075911691954967;
                                attribute sigma_Ixz : Real = 0.022566176940390956;
                                attribute Iyz : Real = -0.01451089432710169;
                                attribute sigma_Iyz : Real = 0.02209918015384651;
                            }
                            part <'C.1.2.1.4.4.3.5'> 'Part 901' {
                                attribute POIconv : String = "+";
                                attribute Ipoint : Boolean = false;
                                attribute mass : Real = 0.8402870817596558;
                                attribute sigma_mass : Real = 0.28909372274994966;
                                attribute Cx : Real = 99.09817320294678;
                                attribute sigma_Cx : Real = 28.721044428837228;
                                attribute Cy : Real = -37.684794375672936;
                                attribute sigma_Cy : Real = 28.23690002309109;
                                attribute Cz : Real = 91.3101399783045;
                                attribute sigma_Cz : Real = 29.057750463592832;
                                attribute Ixx : Real = 1.0499494222789698;
                                attribute sigma_Ixx : Real = 0.37074144170588635;
                                attribute Iyy : Real = 1.0311288766198201;
                                attribute sigma_Iyy : Real = 0.3723953238821935;
                                attribute Izz : Real = 0.9452527494790259;
                                attribute sigma_Izz : Real = 0.37017423652493897;
                                attribute Ixy : Real = 0.01649123168632765;
                                attribute sigma_Ixy : Real = 0.02351283871158888;
                                attribute Ixz : Real = 0.0875617034375826;
                                attribute sigma_Ixz : Real = 0.022566176940390956;
                                attribute Iyz : Real = 0.060795154040447816;
                                attribute sigma_Iyz : Real = 0.02209918015384651;
                            }
                        }
                    }
                    part <'C.1.2.1.4.5'> 'Assembly 74' {
                        attribute POIconv : String = "-";
                        attribute Ipoint : Boolean = false;
                        attribute mass : Real = 5.799761062838369;
                        attribute sigma_mass : Real = 1.0423422407897138;
                        attribute Cx : Real = 25.917591810344895;
                        attribute sigma_Cx : Real = 13.89851978831304;
                        attribute Cy : Real = 7.431248138158655;
                        attribute sigma_Cy : Real = 15.889370150620477;
                        attribute Cz : Real = -21.82230179855385;
                        attribute sigma_Cz : Real = 14.985402993131206;
                        attribute Ixx : Real = 44017.46246752882;
                        attribute sigma_Ixx : Real = 13692.768511264596;
                        attribute Iyy : Real = 34433.68483579489;
                        attribute sigma_Iyy : Real = 12187.655695401048;
                        attribute Izz : Real = 41156.59162410723;
                        attribute sigma_Izz : Real = 13552.96033671169;
                        attribute Ixy : Real = -1047.6766345755473;
                        attribute sigma_Ixy : Real = 6658.800134236569;
                        attribute Ixz : Real = 9962.950573820155;
                        attribute sigma_Ixz : Real = 6018.666856299314;
                        attribute Iyz : Real = 2076.4857467068023;
                        attribute sigma_Iyz : Real = 6918.154945728494;
                        part <'C.1.2.1.4.5.1'> 'Subassembly 256' {
                            attribute POIconv : String = "-";
                            attribute Ipoint : Boolean = false;
                            attribute mass : Real = 0.1995283482989762;
                            attribute sigma_mass : Real = 0.40884026350990615;
                            attribute Cx : Real = 32.595165521551195;
                            attribute sigma_Cx : Real = 31.938941117385294;
                            attribute Cy : Real = -27.81202024808498;
                            attribute sigma_Cy : Real = 116.86259873753026;
                            attribute Cz : Real = 20.781752505263594;
                            attribute sigma_Cz : Real = 104.53857307547676;
                            attribute Ixx : Real = 472.34890314635936;
                            attribute sigma_Ixx : Real = 3093.371813857612;
                            attribute Iyy : Real = 217.35787707814393;
                            attribute sigma_Iyy : Real = 1431.0404039543873;
                            attribute Izz : Real = 273.01988885351966;
                            attribute sigma_Izz : Real = 1793.0516056951417;
                            attribute Ixy : Real = 48.39266065280555;
                            attribute sigma_Ixy : Real = 336.14335436669626;
                            attribute Ixz : Real = -42.995554253813026;
                            attribute sigma_Ixz : Real = 298.79855237207556;
                            attribute Iyz : Real = 234.38455787821715;
                            attribute sigma_Iyz : Real = 1536.0612701621446;
                            part <'C.1.2.1.4.5.1.1'> 'Part 902' {
                                attribute POIconv : String = "-";
                                attribute Ipoint : Boolean = false;
                                attribute mass : Real = 0.16321988468291238;
                                attribute sigma_mass : Real = 0.28909372274994966;
                                attribute Cx : Real = 35.74164588935673;
                                attribute sigma_Cx : Real = 28.721044428837228;
                                attribute Cy : Real = -44.9633308686316;
                                attribute sigma_Cy : Real = 28.23690002309109;
                                attribute Cz : Real = 36.01789614185691;
                                attribute sigma_Cz : Real = 29.057750463592832;
                                attribute Ixx : Real = 0.22734708184046687;
                                attribute sigma_Ixx : Real = 0.37074144170588635;
                                attribute Iyy : Real = 0.2076190436766494;
                                attribute sigma_Iyy : Real = 0.3723953238821935;
                                attribute Izz : Real = 0.23427637492602166;
                                attribute sigma_Izz : Real = 0.37017423652493897;
                                attribute Ixy : Real = -0.009973224396861505;
                                attribute sigma_Ixy : Real = 0.02351283871158888;
                                attribute Ixz : Real = 0.003016754044513954;
                                attribute sigma_Ixz : Real = 0.022566176940390956;
                                attribute Iyz : Real = -0.006980194161737406;
                                attribute sigma_Iyz : Real = 0.02209918015384651;
                            }
                            part <'C.1.2.1.4.5.1.2'> 'Part 903' {
                                attribute POIconv : String = "-";
                                attribute Ipoint : Boolean = false;
                                attribute mass : Real = 0.03630846361606382;
                                attribute sigma_mass : Real = 0.28909372274994966;
                                attribute Cx : Real = 18.450580164790154;
                                attribute sigma_Cx : Real = 28.721044428837228;
                                attribute Cy : Real = 49.28942285478115;
                                attribute sigma_Cy : Real = 28.23690002309109;
                                attribute Cz : Real = -47.71031131967902;
                                attribute sigma_Cz : Real = 29.057750463592832;
                                attribute Ixx : Real = 0.04831391835655754;
                                attribute sigma_Ixx : Real = 0.37074144170588635;
                                attribute Iyy : Real = 0.051327151170760706;
                                attribute sigma_Iyy : Real = 0.3723953238821935;
                                attribute Izz : Real = 0.05101950202499285;
                                attribute sigma_Izz : Real = 0.37017423652493897;
                                attribute Ixy : Real = -0.0025796904542062463;
                                attribute sigma_Ixy : Real = 0.02351283871158888;
                                attribute Ixz : Real = 0.0015706718858319703;
                                attribute sigma_Ixz : Real = 0.022566176940390956;
                                attribute Iyz : Real = -0.00013149686612232364;
                                attribute sigma_Iyz : Real = 0.02209918015384651;
                            }
                        }
                        part <'C.1.2.1.4.5.2'> 'Subassembly 257' {
                            attribute POIconv : String = "-";
                            attribute Ipoint : Boolean = false;
                            attribute mass : Real = 0.7849569855732843;
                            attribute sigma_mass : Real = 0.40884026350990615;
                            attribute Cx : Real = -35.54257794626428;
                            attribute sigma_Cx : Real = 36.1728336672106;
                            attribute Cy : Real = -3.7957220408574726;
                            attribute sigma_Cy : Real = 42.0387353277241;
                            attribute Cz : Real = 71.87748381793959;
                            attribute sigma_Cz : Real = 20.870544913442586;
                            attribute Ixx : Real = 3738.97492940781;
                            attribute sigma_Ixx : Real = 3029.547523238237;
                            attribute Iyy : Real = 2439.8420228928485;
                            attribute sigma_Iyy : Real = 2245.7236156954145;
                            attribute Izz : Real = 6164.482928800501;
                            attribute sigma_Izz : Real = 4491.952995426915;
                            attribute Ixy : Real = 3012.52385020532;
                            attribute sigma_Ixy : Real = 2217.7882505642997;
                            attribute Ixz : Real = 127.95426749229378;
                            attribute sigma_Ixz : Real = 890.2895187760834;
                            attribute Iyz : Real = -158.4561814122404;
                            attribute sigma_Iyz : Real = 1102.1862140469811;
                            part <'C.1.2.1.4.5.2.1'> 'Part 904' {
                                attribute POIconv : String = "-";
                                attribute Ipoint : Boolean = false;
                                attribute mass : Real = 0.4556970932257827;
                                attribute sigma_mass : Real = 0.28909372274994966;
                                attribute Cx : Real = -82.85814980044961;
                                attribute sigma_Cx : Real = 28.721044428837228;
                                attribute Cy : Real = 54.810406314209104;
                                attribute sigma_Cy : Real = 28.23690002309109;
                                attribute Cz : Real = 74.36641436070204;
                                attribute sigma_Cz : Real = 29.057750463592832;
                                attribute Ixx : Real = 0.5373910816917773;
                                attribute sigma_Ixx : Real = 0.37074144170588635;
                                attribute Iyy : Real = 0.5466813953993623;
                                attribute sigma_Iyy : Real = 0.3723953238821935;
                                attribute Izz : Real = 0.5760682400459038;
                                attribute sigma_Izz : Real = 0.37017423652493897;
                                attribute Ixy : Real = 0.012471985862480921;
                                attribute sigma_Ixy : Real = 0.02351283871158888;
                                attribute Ixz : Real = 0.008315407157988192;
                                attribute sigma_Ixz : Real = 0.022566176940390956;
                                attribute Iyz : Real = 0.007519354798033175;
                                attribute sigma_Iyz : Real = 0.02209918015384651;
                            }
                            part <'C.1.2.1.4.5.2.2'> 'Part 905' {
                                attribute POIconv : String = "+";
                                attribute Ipoint : Boolean = false;
                                attribute mass : Real = 0.3292598923475016;
                                attribute sigma_mass : Real = 0.28909372274994966;
                                attribute Cx : Real = 29.94237500242889;
                                attribute sigma_Cx : Real = 28.721044428837228;
                                attribute Cy : Real = -84.90685326978564;
                                attribute sigma_Cy : Real = 28.23690002309109;
                                attribute Cz : Real = 68.43279334716499;
                                attribute sigma_Cz : Real = 29.057750463592832;
                                attribute Ixx : Real = 0.3287548232186033;
                                attribute sigma_Ixx : Real = 0.37074144170588635;
                                attribute Iyy : Real = 0.4091890112585607;
                                attribute sigma_Iyy : Real = 0.3723953238821935;
                                attribute Izz : Real = 0.3717316520153332;
                                attribute sigma_Izz : Real = 0.37017423652493897;
                                attribute Ixy : Real = 0.011893074160816895;
                                attribute sigma_Ixy : Real = 0.02351283871158888;
                                attribute Ixz : Real = -0.00777580297754038;
                                attribute sigma_Ixz : Real = 0.022566176940390956;
                                attribute Iyz : Real = -0.0033934025539105067;
                                attribute sigma_Iyz : Real = 0.02209918015384651;
                            }
                        }
                        part <'C.1.2.1.4.5.3'> 'Subassembly 258' {
                            attribute POIconv : String = "-";
                            attribute Ipoint : Boolean = false;
                            attribute mass : Real = 0.3471185716001783;
                            attribute sigma_mass : Real = 0.40884026350990615;
                            attribute Cx : Real = -15.081905937143572;
                            attribute sigma_Cx : Real = 26.384163872510182;
                            attribute Cy : Real = 71.46303345292363;
                            attribute sigma_Cy : Real = 22.37726299548783;
                            attribute Cz : Real = -23.24055905383722;
                            attribute sigma_Cz : Real = 32.8324374589747;
                            attribute Ixx : Real = 82.17024158137258;
                            attribute sigma_Ixx : Real = 280.7821348422313;
                            attribute Iyy : Real = 108.6508111435903;
                            attribute sigma_Iyy : Real = 350.2325042955863;
                            attribute Izz : Real = 27.160156343545744;
                            attribute sigma_Izz : Real = 126.53976630352238;
                            attribute Ixy : Real = -1.6794212139436289;
                            attribute sigma_Ixy : Real = 52.67388120659763;
                            attribute Ixz : Real = 46.589492844943976;
                            attribute sigma_Ixz : Real = 160.13129864186322;
                            attribute Iyz : Real = 2.928616834007755;
                            attribute sigma_Iyz : Real = 92.126967411315;
                            part <'C.1.2.1.4.5.3.1'> 'Part 906' {
                                attribute POIconv : String = "-";
                                attribute Ipoint : Boolean = false;
                                attribute mass : Real = 0.08604126638337038;
                                attribute sigma_mass : Real = 0.28909372274994966;
                                attribute Cx : Real = 0.16682944260537624;
                                attribute sigma_Cx : Real = 28.721044428837228;
                                attribute Cy : Real = 72.42533755488694;
                                attribute sigma_Cy : Real = 28.23690002309109;
                                attribute Cz : Real = -49.94699549861252;
                                attribute sigma_Cz : Real = 29.057750463592832;
                                attribute Ixx : Real = 0.12348995040614347;
                                attribute sigma_Ixx : Real = 0.37074144170588635;
                                attribute Iyy : Real = 0.0969606623349993;
                                attribute sigma_Iyy : Real = 0.3723953238821935;
                                attribute Izz : Real = 0.10742809834243293;
                                attribute sigma_Izz : Real = 0.37017423652493897;
                                attribute Ixy : Real = 0.0001746850971018804;
                                attribute sigma_Ixy : Real = 0.02351283871158888;
                                attribute Ixz : Real = -0.005498840870320367;
                                attribute sigma_Ixz : Real = 0.022566176940390956;
                                attribute Iyz : Real = -0.0022803598221760703;
                                attribute sigma_Iyz : Real = 0.02209918015384651;
                            }
                            part <'C.1.2.1.4.5.3.2'> 'Part 907' {
                                attribute POIconv : String = "+";
                                attribute Ipoint : Boolean = false;
                                attribute mass : Real = 0.2610773052168079;
                                attribute sigma_mass : Real = 0.28909372274994966;
                                attribute Cx : Real = -20.107315946370363;
                                attribute sigma_Cx : Real = 28.721044428837228;
                                attribute Cy : Real = 71.14589419215918;
                                attribute sigma_Cy : Real = 28.23690002309109;
                                attribute Cz : Real = -14.439121447503567;
                                attribute sigma_Cz : Real = 29.057750463592832;
                                attribute Ixx : Real = 0.34884878494131816;
                                attribute sigma_Ixx : Real = 0.37074144170588635;
                                attribute Iyy : Real = 0.36178838477476194;
                                attribute sigma_Iyy : Real = 0.3723953238821935;
                                attribute Izz : Real = 0.34669864073993517;
                                attribute sigma_Izz : Real = 0.37017423652493897;
                                attribute Ixy : Real = 0.0009399749468557673;
                                attribute sigma_Ixy : Real = 0.02351283871158888;
                                attribute Ixz : Real = -0.007932919262221935;
                                attribute sigma_Ixz : Real = 0.022566176940390956;
                                attribute Iyz : Real = 0.009078917828234521;
                                attribute sigma_Iyz : Real = 0.02209918015384651;
                            }
                        }
                        part <'C.1.2.1.4.5.4'> 'Subassembly 259' {
                            attribute POIconv : String = "-";
                            attribute Ipoint : Boolean = false;
                            attribute mass : Real = 1.2760915947614704;
                            attribute sigma_mass : Real = 0.40884026350990615;
                            attribute Cx : Real = 1.5510917591468536;
                            attribute sigma_Cx : Real = 21.041134151525725;
                            attribute Cy : Real = -7.291807819500294;
                            attribute sigma_Cy : Real = 20.980586619958714;
                            attribute Cz : Real = -1.2751792356749982;
                            attribute sigma_Cz : Real = 27.382993139947885;
                            attribute Ixx : Real = 3369.7897592077143;
                            attribute sigma_Ixx : Real = 2941.57349273432;
                            attribute Iyy : Real = 3237.8352413412113;
                            attribute sigma_Iyy : Real = 2873.4751595342373;
                            attribute Izz : Real = 163.85327419921825;
                            attribute sigma_Izz : Real = 559.4382021519126;
                            attribute Ixy : Real = 47.49063348545526;
                            attribute sigma_Ixy : Real = 282.2511042682877;
                            attribute Ixz : Real = -221.90565245843908;
                            attribute sigma_Ixz : Real = 1262.0316713511215;
                            attribute Iyz : Real = 688.5557601021127;
                            attribute sigma_Iyz : Real = 1295.363349543793;
                            part <'C.1.2.1.4.5.4.1'> 'Part 908' {
                                attribute POIconv : String = "+";
                                attribute Ipoint : Boolean = false;
                                attribute mass : Real = 0.8068403077791445;
                                attribute sigma_mass : Real = 0.28909372274994966;
                                attribute Cx : Real = -1.0880951303988695;
                                attribute sigma_Cx : Real = 28.721044428837228;
                                attribute Cy : Real = 0.8990242145955563;
                                attribute sigma_Cy : Real = 28.23690002309109;
                                attribute Cz : Real = -39.590950217098;
                                attribute sigma_Cz : Real = 29.057750463592832;
                                attribute Ixx : Real = 0.7986237294814765;
                                attribute sigma_Ixx : Real = 0.37074144170588635;
                                attribute Iyy : Real = 0.8436211985908275;
                                attribute sigma_Iyy : Real = 0.3723953238821935;
                                attribute Izz : Real = 0.8312427565921664;
                                attribute sigma_Izz : Real = 0.37017423652493897;
                                attribute Ixy : Real = -0.030949503629324464;
                                attribute sigma_Ixy : Real = 0.02351283871158888;
                                attribute Ixz : Real = 0.05107112979500075;
                                attribute sigma_Ixz : Real = 0.022566176940390956;
                                attribute Iyz : Real = -0.019157663661828396;
                                attribute sigma_Iyz : Real = 0.02209918015384651;
                            }
                            part <'C.1.2.1.4.5.4.2'> 'Part 909' {
                                attribute POIconv : String = "-";
                                attribute Ipoint : Boolean = false;
                                attribute mass : Real = 0.4692512869823258;
                                attribute sigma_mass : Real = 0.28909372274994966;
                                attribute Cx : Real = 6.088963942602277;
                                attribute sigma_Cx : Real = 28.721044428837228;
                                attribute Cy : Real = -21.3752927724272;
                                attribute sigma_Cy : Real = 28.23690002309109;
                                attribute Cz : Real = 64.60574492812157;
                                attribute sigma_Cz : Real = 29.057750463592832;
                                attribute Ixx : Real = 0.57655092121534;
                                attribute sigma_Ixx : Real = 0.37074144170588635;
                                attribute Iyy : Real = 0.49832157986254155;
                                attribute sigma_Iyy : Real = 0.3723953238821935;
                                attribute Izz : Real = 0.5350523602865666;
                                attribute sigma_Izz : Real = 0.37017423652493897;
                                attribute Ixy : Real = 0.028700772204402966;
                                attribute sigma_Ixy : Real = 0.02351283871158888;
                                attribute Ixz : Real = 0.02210745199556042;
                                attribute sigma_Ixz : Real = 0.022566176940390956;
                                attribute Iyz : Real = -0.06741317046096157;
                                attribute sigma_Iyz : Real = 0.02209918015384651;
                            }
                        }
                        part <'C.1.2.1.4.5.5'> 'Subassembly 260' {
                            attribute POIconv : String = "-";
                            attribute Ipoint : Boolean = false;
                            attribute mass : Real = 3.1920655626044607;
                            attribute sigma_mass : Real = 0.6464332159373649;
                            attribute Cx : Real = 54.813238070189485;
                            attribute sigma_Cx : Real = 18.47547767674796;
                            attribute Cy : Real = 11.317780434125954;
                            attribute sigma_Cy : Real = 22.429739275040248;
                            attribute Cz : Real = -55.58687295320634;
                            attribute sigma_Cz : Real = 17.6690918509872;
                            attribute Ixx : Real = 22827.00506759876;
                            attribute sigma_Ixx : Real = 10364.890455167297;
                            attribute Iyy : Real = 10017.300792050612;
                            attribute sigma_Iyy : Real = 6973.075929833251;
                            attribute Izz : Real = 25452.921428099082;
                            attribute sigma_Izz : Real = 10949.312778589765;
                            attribute Ixy : Real = -3754.7339411115536;
                            attribute sigma_Ixy : Real = 5320.585115606031;
                            attribute Ixz : Real = 1856.6165823580495;
                            attribute sigma_Ixz : Real = 3416.530648116768;
                            attribute Iyz : Real = -652.7143246381997;
                            attribute sigma_Iyz : Real = 4888.867279485089;
                            part <'C.1.2.1.4.5.5.1'> 'Part 910' {
                                attribute POIconv : String = "+";
                                attribute Ipoint : Boolean = false;
                                attribute mass : Real = 0.05411040050140582;
                                attribute sigma_mass : Real = 0.28909372274994966;
                                attribute Cx : Real = -31.49070292711258;
                                attribute sigma_Cx : Real = 28.721044428837228;
                                attribute Cy : Real = -95.90522358193994;
                                attribute sigma_Cy : Real = 28.23690002309109;
                                attribute Cz : Real = 35.6134373228997;
                                attribute sigma_Cz : Real = 29.057750463592832;
                                attribute Ixx : Real = 0.06452898808547211;
                                attribute sigma_Ixx : Real = 0.37074144170588635;
                                attribute Iyy : Real = 0.07071973036627267;
                                attribute sigma_Iyy : Real = 0.3723953238821935;
                                attribute Izz : Real = 0.05949398525096096;
                                attribute sigma_Izz : Real = 0.37017423652493897;
                                attribute Ixy : Real = 0.004295690846381135;
                                attribute sigma_Ixy : Real = 0.02351283871158888;
                                attribute Ixz : Real = 0.0003341978864272371;
                                attribute sigma_Ixz : Real = 0.022566176940390956;
                                attribute Iyz : Real = -0.0006686160451230072;
                                attribute sigma_Iyz : Real = 0.02209918015384651;
                            }
                            part <'C.1.2.1.4.5.5.2'> 'Part 911' {
                                attribute POIconv : String = "+";
                                attribute Ipoint : Boolean = false;
                                attribute mass : Real = 0.9242297377332579;
                                attribute sigma_mass : Real = 0.28909372274994966;
                                attribute Cx : Real = 28.850201843306422;
                                attribute sigma_Cx : Real = 28.721044428837228;
                                attribute Cy : Real = 59.65702119283378;
                                attribute sigma_Cy : Real = 28.23690002309109;
                                attribute Cz : Real = -10.29543704353273;
                                attribute sigma_Cz : Real = 29.057750463592832;
                                attribute Ixx : Real = 1.3496659670435212;
                                attribute sigma_Ixx : Real = 0.37074144170588635;
                                attribute Iyy : Real = 1.1661099603608587;
                                attribute sigma_Iyy : Real = 0.3723953238821935;
                                attribute Izz : Real = 1.2270295291901012;
                                attribute sigma_Izz : Real = 0.37017423652493897;
                                attribute Ixy : Real = 0.1226870384290793;
                                attribute sigma_Ixy : Real = 0.02351283871158888;
                                attribute Ixz : Real = 0.002985209822428875;
                                attribute sigma_Ixz : Real = 0.022566176940390956;
                                attribute Iyz : Real = -0.0014710157500724868;
                                attribute sigma_Iyz : Real = 0.02209918015384651;
                            }
                            part <'C.1.2.1.4.5.5.3'> 'Part 912' {
                                attribute POIconv : String = "+";
                                attribute Ipoint : Boolean = false;
                                attribute mass : Real = 0.7754282531798817;
                                attribute sigma_mass : Real = 0.28909372274994966;
                                attribute Cx : Real = 92.87134446203709;
                                attribute sigma_Cx : Real = 28.721044428837228;
                                attribute Cy : Real = -68.52519162930548;
                                attribute sigma_Cy : Real = 28.23690002309109;
                                attribute Cz : Real = -59.747326048091054;
                                attribute sigma_Cz : Real = 29.057750463592832;
                                attribute Ixx : Real = 1.0911166716455396;
                                attribute sigma_Ixx : Real = 0.37074144170588635;
                                attribute Iyy : Real = 1.1007192810350237;
                                attribute sigma_Iyy : Real = 0.3723953238821935;
                                attribute Izz : Real = 1.0795607138371808;
                                attribute sigma_Izz : Real = 0.37017423652493897;
                                attribute Ixy : Real = -0.014754331565705572;
                                attribute sigma_Ixy : Real = 0.02351283871158888;
                                attribute Ixz : Real = 0.0149293794165677;
                                attribute sigma_Ixz : Real = 0.022566176940390956;
                                attribute Iyz : Real = 0.011358750116650218;
                                attribute sigma_Iyz : Real = 0.02209918015384651;
                            }
                            part <'C.1.2.1.4.5.5.4'> 'Part 913' {
                                attribute POIconv : String = "+";
                                attribute Ipoint : Boolean = false;
                                attribute mass : Real = 0.5277832171006593;
                                attribute sigma_mass : Real = 0.28909372274994966;
                                attribute Cx : Real = -16.497942758724093;
                                attribute sigma_Cx : Real = 28.721044428837228;
                                attribute Cy : Real = -87.71315040066838;
                                attribute sigma_Cy : Real = 28.23690002309109;
                                attribute Cz : Real = -81.69335275888443;
                                attribute sigma_Cz : Real = 29.057750463592832;
                                attribute Ixx : Real = 0.6284057323342536;
                                attribute sigma_Ixx : Real = 0.37074144170588635;
                                attribute Iyy : Real = 0.5303161842795756;
                                attribute sigma_Iyy : Real = 0.3723953238821935;
                                attribute Izz : Real = 0.6409211170850135;
                                attribute sigma_Izz : Real = 0.37017423652493897;
                                attribute Ixy : Real = -0.06409805373840372;
                                attribute sigma_Ixy : Real = 0.02351283871158888;
                                attribute Ixz : Real = -0.00298168478519825;
                                attribute sigma_Ixz : Real = 0.022566176940390956;
                                attribute Iyz : Real = 0.04669028045524837;
                                attribute sigma_Iyz : Real = 0.02209918015384651;
                            }
                            part <'C.1.2.1.4.5.5.5'> 'Part 914' {
                                attribute POIconv : String = "+";
                                attribute Ipoint : Boolean = false;
                                attribute mass : Real = 0.910513954089256;
                                attribute sigma_mass : Real = 0.28909372274994966;
                                attribute Cx : Real = 95.22037766873837;
                                attribute sigma_Cx : Real = 28.721044428837228;
                                attribute Cy : Real = 94.02346019633114;
                                attribute sigma_Cy : Real = 28.23690002309109;
                                attribute Cz : Real = -88.30452910624444;
                                attribute sigma_Cz : Real = 29.057750463592832;
                                attribute Ixx : Real = 0.9713111976167066;
                                attribute sigma_Ixx : Real = 0.37074144170588635;
                                attribute Iyy : Real = 0.9559105266824719;
                                attribute sigma_Iyy : Real = 0.3723953238821935;
                                attribute Izz : Real = 1.008727936764042;
                                attribute sigma_Izz : Real = 0.37017423652493897;
                                attribute Ixy : Real = 0.11407276798272098;
                                attribute sigma_Ixy : Real = 0.02351283871158888;
                                attribute Ixz : Real = 0.011828437228512768;
                                attribute sigma_Ixz : Real = 0.022566176940390956;
                                attribute Iyz : Real = 0.030549192355939177;
                                attribute sigma_Iyz : Real = 0.02209918015384651;
                            }
                        }
                    }
                }
            }
            part <'C.1.2.2'> 'Element 6' {
                attribute POIconv : String = "-";
                attribute Ipoint : Boolean = false;
                attribute mass : Real = 52.580994505537674;
                attribute sigma_mass : Real = 2.9339808443380724;
                attribute Cx : Real = -9.505755390385097;
                attribute sigma_Cx : Real = 4.643957092838555;
                attribute Cy : Real = 0.8066804806805336;
                attribute sigma_Cy : Real = 4.929917667343192;
                attribute Cz : Real = 9.891200771235797;
                attribute sigma_Cz : Real = 4.645236591889178;
                attribute Ixx : Real = 374800.4340847049;
                attribute sigma_Ixx : Real = 39940.49411607027;
                attribute Iyy : Real = 326990.8212879377;
                attribute sigma_Iyy : Real = 35944.96949162367;
                attribute Izz : Real = 392294.9078249987;
                attribute sigma_Izz : Real = 40159.02435648014;
                attribute Ixy : Real = 3136.1398833046187;
                attribute sigma_Ixy : Real = 18836.729705177313;
                attribute Ixz : Real = -4233.584838408355;
                attribute sigma_Ixz : Real = 16548.193591375555;
                attribute Iyz : Real = -2976.2181745517864;
                attribute sigma_Iyz : Real = 18839.51295024188;
                part <'C.1.2.2.1'> 'Subsystem 20' {
                    attribute POIconv : String = "-";
                    attribute Ipoint : Boolean = false;
                    attribute mass : Real = 13.054173515830888;
                    attribute sigma_mass : Real = 1.416264217158011;
                    attribute Cx : Real = -28.539456552231407;
                    attribute sigma_Cx : Real = 9.482849883726471;
                    attribute Cy : Real = -17.327481221970753;
                    attribute sigma_Cy : Real = 8.732161294055965;
                    attribute Cz : Real = 27.74660369937698;
                    attribute sigma_Cz : Real = 8.660618427292208;
                    attribute Ixx : Real = 54230.0838824867;
                    attribute sigma_Ixx : Real = 14493.413728054584;
                    attribute Iyy : Real = 65619.65502881723;
                    attribute sigma_Iyy : Real = 16818.654748052108;
                    attribute Izz : Real = 75610.26122618516;
                    attribute sigma_Izz : Real = 17420.311760673878;
                    attribute Ixy : Real = -12474.871569719318;
                    attribute sigma_Ixy : Real = 8324.310141124724;
                    attribute Ixz : Real = -10240.467867492032;
                    attribute sigma_Ixz : Real = 7513.0169946019105;
                    attribute Iyz : Real = 1706.8021011158803;
                    attribute sigma_Iyz : Real = 6403.634488702549;
                    part <'C.1.2.2.1.1'> 'Assembly 75' {
                        attribute POIconv : String = "-";
                        attribute Ipoint : Boolean = false;
                        attribute mass : Real = 6.5074355053801565;
                        attribute sigma_mass : Real = 1.0423422407897138;
                        attribute Cx : Real = -16.95152169899038;
                        attribute sigma_Cx : Real = 13.60294034143556;
                        attribute Cy : Real = -4.111638775841815;
                        attribute sigma_Cy : Real = 11.944599920748495;
                        attribute Cz : Real = 22.101160942736783;
                        attribute sigma_Cz : Real = 12.032297779613302;
                        attribute Ixx : Real = 24050.851539173644;
                        attribute sigma_Ixx : Real = 9524.20842006855;
                        attribute Iyy : Real = 35190.19718898317;
                        attribute sigma_Iyy : Real = 11767.409972820411;
                        attribute Izz : Real = 40380.931170119984;
                        attribute sigma_Izz : Real = 12650.210478205981;
                        attribute Ixy : Real = -8578.49836127396;
                        attribute sigma_Ixy : Real = 6026.928125412929;
                        attribute Ixz : Real = -2800.4479964572406;
                        attribute sigma_Ixz : Real = 4803.114619669386;
                        attribute Iyz : Real = -3199.2154057236394;
                        attribute sigma_Iyz : Real = 4183.901210734602;
                        part <'C.1.2.2.1.1.1'> 'Subassembly 261' {
                            attribute POIconv : String = "-";
                            attribute Ipoint : Boolean = false;
                            attribute mass : Real = 1.7584003097366077;
                            attribute sigma_mass : Real = 0.5781874454998993;
                            attribute Cx : Real = -32.06555886160362;
                            attribute sigma_Cx : Real = 29.182615328667666;
                            attribute Cy : Real = -30.240082912305827;
                            attribute sigma_Cy : Real = 21.20040816394241;
                            attribute Cz : Real = 25.24264440743736;
                            attribute sigma_Cz : Real = 27.764193960120547;
                            attribute Ixx : Real = 6826.152935264664;
                            attribute sigma_Ixx : Real = 5898.675083446934;
                            attribute Iyy : Real = 14965.81105119262;
                            attribute sigma_Iyy : Real = 8295.806676289994;
                            attribute Izz : Real = 16122.39899169483;
                            attribute sigma_Izz : Real = 7722.2859980365165;
                            attribute Ixy : Real = -6798.974785985633;
                            attribute sigma_Ixy : Real = 3586.6163926354557;
                            attribute Ixz : Real = -3433.6117318928295;
                            attribute sigma_Ixz : Real = 3191.3540158712135;
                            attribute Iyz : Real = -1967.3686454623194;
                            attribute sigma_Iyz : Real = 2075.3209016135474;
                            part <'C.1.2.2.1.1.1.1'> 'Part 915' {
                                attribute POIconv : String = "-";
                                attribute Ipoint : Boolean = false;
                                attribute mass : Real = 0.36086366243776863;
                                attribute sigma_mass : Real = 0.28909372274994966;
                                attribute Cx : Real = -96.05082822963595;
                                attribute sigma_Cx : Real = 28.721044428837228;
                                attribute Cy : Real = -54.78245229460299;
                                attribute sigma_Cy : Real = 28.23690002309109;
                                attribute Cz : Real = 55.986605025827885;
                                attribute sigma_Cz : Real = 29.057750463592832;
                                attribute Ixx : Real = 0.3860246912287275;
                                attribute sigma_Ixx : Real = 0.37074144170588635;
                                attribute Iyy : Real = 0.39453440759335656;
                                attribute sigma_Iyy : Real = 0.3723953238821935;
                                attribute Izz : Real = 0.3866428853829205;
                                attribute sigma_Izz : Real = 0.37017423652493897;
                                attribute Ixy : Real = 0.017560447715276668;
                                attribute sigma_Ixy : Real = 0.02351283871158888;
                                attribute Ixz : Real = -0.01578187406659621;
                                attribute sigma_Ixz : Real = 0.022566176940390956;
                                attribute Iyz : Real = -0.014754927220251481;
                                attribute sigma_Iyz : Real = 0.02209918015384651;
                            }
                            part <'C.1.2.2.1.1.1.2'> 'Part 916' {
                                attribute POIconv : String = "+";
                                attribute Ipoint : Boolean = false;
                                attribute mass : Real = 0.6230471224761568;
                                attribute sigma_mass : Real = 0.28909372274994966;
                                attribute Cx : Real = 79.72097382880747;
                                attribute sigma_Cx : Real = 28.721044428837228;
                                attribute Cy : Real = 31.737680453807116;
                                attribute sigma_Cy : Real = 28.23690002309109;
                                attribute Cz : Real = 59.28669576533139;
                                attribute sigma_Cz : Real = 29.057750463592832;
                                attribute Ixx : Real = 0.7365694227711755;
                                attribute sigma_Ixx : Real = 0.37074144170588635;
                                attribute Iyy : Real = 0.7295201248252913;
                                attribute sigma_Iyy : Real = 0.3723953238821935;
                                attribute Izz : Real = 0.618345636521789;
                                attribute sigma_Izz : Real = 0.37017423652493897;
                                attribute Ixy : Real = -0.004303659115087235;
                                attribute sigma_Ixy : Real = 0.02351283871158888;
                                attribute Ixz : Real = -0.029245930707172872;
                                attribute sigma_Ixz : Real = 0.022566176940390956;
                                attribute Iyz : Real = 0.013223996752649222;
                                attribute sigma_Iyz : Real = 0.02209918015384651;
                            }
                            part <'C.1.2.2.1.1.1.3'> 'Part 917' {
                                attribute POIconv : String = "+";
                                attribute Ipoint : Boolean = false;
                                attribute mass : Real = 0.06109494648454711;
                                attribute sigma_mass : Real = 0.28909372274994966;
                                attribute Cx : Real = -60.14827489852905;
                                attribute sigma_Cx : Real = 28.721044428837228;
                                attribute Cy : Real = -8.96461522206664;
                                attribute sigma_Cy : Real = 28.23690002309109;
                                attribute Cz : Real = -96.33653969503939;
                                attribute sigma_Cz : Real = 29.057750463592832;
                                attribute Ixx : Real = 0.07257276811325816;
                                attribute sigma_Ixx : Real = 0.37074144170588635;
                                attribute Iyy : Real = 0.07149315115337382;
                                attribute sigma_Iyy : Real = 0.3723953238821935;
                                attribute Izz : Real = 0.0718609471865199;
                                attribute sigma_Izz : Real = 0.37017423652493897;
                                attribute Ixy : Real = -0.002870623075422591;
                                attribute sigma_Ixy : Real = 0.02351283871158888;
                                attribute Ixz : Real = -0.006649221059225049;
                                attribute sigma_Ixz : Real = 0.022566176940390956;
                                attribute Iyz : Real = 0.006603619038093246;
                                attribute sigma_Iyz : Real = 0.02209918015384651;
                            }
                            part <'C.1.2.2.1.1.1.4'> 'Part 918' {
                                attribute POIconv : String = "-";
                                attribute Ipoint : Boolean = false;
                                attribute mass : Real = 0.713394578338135;
                                attribute sigma_mass : Real = 0.28909372274994966;
                                attribute Cx : Real = -94.92362956516445;
                                attribute sigma_Cx : Real = 28.721044428837228;
                                attribute Cy : Real = -73.7762161064893;
                                attribute sigma_Cy : Real = 28.23690002309109;
                                attribute Cz : Real = -9.6294354647398;
                                attribute sigma_Cz : Real = 29.057750463592832;
                                attribute Ixx : Real = 0.7032529255843124;
                                attribute sigma_Ixx : Real = 0.37074144170588635;
                                attribute Iyy : Real = 0.7552442876030476;
                                attribute sigma_Iyy : Real = 0.3723953238821935;
                                attribute Izz : Real = 0.8113232026448255;
                                attribute sigma_Izz : Real = 0.37017423652493897;
                                attribute Ixy : Real = 0.09836509643646447;
                                attribute sigma_Ixy : Real = 0.02351283871158888;
                                attribute Ixz : Real = -0.04925069913912512;
                                attribute sigma_Ixz : Real = 0.022566176940390956;
                                attribute Iyz : Real = 0.03789759159950372;
                                attribute sigma_Iyz : Real = 0.02209918015384651;
                            }
                        }
                        part <'C.1.2.2.1.1.2'> 'Subassembly 262' {
                            attribute POIconv : String = "-";
                            attribute Ipoint : Boolean = false;
                            attribute mass : Real = 2.3866064461229834;
                            attribute sigma_mass : Real = 0.6464332159373649;
                            attribute Cx : Real = 9.868711754552402;
                            attribute sigma_Cx : Real = 19.11250661414788;
                            attribute Cy : Real = 5.389553225418541;
                            attribute sigma_Cy : Real = 21.803610403289635;
                            attribute Cz : Real = 18.405686668023154;
                            attribute sigma_Cz : Real = 20.177514484485727;
                            attribute Ixx : Real = 12508.972539221702;
                            attribute sigma_Ixx : Real = 6590.530376350633;
                            attribute Iyy : Real = 9067.063820903839;
                            attribute sigma_Iyy : Real = 5250.296833319436;
                            attribute Izz : Real = 10271.423022959583;
                            attribute sigma_Izz : Real = 6417.0315258364935;
                            attribute Ixy : Real = -4559.30878309368;
                            attribute sigma_Ixy : Real = 3150.8093095015042;
                            attribute Ixz : Real = 236.82330717108897;
                            attribute sigma_Ixz : Real = 2544.8924583587054;
                            attribute Iyz : Real = -1006.260515787287;
                            attribute sigma_Iyz : Real = 3137.6759802703127;
                            part <'C.1.2.2.1.1.2.1'> 'Part 919' {
                                attribute POIconv : String = "+";
                                attribute Ipoint : Boolean = false;
                                attribute mass : Real = 0.8259045990500599;
                                attribute sigma_mass : Real = 0.28909372274994966;
                                attribute Cx : Real = 14.283949974924326;
                                attribute sigma_Cx : Real = 28.721044428837228;
                                attribute Cy : Real = -13.152746018022299;
                                attribute sigma_Cy : Real = 28.23690002309109;
                                attribute Cz : Real = -27.273988351225853;
                                attribute sigma_Cz : Real = 29.057750463592832;
                                attribute Ixx : Real = 1.0355150587577753;
                                attribute sigma_Ixx : Real = 0.37074144170588635;
                                attribute Iyy : Real = 1.0395092993226673;
                                attribute sigma_Iyy : Real = 0.3723953238821935;
                                attribute Izz : Real = 1.3190653100202023;
                                attribute sigma_Izz : Real = 0.37017423652493897;
                                attribute Ixy : Real = -0.0022686051785832393;
                                attribute sigma_Ixy : Real = 0.02351283871158888;
                                attribute Ixz : Real = 0.027544862143464882;
                                attribute sigma_Ixz : Real = 0.022566176940390956;
                                attribute Iyz : Real = 0.044601215615107714;
                                attribute sigma_Iyz : Real = 0.02209918015384651;
                            }
                            part <'C.1.2.2.1.1.2.2'> 'Part 920' {
                                attribute POIconv : String = "-";
                                attribute Ipoint : Boolean = false;
                                attribute mass : Real = 0.7616543880011887;
                                attribute sigma_mass : Real = 0.28909372274994966;
                                attribute Cx : Real = 47.759889578446746;
                                attribute sigma_Cx : Real = 28.721044428837228;
                                attribute Cy : Real = 70.23149468004704;
                                attribute sigma_Cy : Real = 28.23690002309109;
                                attribute Cz : Real = 64.2881260253489;
                                attribute sigma_Cz : Real = 29.057750463592832;
                                attribute Ixx : Real = 0.8365410239384761;
                                attribute sigma_Ixx : Real = 0.37074144170588635;
                                attribute Iyy : Real = 0.9492416930287492;
                                attribute sigma_Iyy : Real = 0.3723953238821935;
                                attribute Izz : Real = 0.8685955399659884;
                                attribute sigma_Izz : Real = 0.37017423652493897;
                                attribute Ixy : Real = -0.003347153783754152;
                                attribute sigma_Ixy : Real = 0.02351283871158888;
                                attribute Ixz : Real = -0.011975874145181647;
                                attribute sigma_Ixz : Real = 0.022566176940390956;
                                attribute Iyz : Real = 0.005839179218359931;
                                attribute sigma_Iyz : Real = 0.02209918015384651;
                            }
                            part <'C.1.2.2.1.1.2.3'> 'Part 921' {
                                attribute POIconv : String = "+";
                                attribute Ipoint : Boolean = false;
                                attribute mass : Real = 0.021379657721845434;
                                attribute sigma_mass : Real = 0.28909372274994966;
                                attribute Cx : Real = 57.531608222052455;
                                attribute sigma_Cx : Real = 28.721044428837228;
                                attribute Cy : Real = 73.42850370332599;
                                attribute sigma_Cy : Real = 28.23690002309109;
                                attribute Cz : Real = 61.6898390930146;
                                attribute sigma_Cz : Real = 29.057750463592832;
                                attribute Ixx : Real = 0.021527752953343134;
                                attribute sigma_Ixx : Real = 0.37074144170588635;
                                attribute Iyy : Real = 0.02619449818308588;
                                attribute sigma_Iyy : Real = 0.3723953238821935;
                                attribute Izz : Real = 0.028343739182350582;
                                attribute sigma_Izz : Real = 0.37017423652493897;
                                attribute Ixy : Real = 0.0008116811288694989;
                                attribute sigma_Ixy : Real = 0.02351283871158888;
                                attribute Ixz : Real = 0.0006632069751084687;
                                attribute sigma_Ixz : Real = 0.022566176940390956;
                                attribute Iyz : Real = 0.000113792767616614;
                                attribute sigma_Iyz : Real = 0.02209918015384651;
                            }
                            part <'C.1.2.2.1.1.2.4'> 'Part 922' {
                                attribute POIconv : String = "+";
                                attribute Ipoint : Boolean = false;
                                attribute mass : Real = 0.3944050546500366;
                                attribute sigma_mass : Real = 0.28909372274994966;
                                attribute Cx : Real = -65.04850061610341;
                                attribute sigma_Cx : Real = 28.721044428837228;
                                attribute Cy : Real = -85.6566856149584;
                                attribute sigma_Cy : Real = 28.23690002309109;
                                attribute Cz : Real = 74.16435056366026;
                                attribute sigma_Cz : Real = 29.057750463592832;
                                attribute Ixx : Real = 0.5517367652677677;
                                attribute sigma_Ixx : Real = 0.37074144170588635;
                                attribute Iyy : Real = 0.4595055453477788;
                                attribute sigma_Iyy : Real = 0.3723953238821935;
                                attribute Izz : Real = 0.5089780501031764;
                                attribute sigma_Izz : Real = 0.37017423652493897;
                                attribute Ixy : Real = -0.0018066614633099939;
                                attribute sigma_Ixy : Real = 0.02351283871158888;
                                attribute Ixz : Real = -0.0039876135243384495;
                                attribute sigma_Ixz : Real = 0.022566176940390956;
                                attribute Iyz : Real = 0.003396071970097911;
                                attribute sigma_Iyz : Real = 0.02209918015384651;
                            }
                            part <'C.1.2.2.1.1.2.5'> 'Part 923' {
                                attribute POIconv : String = "-";
                                attribute Ipoint : Boolean = false;
                                attribute mass : Real = 0.3832627466998529;
                                attribute sigma_mass : Real = 0.28909372274994966;
                                attribute Cx : Real = -0.5101643968373537;
                                attribute sigma_Cx : Real = 28.721044428837228;
                                attribute Cy : Real = 6.384871248155832;
                                attribute sigma_Cy : Real = 28.23690002309109;
                                attribute Cz : Real = -34.1337448451668;
                                attribute sigma_Cz : Real = 29.057750463592832;
                                attribute Ixx : Real = 0.4477798341795467;
                                attribute sigma_Ixx : Real = 0.37074144170588635;
                                attribute Iyy : Real = 0.4419436298176441;
                                attribute sigma_Iyy : Real = 0.3723953238821935;
                                attribute Izz : Real = 0.5115002617604051;
                                attribute sigma_Izz : Real = 0.37017423652493897;
                                attribute Ixy : Real = -0.004129105121358612;
                                attribute sigma_Ixy : Real = 0.02351283871158888;
                                attribute Ixz : Real = 0.010683859248127748;
                                attribute sigma_Ixz : Real = 0.022566176940390956;
                                attribute Iyz : Real = 0.008836181083328244;
                                attribute sigma_Iyz : Real = 0.02209918015384651;
                            }
                        }
                        part <'C.1.2.2.1.1.3'> 'Subassembly 263' {
                            attribute POIconv : String = "-";
                            attribute Ipoint : Boolean = false;
                            attribute mass : Real = 2.3624287495205647;
                            attribute sigma_mass : Real = 0.5781874454998993;
                            attribute Cx : Real = -32.796577100655064;
                            attribute sigma_Cx : Real = 21.835979659669672;
                            attribute Cy : Real = 5.737825759821346;
                            attribute sigma_Cy : Real = 17.172627031217715;
                            attribute Cz : Real = 23.496190201849938;
                            attribute sigma_Cz : Real = 15.943675475202364;
                            attribute Ixx : Real = 3016.1010016756386;
                            attribute sigma_Ixx : Real = 2582.579574420686;
                            attribute Iyy : Real = 8391.229365292425;
                            attribute sigma_Iyy : Real = 5524.8601454403515;
                            attribute Izz : Real = 9630.478761189213;
                            attribute sigma_Izz : Real = 6492.0990832170055;
                            attribute Ixy : Real = 3713.6603958516716;
                            attribute sigma_Ixy : Real = 2919.4014898818045;
                            attribute Ixz : Real = 24.08595793157673;
                            attribute sigma_Ixz : Real = 1943.0232107626637;
                            attribute Iyz : Real = -421.2560508797337;
                            attribute sigma_Iyz : Real = 1149.8662039027026;
                            part <'C.1.2.2.1.1.3.1'> 'Part 924' {
                                attribute POIconv : String = "+";
                                attribute Ipoint : Boolean = false;
                                attribute mass : Real = 0.9098902928296011;
                                attribute sigma_mass : Real = 0.28909372274994966;
                                attribute Cx : Real = -67.32482938095927;
                                attribute sigma_Cx : Real = 28.721044428837228;
                                attribute Cy : Real = 13.133474811911583;
                                attribute sigma_Cy : Real = 28.23690002309109;
                                attribute Cz : Real = 2.206150349229574;
                                attribute sigma_Cz : Real = 29.057750463592832;
                                attribute Ixx : Real = 1.361844708158152;
                                attribute sigma_Ixx : Real = 0.37074144170588635;
                                attribute Iyy : Real = 1.3298241465574654;
                                attribute sigma_Iyy : Real = 0.3723953238821935;
                                attribute Izz : Real = 1.3458447578579866;
                                attribute sigma_Izz : Real = 0.37017423652493897;
                                attribute Ixy : Real = -0.01226606230409862;
                                attribute sigma_Ixy : Real = 0.02351283871158888;
                                attribute Ixz : Real = -0.028852209553286642;
                                attribute sigma_Ixz : Real = 0.022566176940390956;
                                attribute Iyz : Real = -0.010151314568700009;
                                attribute sigma_Iyz : Real = 0.02209918015384651;
                            }
                            part <'C.1.2.2.1.1.3.2'> 'Part 925' {
                                attribute POIconv : String = "-";
                                attribute Ipoint : Boolean = false;
                                attribute mass : Real = 0.48804895440395923;
                                attribute sigma_mass : Real = 0.28909372274994966;
                                attribute Cx : Real = -74.20310853049159;
                                attribute sigma_Cx : Real = 28.721044428837228;
                                attribute Cy : Real = 29.36070477589965;
                                attribute sigma_Cy : Real = 28.23690002309109;
                                attribute Cz : Real = 48.44129062257707;
                                attribute sigma_Cz : Real = 29.057750463592832;
                                attribute Ixx : Real = 0.645321086113301;
                                attribute sigma_Ixx : Real = 0.37074144170588635;
                                attribute Iyy : Real = 0.6826182242447267;
                                attribute sigma_Iyy : Real = 0.3723953238821935;
                                attribute Izz : Real = 0.6597736995008983;
                                attribute sigma_Izz : Real = 0.37017423652493897;
                                attribute Ixy : Real = 0.021845674250418168;
                                attribute sigma_Ixy : Real = 0.02351283871158888;
                                attribute Ixz : Real = 0.01922806005937716;
                                attribute sigma_Ixz : Real = 0.022566176940390956;
                                attribute Iyz : Real = -0.02907158346786725;
                                attribute sigma_Iyz : Real = 0.02209918015384651;
                            }
                            part <'C.1.2.2.1.1.3.3'> 'Part 926' {
                                attribute POIconv : String = "+";
                                attribute Ipoint : Boolean = false;
                                attribute mass : Real = 0.5580423413272947;
                                attribute sigma_mass : Real = 0.28909372274994966;
                                attribute Cx : Real = -25.388148706406355;
                                attribute sigma_Cx : Real = 28.721044428837228;
                                attribute Cy : Real = 19.993044063448906;
                                attribute sigma_Cy : Real = 28.23690002309109;
                                attribute Cz : Real = 40.35831596702337;
                                attribute sigma_Cz : Real = 29.057750463592832;
                                attribute Ixx : Real = 0.6745063598180404;
                                attribute sigma_Ixx : Real = 0.37074144170588635;
                                attribute Iyy : Real = 0.6784042269102898;
                                attribute sigma_Iyy : Real = 0.3723953238821935;
                                attribute Izz : Real = 0.6459669176582017;
                                attribute sigma_Izz : Real = 0.37017423652493897;
                                attribute Ixy : Real = 0.040450960801018926;
                                attribute sigma_Ixy : Real = 0.02351283871158888;
                                attribute Ixz : Real = -0.02030124017871201;
                                attribute sigma_Ixz : Real = 0.022566176940390956;
                                attribute Iyz : Real = 0.06462954329343132;
                                attribute sigma_Iyz : Real = 0.02209918015384651;
                            }
                            part <'C.1.2.2.1.1.3.4'> 'Part 927' {
                                attribute POIconv : String = "-";
                                attribute Ipoint : Boolean = false;
                                attribute mass : Real = 0.40644716095970945;
                                attribute sigma_mass : Real = 0.28909372274994966;
                                attribute Cx : Real = 84.04793255031109;
                                attribute sigma_Cx : Real = 28.721044428837228;
                                attribute Cy : Real = -58.756082924082875;
                                attribute sigma_Cy : Real = 28.23690002309109;
                                attribute Cz : Real = 18.052408238872886;
                                attribute sigma_Cz : Real = 29.057750463592832;
                                attribute Ixx : Real = 0.4699585397163946;
                                attribute sigma_Ixx : Real = 0.37074144170588635;
                                attribute Iyy : Real = 0.47379991403944666;
                                attribute sigma_Iyy : Real = 0.3723953238821935;
                                attribute Izz : Real = 0.4698722999414431;
                                attribute sigma_Izz : Real = 0.37017423652493897;
                                attribute Ixy : Real = -0.016463384559653734;
                                attribute sigma_Ixy : Real = 0.02351283871158888;
                                attribute Ixz : Real = -0.0354527632987033;
                                attribute sigma_Ixz : Real = 0.022566176940390956;
                                attribute Iyz : Real = -0.004649885440174157;
                                attribute sigma_Iyz : Real = 0.02209918015384651;
                            }
                        }
                    }
                    part <'C.1.2.2.1.2'> 'Assembly 76' {
                        attribute POIconv : String = "-";
                        attribute Ipoint : Boolean = false;
                        attribute mass : Real = 6.546738010450731;
                        attribute sigma_mass : Real = 0.9588154076086138;
                        attribute Cx : Real = -40.0578247193457;
                        attribute sigma_Cx : Real = 12.9794818897398;
                        attribute Cy : Real = -30.46398404676129;
                        attribute sigma_Cy : Real = 12.412883111455383;
                        attribute Cz : Real = 33.358154761830804;
                        attribute sigma_Cz : Real = 12.397593054472079;
                        attribute Ixx : Real = 27499.345736626463;
                        attribute sigma_Ixx : Real = 10434.229181014436;
                        attribute Iyy : Real = 28273.511605306463;
                        attribute sigma_Iyy : Real = 11605.536690782841;
                        attribute Izz : Real = 31220.601563034063;
                        attribute sigma_Izz : Real = 11244.112324653708;
                        attribute Ixy : Real = -1909.2024421760468;
                        attribute sigma_Ixy : Real = 5349.925148852048;
                        attribute Ixz : Real = -8288.884319470179;
                        attribute sigma_Ixz : Real = 5585.041099390735;
                        attribute Iyz : Real = 3937.902053074733;
                        attribute sigma_Iyz : Real = 4569.721853642768;
                        part <'C.1.2.2.1.2.1'> 'Subassembly 264' {
                            attribute POIconv : String = "-";
                            attribute Ipoint : Boolean = false;
                            attribute mass : Real = 2.576666848515859;
                            attribute sigma_mass : Real = 0.5007250159521434;
                            attribute Cx : Real = -86.53296587563325;
                            attribute sigma_Cx : Real = 16.8162179021335;
                            attribute Cy : Real = -31.10069600161796;
                            attribute sigma_Cy : Real = 17.190431913664924;
                            attribute Cz : Real = 5.416715296091666;
                            attribute sigma_Cz : Real = 18.246517057238634;
                            attribute Ixx : Real = 5086.487868449069;
                            attribute sigma_Ixx : Real = 3936.1998252957897;
                            attribute Iyy : Real = 3480.9405597717646;
                            attribute sigma_Iyy : Real = 3209.3032556246208;
                            attribute Izz : Real = 2275.936337731864;
                            attribute sigma_Izz : Real = 2588.997275371848;
                            attribute Ixy : Real = 106.00138355978629;
                            attribute sigma_Ixy : Real = 1295.9946132235182;
                            attribute Ixz : Real = -794.589342733037;
                            attribute sigma_Ixz : Real = 1545.21271123848;
                            attribute Iyz : Real = -1291.9814513170245;
                            attribute sigma_Iyz : Real = 1931.8910302377378;
                            part <'C.1.2.2.1.2.1.1'> 'Part 928' {
                                attribute POIconv : String = "-";
                                attribute Ipoint : Boolean = false;
                                attribute mass : Real = 0.7995262390787248;
                                attribute sigma_mass : Real = 0.28909372274994966;
                                attribute Cx : Real = -70.02420681528747;
                                attribute sigma_Cx : Real = 28.721044428837228;
                                attribute Cy : Real = -45.677982131019235;
                                attribute sigma_Cy : Real = 28.23690002309109;
                                attribute Cz : Real = 37.172099854797125;
                                attribute sigma_Cz : Real = 29.057750463592832;
                                attribute Ixx : Real = 0.810093025908591;
                                attribute sigma_Ixx : Real = 0.37074144170588635;
                                attribute Iyy : Real = 0.7725583471161834;
                                attribute sigma_Iyy : Real = 0.3723953238821935;
                                attribute Izz : Real = 0.8106496361914727;
                                attribute sigma_Izz : Real = 0.37017423652493897;
                                attribute Ixy : Real = 0.00747103716986839;
                                attribute sigma_Ixy : Real = 0.02351283871158888;
                                attribute Ixz : Real = 0.002271714147283138;
                                attribute sigma_Ixz : Real = 0.022566176940390956;
                                attribute Iyz : Real = 0.014016636322683622;
                                attribute sigma_Iyz : Real = 0.02209918015384651;
                            }
                            part <'C.1.2.2.1.2.1.2'> 'Part 929' {
                                attribute POIconv : String = "-";
                                attribute Ipoint : Boolean = false;
                                attribute mass : Real = 0.7995670292919967;
                                attribute sigma_mass : Real = 0.28909372274994966;
                                attribute Cx : Real = -97.44771784171462;
                                attribute sigma_Cx : Real = 28.721044428837228;
                                attribute Cy : Real = -58.66879811510444;
                                attribute sigma_Cy : Real = 28.23690002309109;
                                attribute Cz : Real = -45.73369529098272;
                                attribute sigma_Cz : Real = 29.057750463592832;
                                attribute Ixx : Real = 0.8056292724888053;
                                attribute sigma_Ixx : Real = 0.37074144170588635;
                                attribute Iyy : Real = 0.8123907465948877;
                                attribute sigma_Iyy : Real = 0.3723953238821935;
                                attribute Izz : Real = 0.9152130513852671;
                                attribute sigma_Izz : Real = 0.37017423652493897;
                                attribute Ixy : Real = 0.008575871360702694;
                                attribute sigma_Ixy : Real = 0.02351283871158888;
                                attribute Ixz : Real = 0.019939681104693095;
                                attribute sigma_Ixz : Real = 0.022566176940390956;
                                attribute Iyz : Real = -0.025695000410455287;
                                attribute sigma_Iyz : Real = 0.02209918015384651;
                            }
                            part <'C.1.2.2.1.2.1.3'> 'Part 930' {
                                attribute POIconv : String = "+";
                                attribute Ipoint : Boolean = false;
                                attribute mass : Real = 0.9775735801451374;
                                attribute sigma_mass : Real = 0.28909372274994966;
                                attribute Cx : Real = -91.10767035745084;
                                attribute sigma_Cx : Real = 28.721044428837228;
                                attribute Cy : Real = 3.369822585955262;
                                attribute sigma_Cy : Real = 28.23690002309109;
                                attribute Cz : Real = 21.281422534957528;
                                attribute sigma_Cz : Real = 29.057750463592832;
                                attribute Ixx : Real = 1.4855871098462907;
                                attribute sigma_Ixx : Real = 0.37074144170588635;
                                attribute Iyy : Real = 1.491914369412807;
                                attribute sigma_Iyy : Real = 0.3723953238821935;
                                attribute Izz : Real = 1.4583468439755838;
                                attribute sigma_Izz : Real = 0.37017423652493897;
                                attribute Ixy : Real = -0.009982867245512811;
                                attribute sigma_Ixy : Real = 0.02351283871158888;
                                attribute Ixz : Real = 0.021534481927929873;
                                attribute sigma_Ixz : Real = 0.022566176940390956;
                                attribute Iyz : Real = -0.009394902390628075;
                                attribute sigma_Iyz : Real = 0.02209918015384651;
                            }
                        }
                        part <'C.1.2.2.1.2.2'> 'Subassembly 265' {
                            attribute POIconv : String = "-";
                            attribute Ipoint : Boolean = false;
                            attribute mass : Real = 1.8187305674185041;
                            attribute sigma_mass : Real = 0.6464332159373649;
                            attribute Cx : Real = 1.6249159371674544;
                            attribute sigma_Cx : Real = 27.472355532533285;
                            attribute Cy : Real = 11.35855563175906;
                            attribute sigma_Cy : Real = 26.301603524238217;
                            attribute Cz : Real = 23.993081244205452;
                            attribute sigma_Cz : Real = 25.917288841515315;
                            attribute Ixx : Real = 9838.350225774866;
                            attribute sigma_Ixx : Real = 6835.950140571191;
                            attribute Iyy : Real = 7259.253471828142;
                            attribute sigma_Iyy : Real = 7730.920258606303;
                            attribute Izz : Real = 12410.573059963224;
                            attribute sigma_Izz : Real = 7152.123284022562;
                            attribute Ixy : Real = -163.77930700964862;
                            attribute sigma_Ixy : Real = 3141.506552798141;
                            attribute Ixz : Real = -2057.584480076576;
                            attribute sigma_Ixz : Real = 3629.8184177700014;
                            attribute Iyz : Real = 1559.6571651498161;
                            attribute sigma_Iyz : Real = 2503.9504217336366;
                            part <'C.1.2.2.1.2.2.1'> 'Part 931' {
                                attribute POIconv : String = "+";
                                attribute Ipoint : Boolean = false;
                                attribute mass : Real = 0.021402636292390528;
                                attribute sigma_mass : Real = 0.28909372274994966;
                                attribute Cx : Real = -92.75170937180519;
                                attribute sigma_Cx : Real = 28.721044428837228;
                                attribute Cy : Real = 43.91828738152981;
                                attribute sigma_Cy : Real = 28.23690002309109;
                                attribute Cz : Real = -93.28296408057213;
                                attribute sigma_Cz : Real = 29.057750463592832;
                                attribute Ixx : Real = 0.02682958562219768;
                                attribute sigma_Ixx : Real = 0.37074144170588635;
                                attribute Iyy : Real = 0.028817092257073577;
                                attribute sigma_Iyy : Real = 0.3723953238821935;
                                attribute Izz : Real = 0.02694188151256071;
                                attribute sigma_Izz : Real = 0.37017423652493897;
                                attribute Ixy : Real = 0.00066169702075143;
                                attribute sigma_Ixy : Real = 0.02351283871158888;
                                attribute Ixz : Real = 0.002165462399996659;
                                attribute sigma_Ixz : Real = 0.022566176940390956;
                                attribute Iyz : Real = -5.7933430365538334e-05;
                                attribute sigma_Iyz : Real = 0.02209918015384651;
                            }
                            part <'C.1.2.2.1.2.2.2'> 'Part 932' {
                                attribute POIconv : String = "-";
                                attribute Ipoint : Boolean = false;
                                attribute mass : Real = 0.3272131983656436;
                                attribute sigma_mass : Real = 0.28909372274994966;
                                attribute Cx : Real = -84.2272687703371;
                                attribute sigma_Cx : Real = 28.721044428837228;
                                attribute Cy : Real = -42.10040234029293;
                                attribute sigma_Cy : Real = 28.23690002309109;
                                attribute Cz : Real = 26.3877481687814;
                                attribute sigma_Cz : Real = 29.057750463592832;
                                attribute Ixx : Real = 0.3927297203302749;
                                attribute sigma_Ixx : Real = 0.37074144170588635;
                                attribute Iyy : Real = 0.3667391269978756;
                                attribute sigma_Iyy : Real = 0.3723953238821935;
                                attribute Izz : Real = 0.43938759921654547;
                                attribute sigma_Izz : Real = 0.37017423652493897;
                                attribute Ixy : Real = -0.024800585605636784;
                                attribute sigma_Ixy : Real = 0.02351283871158888;
                                attribute Ixz : Real = -0.019196181839835603;
                                attribute sigma_Ixz : Real = 0.022566176940390956;
                                attribute Iyz : Real = -0.006210975820636622;
                                attribute sigma_Iyz : Real = 0.02209918015384651;
                            }
                            part <'C.1.2.2.1.2.2.3'> 'Part 933' {
                                attribute POIconv : String = "-";
                                attribute Ipoint : Boolean = false;
                                attribute mass : Real = 0.3637619523713365;
                                attribute sigma_mass : Real = 0.28909372274994966;
                                attribute Cx : Real = 56.703932071104646;
                                attribute sigma_Cx : Real = 28.721044428837228;
                                attribute Cy : Real = -91.10476705245674;
                                attribute sigma_Cy : Real = 28.23690002309109;
                                attribute Cz : Real = 57.741919392719865;
                                attribute sigma_Cz : Real = 29.057750463592832;
                                attribute Ixx : Real = 0.47905852257414216;
                                attribute sigma_Ixx : Real = 0.37074144170588635;
                                attribute Iyy : Real = 0.4028898340008814;
                                attribute sigma_Iyy : Real = 0.3723953238821935;
                                attribute Izz : Real = 0.4423681904178884;
                                attribute sigma_Izz : Real = 0.37017423652493897;
                                attribute Ixy : Real = -0.024919868043831037;
                                attribute sigma_Ixy : Real = 0.02351283871158888;
                                attribute Ixz : Real = -0.03699538509650166;
                                attribute sigma_Ixz : Real = 0.022566176940390956;
                                attribute Iyz : Real = 0.003665243380487599;
                                attribute sigma_Iyz : Real = 0.02209918015384651;
                            }
                            part <'C.1.2.2.1.2.2.4'> 'Part 934' {
                                attribute POIconv : String = "-";
                                attribute Ipoint : Boolean = false;
                                attribute mass : Real = 0.5193952887237537;
                                attribute sigma_mass : Real = 0.28909372274994966;
                                attribute Cx : Real = -23.044981574639678;
                                attribute sigma_Cx : Real = 28.721044428837228;
                                attribute Cy : Real = 51.513195876032114;
                                attribute sigma_Cy : Real = 28.23690002309109;
                                attribute Cz : Real = -25.090753939002752;
                                attribute sigma_Cz : Real = 29.057750463592832;
                                attribute Ixx : Real = 0.724839429412922;
                                attribute sigma_Ixx : Real = 0.37074144170588635;
                                attribute Iyy : Real = 0.6189863739809514;
                                attribute sigma_Iyy : Real = 0.3723953238821935;
                                attribute Izz : Real = 0.6621499257365612;
                                attribute sigma_Izz : Real = 0.37017423652493897;
                                attribute Ixy : Real = 0.021548560645599485;
                                attribute sigma_Ixy : Real = 0.02351283871158888;
                                attribute Ixz : Real = -0.017812116418874785;
                                attribute sigma_Ixz : Real = 0.022566176940390956;
                                attribute Iyz : Real = 0.015228660831936528;
                                attribute sigma_Iyz : Real = 0.02209918015384651;
                            }
                            part <'C.1.2.2.1.2.2.5'> 'Part 935' {
                                attribute POIconv : String = "-";
                                attribute Ipoint : Boolean = false;
                                attribute mass : Real = 0.58695749166538;
                                attribute sigma_mass : Real = 0.28909372274994966;
                                attribute Cx : Real = 40.622040862217546;
                                attribute sigma_Cx : Real = 28.721044428837228;
                                attribute Cy : Real = 67.94142634607852;
                                attribute sigma_Cy : Real = 28.23690002309109;
                                attribute Cz : Real = 49.45287965238094;
                                attribute sigma_Cz : Real = 29.057750463592832;
                                attribute Ixx : Real = 0.816131836828404;
                                attribute sigma_Ixx : Real = 0.37074144170588635;
                                attribute Iyy : Real = 0.8005513906078435;
                                attribute sigma_Iyy : Real = 0.3723953238821935;
                                attribute Izz : Real = 0.7879026653987344;
                                attribute sigma_Izz : Real = 0.37017423652493897;
                                attribute Ixy : Real = -0.026382847827147754;
                                attribute sigma_Ixy : Real = 0.02351283871158888;
                                attribute Ixz : Real = -0.014195410767882772;
                                attribute sigma_Ixz : Real = 0.022566176940390956;
                                attribute Iyz : Real = 0.00019774592075020214;
                                attribute sigma_Iyz : Real = 0.02209918015384651;
                            }
                        }
                        part <'C.1.2.2.1.2.3'> 'Subassembly 266' {
                            attribute POIconv : String = "-";
                            attribute Ipoint : Boolean = false;
                            attribute mass : Real = 2.1513405945163684;
                            attribute sigma_mass : Real = 0.5007250159521434;
                            attribute Cx : Real = -19.632755325998033;
                            attribute sigma_Cx : Real = 17.847844402646437;
                            attribute Cy : Real = -65.05791906754122;
                            attribute sigma_Cy : Real = 16.90429080516606;
                            attribute Cz : Real = 74.74087513197443;
                            attribute sigma_Cz : Real = 17.963632722014367;
                            attribute Ixx : Real = 962.2690747305049;
                            attribute sigma_Ixx : Real = 1645.4030960273335;
                            attribute Iyy : Real = 2055.0051761972977;
                            attribute sigma_Iyy : Real = 2445.416600241605;
                            attribute Izz : Real = 1154.36344159681;
                            attribute sigma_Izz : Real = 1815.5557351273258;
                            attribute Ixy : Real = -124.72634849427901;
                            attribute sigma_Ixy : Real = 883.6020601782745;
                            attribute Ixz : Real = -982.2498568150825;
                            attribute sigma_Ixz : Real = 1223.293044811523;
                            attribute Iyz : Real = -76.117528384081;
                            attribute sigma_Iyz : Real = 794.0219351832071;
                            part <'C.1.2.2.1.2.3.1'> 'Part 936' {
                                attribute POIconv : String = "-";
                                attribute Ipoint : Boolean = false;
                                attribute mass : Real = 0.8690858327089809;
                                attribute sigma_mass : Real = 0.28909372274994966;
                                attribute Cx : Real = 5.956424260511994;
                                attribute sigma_Cx : Real = 28.721044428837228;
                                attribute Cy : Real = -63.47609465010464;
                                attribute sigma_Cy : Real = 28.23690002309109;
                                attribute Cz : Real = 99.81979625299573;
                                attribute sigma_Cz : Real = 29.057750463592832;
                                attribute Ixx : Real = 1.0728206477751006;
                                attribute sigma_Ixx : Real = 0.37074144170588635;
                                attribute Iyy : Real = 0.9984520385474636;
                                attribute sigma_Iyy : Real = 0.3723953238821935;
                                attribute Izz : Real = 1.0343238929780978;
                                attribute sigma_Izz : Real = 0.37017423652493897;
                                attribute Ixy : Real = 0.03826574876350809;
                                attribute sigma_Ixy : Real = 0.02351283871158888;
                                attribute Ixz : Real = 0.109191755978082;
                                attribute sigma_Ixz : Real = 0.022566176940390956;
                                attribute Iyz : Real = 0.019069675750405357;
                                attribute sigma_Iyz : Real = 0.02209918015384651;
                            }
                            part <'C.1.2.2.1.2.3.2'> 'Part 937' {
                                attribute POIconv : String = "-";
                                attribute Ipoint : Boolean = false;
                                attribute mass : Real = 0.4456750747319311;
                                attribute sigma_mass : Real = 0.28909372274994966;
                                attribute Cx : Real = -21.321478625759482;
                                attribute sigma_Cx : Real = 28.721044428837228;
                                attribute Cy : Real = -59.986153710633516;
                                attribute sigma_Cy : Real = 28.23690002309109;
                                attribute Cz : Real = 62.09910814650357;
                                attribute sigma_Cz : Real = 29.057750463592832;
                                attribute Ixx : Real = 0.5609739261604525;
                                attribute sigma_Ixx : Real = 0.37074144170588635;
                                attribute Iyy : Real = 0.6079352732051975;
                                attribute sigma_Iyy : Real = 0.3723953238821935;
                                attribute Izz : Real = 0.5851442200880124;
                                attribute sigma_Izz : Real = 0.37017423652493897;
                                attribute Ixy : Real = -0.050481005002403184;
                                attribute sigma_Ixy : Real = 0.02351283871158888;
                                attribute Ixz : Real = -0.0002863930330591573;
                                attribute sigma_Ixz : Real = 0.022566176940390956;
                                attribute Iyz : Real = -0.00035979592361950986;
                                attribute sigma_Iyz : Real = 0.02209918015384651;
                            }
                            part <'C.1.2.2.1.2.3.3'> 'Part 938' {
                                attribute POIconv : String = "+";
                                attribute Ipoint : Boolean = false;
                                attribute mass : Real = 0.8365796870754566;
                                attribute sigma_mass : Real = 0.28909372274994966;
                                attribute Cx : Real = -45.31658664345741;
                                attribute sigma_Cx : Real = 28.721044428837228;
                                attribute Cy : Real = -69.40311254002154;
                                attribute sigma_Cy : Real = 28.23690002309109;
                                attribute Cz : Real = 55.42219593189657;
                                attribute sigma_Cz : Real = 29.057750463592832;
                                attribute Ixx : Real = 1.1416474236276872;
                                attribute sigma_Ixx : Real = 0.37074144170588635;
                                attribute Iyy : Real = 1.1278183915803692;
                                attribute sigma_Iyy : Real = 0.3723953238821935;
                                attribute Izz : Real = 1.0989815533828418;
                                attribute sigma_Izz : Real = 0.37017423652493897;
                                attribute Ixy : Real = -0.010554908537077475;
                                attribute sigma_Ixy : Real = 0.02351283871158888;
                                attribute Ixz : Real = 0.017130195610554688;
                                attribute sigma_Ixz : Real = 0.022566176940390956;
                                attribute Iyz : Real = 0.00880700266928349;
                                attribute sigma_Iyz : Real = 0.02209918015384651;
                            }
                        }
                    }
                }
                part <'C.1.2.2.2'> 'Subsystem 21' {
                    attribute POIconv : String = "-";
                    attribute Ipoint : Boolean = false;
                    attribute mass : Real = 30.562207365172913;
                    attribute sigma_mass : Real = 2.220571019236282;
                    attribute Cx : Real = 0.6459291819371931;
                    attribute sigma_Cx : Real = 5.935753253559431;
                    attribute Cy : Real = 1.7391738985982717;
                    attribute sigma_Cy : Real = 6.502473505394561;
                    attribute Cz : Real = 6.881141393776601;
                    attribute sigma_Cz : Real = 6.112811680063433;
                    attribute Ixx : Real = 235857.07121535757;
                    attribute sigma_Ixx : Real = 31466.64660688789;
                    attribute Iyy : Real = 191372.04451474771;
                    attribute sigma_Iyy : Real = 26671.526261586627;
                    attribute Izz : Real = 230777.20654912296;
                    attribute sigma_Izz : Real = 30488.120313019703;
                    attribute Ixy : Real = 6780.19316022997;
                    attribute sigma_Ixy : Real = 14293.49183151501;
                    attribute Ixz : Real = -1814.7428497317874;
                    attribute sigma_Ixz : Real = 12329.44026678553;
                    attribute Iyz : Real = 5545.232066797618;
                    attribute sigma_Iyz : Real = 14868.163730959815;
                    part <'C.1.2.2.2.1'> 'Assembly 77' {
                        attribute POIconv : String = "-";
                        attribute Ipoint : Boolean = false;
                        attribute mass : Real = 8.256390693801453;
                        attribute sigma_mass : Real = 1.0423422407897138;
                        attribute Cx : Real = 3.3617349304551842;
                        attribute sigma_Cx : Real = 11.094601595681148;
                        attribute Cy : Real = -4.6294887193230325;
                        attribute sigma_Cy : Real = 11.868310689639955;
                        attribute Cz : Real = -2.2000861335280146;
                        attribute sigma_Cz : Real = 11.33833219125626;
                        attribute Ixx : Real = 69773.33543813715;
                        attribute sigma_Ixx : Real = 16749.524438923512;
                        attribute Iyy : Real = 55730.002875035876;
                        attribute sigma_Iyy : Real = 13841.352836439948;
                        attribute Izz : Real = 66219.66099668249;
                        attribute sigma_Izz : Real = 15394.139108473553;
                        attribute Ixy : Real = -262.7132439672846;
                        attribute sigma_Ixy : Real = 7116.488538616383;
                        attribute Ixz : Real = -3783.720736601181;
                        attribute sigma_Ixz : Real = 6477.122791881466;
                        attribute Iyz : Real = 2501.151747758455;
                        attribute sigma_Iyz : Real = 8132.399734461388;
                        part <'C.1.2.2.2.1.1'> 'Subassembly 267' {
                            attribute POIconv : String = "-";
                            attribute Ipoint : Boolean = false;
                            attribute mass : Real = 1.6984050438443663;
                            attribute sigma_mass : Real = 0.5007250159521434;
                            attribute Cx : Real = 49.82081645540351;
                            attribute sigma_Cx : Real = 23.16999034990005;
                            attribute Cy : Real = 41.26602480345358;
                            attribute sigma_Cy : Real = 22.397940801278494;
                            attribute Cz : Real = -12.188242219105264;
                            attribute sigma_Cz : Real = 23.341852491224152;
                            attribute Ixx : Real = 9472.051373135186;
                            attribute sigma_Ixx : Real = 5475.736619370115;
                            attribute Iyy : Real = 9511.793680101937;
                            attribute sigma_Iyy : Real = 5180.463227293832;
                            attribute Izz : Real = 8499.088803022421;
                            attribute sigma_Izz : Real = 4835.458889827518;
                            attribute Ixy : Real = 562.4023634684052;
                            attribute sigma_Ixy : Real = 2135.466673065858;
                            attribute Ixz : Real = -1635.799939668047;
                            attribute sigma_Ixz : Real = 2269.861508359946;
                            attribute Iyz : Real = -4162.854114926466;
                            attribute sigma_Iyz : Real = 2708.4541414168834;
                            part <'C.1.2.2.2.1.1.1'> 'Part 939' {
                                attribute POIconv : String = "-";
                                attribute Ipoint : Boolean = false;
                                attribute mass : Real = 0.5304808197803795;
                                attribute sigma_mass : Real = 0.28909372274994966;
                                attribute Cx : Real = 60.75750580057502;
                                attribute sigma_Cx : Real = 28.721044428837228;
                                attribute Cy : Real = -32.76290348730981;
                                attribute sigma_Cy : Real = 28.23690002309109;
                                attribute Cz : Real = -84.49718449264765;
                                attribute sigma_Cz : Real = 29.057750463592832;
                                attribute Ixx : Real = 0.7213257122723988;
                                attribute sigma_Ixx : Real = 0.37074144170588635;
                                attribute Iyy : Real = 0.7234731790778778;
                                attribute sigma_Iyy : Real = 0.3723953238821935;
                                attribute Izz : Real = 0.7185367014939027;
                                attribute sigma_Izz : Real = 0.37017423652493897;
                                attribute Ixy : Real = 0.01483740539071361;
                                attribute sigma_Ixy : Real = 0.02351283871158888;
                                attribute Ixz : Real = 0.04841522530425567;
                                attribute sigma_Ixz : Real = 0.022566176940390956;
                                attribute Iyz : Real = 0.028203966781611686;
                                attribute sigma_Iyz : Real = 0.02209918015384651;
                            }
                            part <'C.1.2.2.2.1.1.2'> 'Part 940' {
                                attribute POIconv : String = "-";
                                attribute Ipoint : Boolean = false;
                                attribute mass : Real = 0.7308029113435186;
                                attribute sigma_mass : Real = 0.28909372274994966;
                                attribute Cx : Real = 91.09971495345235;
                                attribute sigma_Cx : Real = 28.721044428837228;
                                attribute Cy : Real = 75.5786759313196;
                                attribute sigma_Cy : Real = 28.23690002309109;
                                attribute Cz : Real = 45.52659331820905;
                                attribute sigma_Cz : Real = 29.057750463592832;
                                attribute Ixx : Real = 1.007833088478367;
                                attribute sigma_Ixx : Real = 0.37074144170588635;
                                attribute Iyy : Real = 0.98129261330428;
                                attribute sigma_Iyy : Real = 0.3723953238821935;
                                attribute Izz : Real = 1.023527139249452;
                                attribute sigma_Izz : Real = 0.37017423652493897;
                                attribute Ixy : Real = -0.05562443555643414;
                                attribute sigma_Ixy : Real = 0.02351283871158888;
                                attribute Ixz : Real = 0.004041145063428419;
                                attribute sigma_Ixz : Real = 0.022566176940390956;
                                attribute Iyz : Real = -0.0319486739470413;
                                attribute sigma_Iyz : Real = 0.02209918015384651;
                            }
                            part <'C.1.2.2.2.1.1.3'> 'Part 941' {
                                attribute POIconv : String = "-";
                                attribute Ipoint : Boolean = false;
                                attribute mass : Real = 0.4371213127204683;
                                attribute sigma_mass : Real = 0.28909372274994966;
                                attribute Cx : Real = -32.463991176337004;
                                attribute sigma_Cx : Real = 28.721044428837228;
                                attribute Cy : Real = 73.74017057009041;
                                attribute sigma_Cy : Real = 28.23690002309109;
                                attribute Cz : Real = -20.926463743671775;
                                attribute sigma_Cz : Real = 29.057750463592832;
                                attribute Ixx : Real = 0.3995857926250314;
                                attribute sigma_Ixx : Real = 0.37074144170588635;
                                attribute Iyy : Real = 0.38502937842237395;
                                attribute sigma_Iyy : Real = 0.3723953238821935;
                                attribute Izz : Real = 0.41275025534529675;
                                attribute sigma_Izz : Real = 0.37017423652493897;
                                attribute Ixy : Real = 0.005558983815707172;
                                attribute sigma_Ixy : Real = 0.02351283871158888;
                                attribute Ixz : Real = 0.001144980919016476;
                                attribute sigma_Ixz : Real = 0.022566176940390956;
                                attribute Iyz : Real = -0.006669784596549803;
                                attribute sigma_Iyz : Real = 0.02209918015384651;
                            }
                        }
                        part <'C.1.2.2.2.1.2'> 'Subassembly 268' {
                            attribute POIconv : String = "-";
                            attribute Ipoint : Boolean = false;
                            attribute mass : Real = 3.512449209432583;
                            attribute sigma_mass : Real = 0.6464332159373649;
                            attribute Cx : Real = -32.41173009547161;
                            attribute sigma_Cx : Real = 16.12313808082729;
                            attribute Cy : Real = -4.125871915687928;
                            attribute sigma_Cy : Real = 17.73864181452447;
                            attribute Cz : Real = 1.5683427895378654;
                            attribute sigma_Cz : Real = 16.957942626805547;
                            attribute Ixx : Real = 27436.10614266415;
                            attribute sigma_Ixx : Real = 10401.64229197483;
                            attribute Iyy : Real = 18300.79600410257;
                            attribute sigma_Iyy : Real = 8064.211169313992;
                            attribute Izz : Real = 22090.30760012899;
                            attribute sigma_Izz : Real = 8746.725281006706;
                            attribute Ixy : Real = 318.9463530926545;
                            attribute sigma_Ixy : Real = 3992.479819654935;
                            attribute Ixz : Real = -3823.312890050869;
                            attribute sigma_Ixz : Real = 3788.9945533963196;
                            attribute Iyz : Real = -6639.297466626676;
                            attribute sigma_Iyz : Real = 5040.735873237641;
                            part <'C.1.2.2.2.1.2.1'> 'Part 942' {
                                attribute POIconv : String = "+";
                                attribute Ipoint : Boolean = false;
                                attribute mass : Real = 0.9812123987139203;
                                attribute sigma_mass : Real = 0.28909372274994966;
                                attribute Cx : Real = -49.319747276604176;
                                attribute sigma_Cx : Real = 28.721044428837228;
                                attribute Cy : Real = 95.33907482400537;
                                attribute sigma_Cy : Real = 28.23690002309109;
                                attribute Cz : Real = 55.62381888739765;
                                attribute sigma_Cz : Real = 29.057750463592832;
                                attribute Ixx : Real = 1.0006192960276659;
                                attribute sigma_Ixx : Real = 0.37074144170588635;
                                attribute Iyy : Real = 1.2084499004363687;
                                attribute sigma_Iyy : Real = 0.3723953238821935;
                                attribute Izz : Real = 1.2096661175658778;
                                attribute sigma_Izz : Real = 0.37017423652493897;
                                attribute Ixy : Real = 0.011185861634035815;
                                attribute sigma_Ixy : Real = 0.02351283871158888;
                                attribute Ixz : Real = -0.012322805038329533;
                                attribute sigma_Ixz : Real = 0.022566176940390956;
                                attribute Iyz : Real = -0.0010512235113654103;
                                attribute sigma_Iyz : Real = 0.02209918015384651;
                            }
                            part <'C.1.2.2.2.1.2.2'> 'Part 943' {
                                attribute POIconv : String = "+";
                                attribute Ipoint : Boolean = false;
                                attribute mass : Real = 0.7293517280058004;
                                attribute sigma_mass : Real = 0.28909372274994966;
                                attribute Cx : Real = -5.361723201349378;
                                attribute sigma_Cx : Real = 28.721044428837228;
                                attribute Cy : Real = -43.36663968861103;
                                attribute sigma_Cy : Real = 28.23690002309109;
                                attribute Cz : Real = 14.300070377066731;
                                attribute sigma_Cz : Real = 29.057750463592832;
                                attribute Ixx : Real = 0.7939805078297852;
                                attribute sigma_Ixx : Real = 0.37074144170588635;
                                attribute Iyy : Real = 0.7369344379142871;
                                attribute sigma_Iyy : Real = 0.3723953238821935;
                                attribute Izz : Real = 0.722756761171007;
                                attribute sigma_Izz : Real = 0.37017423652493897;
                                attribute Ixy : Real = 0.013930435433064506;
                                attribute sigma_Ixy : Real = 0.02351283871158888;
                                attribute Ixz : Real = 0.012831483825266419;
                                attribute sigma_Ixz : Real = 0.022566176940390956;
                                attribute Iyz : Real = 0.039817308153053003;
                                attribute sigma_Iyz : Real = 0.02209918015384651;
                            }
                            part <'C.1.2.2.2.1.2.3'> 'Part 944' {
                                attribute POIconv : String = "-";
                                attribute Ipoint : Boolean = false;
                                attribute mass : Real = 0.42534472983982413;
                                attribute sigma_mass : Real = 0.28909372274994966;
                                attribute Cx : Real = 50.050278939306736;
                                attribute sigma_Cx : Real = 28.721044428837228;
                                attribute Cy : Real = 15.128774009644985;
                                attribute sigma_Cy : Real = 28.23690002309109;
                                attribute Cz : Real = -10.529186390340328;
                                attribute sigma_Cz : Real = 29.057750463592832;
                                attribute Ixx : Real = 0.5119424650658849;
                                attribute sigma_Ixx : Real = 0.37074144170588635;
                                attribute Iyy : Real = 0.5307585473489143;
                                attribute sigma_Iyy : Real = 0.3723953238821935;
                                attribute Izz : Real = 0.5022029988226561;
                                attribute sigma_Izz : Real = 0.37017423652493897;
                                attribute Ixy : Real = 0.04111003840472058;
                                attribute sigma_Ixy : Real = 0.02351283871158888;
                                attribute Ixz : Real = -0.01496749705211656;
                                attribute sigma_Ixz : Real = 0.022566176940390956;
                                attribute Iyz : Real = -0.005191622726144549;
                                attribute sigma_Iyz : Real = 0.02209918015384651;
                            }
                            part <'C.1.2.2.2.1.2.4'> 'Part 945' {
                                attribute POIconv : String = "-";
                                attribute Ipoint : Boolean = false;
                                attribute mass : Real = 0.9555976862048264;
                                attribute sigma_mass : Real = 0.28909372274994966;
                                attribute Cx : Real = -83.55107973329723;
                                attribute sigma_Cx : Real = 28.721044428837228;
                                attribute Cy : Real = -50.43617389164865;
                                attribute sigma_Cy : Real = 28.23690002309109;
                                attribute Cz : Real = -85.22074781358242;
                                attribute sigma_Cz : Real = 29.057750463592832;
                                attribute Ixx : Real = 1.1672360051465862;
                                attribute sigma_Ixx : Real = 0.37074144170588635;
                                attribute Iyy : Real = 1.1837072191293871;
                                attribute sigma_Iyy : Real = 0.3723953238821935;
                                attribute Izz : Real = 1.0958214495700125;
                                attribute sigma_Izz : Real = 0.37017423652493897;
                                attribute Ixy : Real = -0.0372436406590437;
                                attribute sigma_Ixy : Real = 0.02351283871158888;
                                attribute Ixz : Real = -0.07339301728699608;
                                attribute sigma_Ixz : Real = 0.022566176940390956;
                                attribute Iyz : Real = -0.06002581903944487;
                                attribute sigma_Iyz : Real = 0.02209918015384651;
                            }
                            part <'C.1.2.2.2.1.2.5'> 'Part 946' {
                                attribute POIconv : String = "-";
                                attribute Ipoint : Boolean = false;
                                attribute mass : Real = 0.42094266666821206;
                                attribute sigma_mass : Real = 0.28909372274994966;
                                attribute Cx : Real = -7.098900340497494;
                                attribute sigma_Cx : Real = 28.721044428837228;
                                attribute Cy : Real = -82.31172608211637;
                                attribute sigma_Cy : Real = 28.23690002309109;
                                attribute Cz : Real = 62.75307317264378;
                                attribute sigma_Cz : Real = 29.057750463592832;
                                attribute Ixx : Real = 0.5065569279605093;
                                attribute sigma_Ixx : Real = 0.37074144170588635;
                                attribute Iyy : Real = 0.5015888289180981;
                                attribute sigma_Iyy : Real = 0.3723953238821935;
                                attribute Izz : Real = 0.6041167793917881;
                                attribute sigma_Izz : Real = 0.37017423652493897;
                                attribute Ixy : Real = 0.01314653157414077;
                                attribute sigma_Ixy : Real = 0.02351283871158888;
                                attribute Ixz : Real = 0.04584804867370509;
                                attribute sigma_Ixz : Real = 0.022566176940390956;
                                attribute Iyz : Real = 0.02308903785672673;
                                attribute sigma_Iyz : Real = 0.02209918015384651;
                            }
                        }
                        part <'C.1.2.2.2.1.3'> 'Subassembly 269' {
                            attribute POIconv : String = "-";
                            attribute Ipoint : Boolean = false;
                            attribute mass : Real = 3.045536440524505;
                            attribute sigma_mass : Real = 0.6464332159373649;
                            attribute Cx : Real = 18.710801168054104;
                            attribute sigma_Cx : Real = 16.287846020316874;
                            attribute Cy : Real = -30.80487740945707;
                            attribute sigma_Cy : Real = 19.309161838393752;
                            attribute Cz : Real = -0.9761574248695107;
                            attribute sigma_Cz : Real = 19.73500347834383;
                            attribute Ixx : Real = 26976.236407298482;
                            attribute sigma_Ixx : Real = 10882.401824980687;
                            attribute Iyy : Real = 18815.08187839876;
                            attribute sigma_Iyy : Real = 8047.111216493222;
                            attribute Izz : Real = 21086.754036672894;
                            attribute sigma_Izz : Real = 8815.4844857846;
                            attribute Ixy : Real = 1190.505861684041;
                            attribute sigma_Ixy : Real = 3883.5357626928485;
                            attribute Ixz : Real = 470.9647766111352;
                            attribute sigma_Ixz : Real = 3659.9455264652943;
                            attribute Iyz : Real = 12433.831645858354;
                            attribute sigma_Iyz : Real = 5229.427629994171;
                            part <'C.1.2.2.2.1.3.1'> 'Part 947' {
                                attribute POIconv : String = "-";
                                attribute Ipoint : Boolean = false;
                                attribute mass : Real = 0.3024013258176856;
                                attribute sigma_mass : Real = 0.28909372274994966;
                                attribute Cx : Real = 45.85023648105562;
                                attribute sigma_Cx : Real = 28.721044428837228;
                                attribute Cy : Real = -3.684002533555031;
                                attribute sigma_Cy : Real = 28.23690002309109;
                                attribute Cz : Real = -94.07813153229654;
                                attribute sigma_Cz : Real = 29.057750463592832;
                                attribute Ixx : Real = 0.32725238184361594;
                                attribute sigma_Ixx : Real = 0.37074144170588635;
                                attribute Iyy : Real = 0.3526668346173522;
                                attribute sigma_Iyy : Real = 0.3723953238821935;
                                attribute Izz : Real = 0.3547297689551177;
                                attribute sigma_Izz : Real = 0.37017423652493897;
                                attribute Ixy : Real = 0.007379397694733824;
                                attribute sigma_Ixy : Real = 0.02351283871158888;
                                attribute Ixz : Real = -0.0018620467074161502;
                                attribute sigma_Ixz : Real = 0.022566176940390956;
                                attribute Iyz : Real = -0.002576270043918154;
                                attribute sigma_Iyz : Real = 0.02209918015384651;
                            }
                            part <'C.1.2.2.2.1.3.2'> 'Part 948' {
                                attribute POIconv : String = "+";
                                attribute Ipoint : Boolean = false;
                                attribute mass : Real = 0.7712300861815456;
                                attribute sigma_mass : Real = 0.28909372274994966;
                                attribute Cx : Real = 86.4832405000925;
                                attribute sigma_Cx : Real = 28.721044428837228;
                                attribute Cy : Real = -71.39332671649754;
                                attribute sigma_Cy : Real = 28.23690002309109;
                                attribute Cz : Real = 31.37113037519157;
                                attribute sigma_Cz : Real = 29.057750463592832;
                                attribute Ixx : Real = 1.0742444285834558;
                                attribute sigma_Ixx : Real = 0.37074144170588635;
                                attribute Iyy : Real = 1.0532506291283061;
                                attribute sigma_Iyy : Real = 0.3723953238821935;
                                attribute Izz : Real = 1.1129527430470079;
                                attribute sigma_Izz : Real = 0.37017423652493897;
                                attribute Ixy : Real = 0.014271390100853461;
                                attribute sigma_Ixy : Real = 0.02351283871158888;
                                attribute Ixz : Real = 0.009819387251517993;
                                attribute sigma_Ixz : Real = 0.022566176940390956;
                                attribute Iyz : Real = -0.04906542134574031;
                                attribute sigma_Iyz : Real = 0.02209918015384651;
                            }
                            part <'C.1.2.2.2.1.3.3'> 'Part 949' {
                                attribute POIconv : String = "-";
                                attribute Ipoint : Boolean = false;
                                attribute mass : Real = 0.6450899850483984;
                                attribute sigma_mass : Real = 0.28909372274994966;
                                attribute Cx : Real = -7.571651693433523;
                                attribute sigma_Cx : Real = 28.721044428837228;
                                attribute Cy : Real = 91.65872284211218;
                                attribute sigma_Cy : Real = 28.23690002309109;
                                attribute Cz : Real = -90.08773728273809;
                                attribute sigma_Cz : Real = 29.057750463592832;
                                attribute Ixx : Real = 0.7193817285350733;
                                attribute sigma_Ixx : Real = 0.37074144170588635;
                                attribute Iyy : Real = 0.7138839830932242;
                                attribute sigma_Iyy : Real = 0.3723953238821935;
                                attribute Izz : Real = 0.6593076541923454;
                                attribute sigma_Izz : Real = 0.37017423652493897;
                                attribute Ixy : Real = -0.016593916541461546;
                                attribute sigma_Ixy : Real = 0.02351283871158888;
                                attribute Ixz : Real = 0.0011190086397145083;
                                attribute sigma_Ixz : Real = 0.022566176940390956;
                                attribute Iyz : Real = 0.01123433779020476;
                                attribute sigma_Iyz : Real = 0.02209918015384651;
                            }
                            part <'C.1.2.2.2.1.3.4'> 'Part 950' {
                                attribute POIconv : String = "-";
                                attribute Ipoint : Boolean = false;
                                attribute mass : Real = 0.39505316310282795;
                                attribute sigma_mass : Real = 0.28909372274994966;
                                attribute Cx : Real = 24.153555231168866;
                                attribute sigma_Cx : Real = 28.721044428837228;
                                attribute Cy : Real = -28.724731458351016;
                                attribute sigma_Cy : Real = 28.23690002309109;
                                attribute Cz : Real = 2.1092519629746675;
                                attribute sigma_Cz : Real = 29.057750463592832;
                                attribute Ixx : Real = 0.4565105817478127;
                                attribute sigma_Ixx : Real = 0.37074144170588635;
                                attribute Iyy : Real = 0.4588437105696054;
                                attribute sigma_Iyy : Real = 0.3723953238821935;
                                attribute Izz : Real = 0.46545579412748667;
                                attribute sigma_Izz : Real = 0.37017423652493897;
                                attribute Ixy : Real = -0.012915001457887484;
                                attribute sigma_Ixy : Real = 0.02351283871158888;
                                attribute Ixz : Real = -0.011585624019641527;
                                attribute sigma_Ixz : Real = 0.022566176940390956;
                                attribute Iyz : Real = -0.019275062383034183;
                                attribute sigma_Iyz : Real = 0.02209918015384651;
                            }
                            part <'C.1.2.2.2.1.3.5'> 'Part 951' {
                                attribute POIconv : String = "-";
                                attribute Ipoint : Boolean = false;
                                attribute mass : Real = 0.931761880374048;
                                attribute sigma_mass : Real = 0.28909372274994966;
                                attribute Cx : Real = -30.304699996486306;
                                attribute sigma_Cx : Real = 28.721044428837228;
                                attribute Cy : Real = -91.6789770592004;
                                attribute sigma_Cy : Real = 28.23690002309109;
                                attribute Cz : Real = 62.852431274950504;
                                attribute sigma_Cz : Real = 29.057750463592832;
                                attribute Ixx : Real = 0.9589455054782718;
                                attribute sigma_Ixx : Real = 0.37074144170588635;
                                attribute Iyy : Real = 0.9426141595917784;
                                attribute sigma_Iyy : Real = 0.3723953238821935;
                                attribute Izz : Real = 1.1042672268306502;
                                attribute sigma_Izz : Real = 0.37017423652493897;
                                attribute Ixy : Real = -0.03446462598165776;
                                attribute sigma_Ixy : Real = 0.02351283871158888;
                                attribute Ixz : Real = 0.011123421512644175;
                                attribute sigma_Ixz : Real = 0.022566176940390956;
                                attribute Iyz : Real = 0.008326846277428385;
                                attribute sigma_Iyz : Real = 0.02209918015384651;
                            }
                        }
                    }
                    part <'C.1.2.2.2.2'> 'Assembly 78' {
                        attribute POIconv : String = "-";
                        attribute Ipoint : Boolean = false;
                        attribute mass : Real = 6.490695031536511;
                        attribute sigma_mass : Real = 1.081689663197327;
                        attribute Cx : Real = -6.281044655930993;
                        attribute sigma_Cx : Real = 13.162758160439395;
                        attribute Cy : Real = -2.441568827236705;
                        attribute sigma_Cy : Real = 15.124570547927938;
                        attribute Cz : Real = 17.29238538120845;
                        attribute sigma_Cz : Real = 14.05954360276799;
                        attribute Ixx : Real = 52331.786138780924;
                        attribute sigma_Ixx : Real = 15187.249872047914;
                        attribute Iyy : Real = 36281.76085621665;
                        attribute sigma_Iyy : Real = 11874.333990964635;
                        attribute Izz : Real = 52319.95677996417;
                        attribute sigma_Izz : Real = 14442.126272647634;
                        attribute Ixy : Real = -546.1165898881382;
                        attribute sigma_Ixy : Real = 6998.827303878356;
                        attribute Ixz : Real = 750.0640284712338;
                        attribute sigma_Ixz : Real = 5542.543578290438;
                        attribute Iyz : Real = 6430.627121861609;
                        attribute sigma_Iyz : Real = 7290.015825270994;
                        part <'C.1.2.2.2.2.1'> 'Subassembly 270' {
                            attribute POIconv : String = "-";
                            attribute Ipoint : Boolean = false;
                            attribute mass : Real = 1.903204191966448;
                            attribute sigma_mass : Real = 0.5781874454998993;
                            attribute Cx : Real = 38.27599220188477;
                            attribute sigma_Cx : Real = 19.71247828195971;
                            attribute Cy : Real = 17.22032952036432;
                            attribute sigma_Cy : Real = 23.191069624184518;
                            attribute Cz : Real = -18.970653850012287;
                            attribute sigma_Cz : Real = 23.43359231507451;
                            attribute Ixx : Real = 9224.340594364638;
                            attribute sigma_Ixx : Real = 5338.643937897518;
                            attribute Iyy : Real = 4990.157947290629;
                            attribute sigma_Iyy : Real = 4002.37609616837;
                            attribute Izz : Real = 7267.381320695282;
                            attribute sigma_Izz : Real = 4417.088921977193;
                            attribute Ixy : Real = 693.4354189504965;
                            attribute sigma_Ixy : Real = 2064.282911043444;
                            attribute Ixz : Real = 2011.9246673123973;
                            attribute sigma_Ixz : Real = 1898.5540679170986;
                            attribute Iyz : Real = 1164.6559511186456;
                            attribute sigma_Iyz : Real = 2570.7088637024935;
                            part <'C.1.2.2.2.2.1.1'> 'Part 952' {
                                attribute POIconv : String = "+";
                                attribute Ipoint : Boolean = false;
                                attribute mass : Real = 0.5570705220787786;
                                attribute sigma_mass : Real = 0.28909372274994966;
                                attribute Cx : Real = 30.003085965290666;
                                attribute sigma_Cx : Real = 28.721044428837228;
                                attribute Cy : Real = -54.571036621928215;
                                attribute sigma_Cy : Real = 28.23690002309109;
                                attribute Cz : Real = 21.27750525251031;
                                attribute sigma_Cz : Real = 29.057750463592832;
                                attribute Ixx : Real = 0.7665951074163597;
                                attribute sigma_Ixx : Real = 0.37074144170588635;
                                attribute Iyy : Real = 0.6630523085738558;
                                attribute sigma_Iyy : Real = 0.3723953238821935;
                                attribute Izz : Real = 0.7396519992902546;
                                attribute sigma_Izz : Real = 0.37017423652493897;
                                attribute Ixy : Real = -0.01687849662981117;
                                attribute sigma_Ixy : Real = 0.02351283871158888;
                                attribute Ixz : Real = 0.043354766851987636;
                                attribute sigma_Ixz : Real = 0.022566176940390956;
                                attribute Iyz : Real = 0.017554973441418563;
                                attribute sigma_Iyz : Real = 0.02209918015384651;
                            }
                            part <'C.1.2.2.2.2.1.2'> 'Part 953' {
                                attribute POIconv : String = "+";
                                attribute Ipoint : Boolean = false;
                                attribute mass : Real = 0.23396996997622774;
                                attribute sigma_mass : Real = 0.28909372274994966;
                                attribute Cx : Real = 98.9019550383091;
                                attribute sigma_Cx : Real = 28.721044428837228;
                                attribute Cy : Real = -30.013889400288463;
                                attribute sigma_Cy : Real = 28.23690002309109;
                                attribute Cz : Real = -92.65798064880073;
                                attribute sigma_Cz : Real = 29.057750463592832;
                                attribute Ixx : Real = 0.2879445622774804;
                                attribute sigma_Ixx : Real = 0.37074144170588635;
                                attribute Iyy : Real = 0.2862266629321412;
                                attribute sigma_Iyy : Real = 0.3723953238821935;
                                attribute Izz : Real = 0.3546024794657702;
                                attribute sigma_Izz : Real = 0.37017423652493897;
                                attribute Ixy : Real = -0.0037929954483616156;
                                attribute sigma_Ixy : Real = 0.02351283871158888;
                                attribute Ixz : Real = 0.02380493223724639;
                                attribute sigma_Ixz : Real = 0.022566176940390956;
                                attribute Iyz : Real = 0.0024373370542601913;
                                attribute sigma_Iyz : Real = 0.02209918015384651;
                            }
                            part <'C.1.2.2.2.2.1.3'> 'Part 954' {
                                attribute POIconv : String = "-";
                                attribute Ipoint : Boolean = false;
                                attribute mass : Real = 0.86733810041775;
                                attribute sigma_mass : Real = 0.28909372274994966;
                                attribute Cx : Real = 18.01522821187973;
                                attribute sigma_Cx : Real = 28.721044428837228;
                                attribute Cy : Real = 61.25991437584162;
                                attribute sigma_Cy : Real = 28.23690002309109;
                                attribute Cz : Real = -5.63686559908092;
                                attribute sigma_Cz : Real = 29.057750463592832;
                                attribute Ixx : Real = 1.1507957085401581;
                                attribute sigma_Ixx : Real = 0.37074144170588635;
                                attribute Iyy : Real = 1.1557880380325536;
                                attribute sigma_Iyy : Real = 0.3723953238821935;
                                attribute Izz : Real = 1.2012781496508196;
                                attribute sigma_Izz : Real = 0.37017423652493897;
                                attribute Ixy : Real = -0.01147436534047317;
                                attribute sigma_Ixy : Real = 0.02351283871158888;
                                attribute Ixz : Real = 0.0004259336001753675;
                                attribute sigma_Ixz : Real = 0.022566176940390956;
                                attribute Iyz : Real = 0.005690544168021413;
                                attribute sigma_Iyz : Real = 0.02209918015384651;
                            }
                            part <'C.1.2.2.2.2.1.4'> 'Part 955' {
                                attribute POIconv : String = "+";
                                attribute Ipoint : Boolean = false;
                                attribute mass : Real = 0.2448255994936917;
                                attribute sigma_mass : Real = 0.28909372274994966;
                                attribute Cx : Real = 70.93952926807106;
                                attribute sigma_Cx : Real = 28.721044428837228;
                                attribute Cy : Real = 69.69455098733306;
                                attribute sigma_Cy : Real = 28.23690002309109;
                                attribute Cz : Real = -87.3676841147244;
                                attribute sigma_Cz : Real = 29.057750463592832;
                                attribute Ixx : Real = 0.3050342462555332;
                                attribute sigma_Ixx : Real = 0.37074144170588635;
                                attribute Iyy : Real = 0.3633899289650806;
                                attribute sigma_Iyy : Real = 0.3723953238821935;
                                attribute Izz : Real = 0.28125321359133754;
                                attribute sigma_Izz : Real = 0.37017423652493897;
                                attribute Ixy : Real = -0.007141392777173988;
                                attribute sigma_Ixy : Real = 0.02351283871158888;
                                attribute Ixz : Real = 0.00116163306847005;
                                attribute sigma_Ixz : Real = 0.022566176940390956;
                                attribute Iyz : Real = 0.0065718634573092355;
                                attribute sigma_Iyz : Real = 0.02209918015384651;
                            }
                        }
                        part <'C.1.2.2.2.2.2'> 'Subassembly 271' {
                            attribute POIconv : String = "-";
                            attribute Ipoint : Boolean = false;
                            attribute mass : Real = 1.1231987442171667;
                            attribute sigma_mass : Real = 0.40884026350990615;
                            attribute Cx : Real = -36.054060101433734;
                            attribute sigma_Cx : Real = 29.466491560190768;
                            attribute Cy : Real = -58.52487803348067;
                            attribute sigma_Cy : Real = 24.190084240982735;
                            attribute Cz : Real = 57.070465198345566;
                            attribute sigma_Cz : Real = 24.57131612034096;
                            attribute Ixx : Real = 75.21304145029974;
                            attribute sigma_Ixx : Real = 292.0824113911126;
                            attribute Iyy : Real = 982.7177570498061;
                            attribute sigma_Iyy : Real = 1571.6434676924002;
                            attribute Izz : Real = 1033.9210584069551;
                            attribute sigma_Izz : Real = 1635.2661287611543;
                            attribute Ixy : Real = 246.46977219958472;
                            attribute sigma_Ixy : Real = 597.5866856705953;
                            attribute Ixz : Real = 105.23032625001157;
                            attribute sigma_Ixz : Real = 533.9593278760982;
                            attribute Iyz : Real = -26.686743890460797;
                            attribute sigma_Iyz : Real = 145.41228240258837;
                            part <'C.1.2.2.2.2.2.1'> 'Part 956' {
                                attribute POIconv : String = "-";
                                attribute Ipoint : Boolean = false;
                                attribute mass : Real = 0.9265268304713536;
                                attribute sigma_mass : Real = 0.28909372274994966;
                                attribute Cx : Real = -22.51451276242733;
                                attribute sigma_Cx : Real = 28.721044428837228;
                                attribute Cy : Real = -61.963509768247604;
                                attribute sigma_Cy : Real = 28.23690002309109;
                                attribute Cz : Real = 55.60203264467418;
                                attribute sigma_Cz : Real = 29.057750463592832;
                                attribute Ixx : Real = 0.9988361908372292;
                                attribute sigma_Ixx : Real = 0.37074144170588635;
                                attribute Iyy : Real = 1.0387515322180894;
                                attribute sigma_Iyy : Real = 0.3723953238821935;
                                attribute Izz : Real = 1.1441927486948744;
                                attribute sigma_Izz : Real = 0.37017423652493897;
                                attribute Ixy : Real = 0.11200498302669121;
                                attribute sigma_Ixy : Real = 0.02351283871158888;
                                attribute Ixz : Real = -0.0009169841521839241;
                                attribute sigma_Ixz : Real = 0.022566176940390956;
                                attribute Iyz : Real = 0.028143453031371238;
                                attribute sigma_Iyz : Real = 0.02209918015384651;
                            }
                            part <'C.1.2.2.2.2.2.2'> 'Part 957' {
                                attribute POIconv : String = "+";
                                attribute Ipoint : Boolean = false;
                                attribute mass : Real = 0.19667191374581308;
                                attribute sigma_mass : Real = 0.28909372274994966;
                                attribute Cx : Real = -99.83924245461822;
                                attribute sigma_Cx : Real = 28.721044428837228;
                                attribute Cy : Real = -42.325388733297586;
                                attribute sigma_Cy : Real = 28.23690002309109;
                                attribute Cz : Real = 63.988291611894965;
                                attribute sigma_Cz : Real = 29.057750463592832;
                                attribute Ixx : Real = 0.23759592093800355;
                                attribute sigma_Ixx : Real = 0.37074144170588635;
                                attribute Iyy : Real = 0.2494436476457511;
                                attribute sigma_Iyy : Real = 0.3723953238821935;
                                attribute Izz : Real = 0.19041222416218706;
                                attribute sigma_Izz : Real = 0.37017423652493897;
                                attribute Ixy : Real = -0.0023721276633502306;
                                attribute sigma_Ixy : Real = 0.02351283871158888;
                                attribute Ixz : Real = -0.02768849944165324;
                                attribute sigma_Ixz : Real = 0.022566176940390956;
                                attribute Iyz : Real = -0.003604262125553083;
                                attribute sigma_Iyz : Real = 0.02209918015384651;
                            }
                        }
                        part <'C.1.2.2.2.2.3'> 'Subassembly 272' {
                            attribute POIconv : String = "-";
                            attribute Ipoint : Boolean = false;
                            attribute mass : Real = 2.9424204367715863;
                            attribute sigma_mass : Real = 0.6464332159373649;
                            attribute Cx : Real = -15.305475562612491;
                            attribute sigma_Cx : Real = 18.560881131740402;
                            attribute Cy : Real = 10.193435427243193;
                            attribute sigma_Cy : Real = 22.71915142567864;
                            attribute Cz : Real = 16.651185513946736;
                            attribute sigma_Cz : Real = 20.309980850986612;
                            attribute Ixx : Real = 29961.88444067313;
                            attribute sigma_Ixx : Real = 10985.71103825737;
                            attribute Iyy : Real = 17612.39423306465;
                            attribute sigma_Iyy : Real = 8128.784638322783;
                            attribute Izz : Real = 30969.15939244512;
                            attribute sigma_Izz : Real = 11020.290225276554;
                            attribute Ixy : Real = 2077.0898521024938;
                            attribute sigma_Ixy : Real = 5362.998429182421;
                            attribute Ixz : Real = -6993.898194692612;
                            attribute sigma_Ixz : Real = 3623.040510507921;
                            attribute Iyz : Real = -236.90555945986324;
                            attribute sigma_Iyz : Real = 5127.638718464874;
                            part <'C.1.2.2.2.2.3.1'> 'Part 958' {
                                attribute POIconv : String = "-";
                                attribute Ipoint : Boolean = false;
                                attribute mass : Real = 0.6220170653872192;
                                attribute sigma_mass : Real = 0.28909372274994966;
                                attribute Cx : Real = -88.4271802380681;
                                attribute sigma_Cx : Real = 28.721044428837228;
                                attribute Cy : Real = -81.5281419083476;
                                attribute sigma_Cy : Real = 28.23690002309109;
                                attribute Cz : Real = -27.723316801711917;
                                attribute sigma_Cz : Real = 29.057750463592832;
                                attribute Ixx : Real = 0.7736162177564065;
                                attribute sigma_Ixx : Real = 0.37074144170588635;
                                attribute Iyy : Real = 0.8860050731648637;
                                attribute sigma_Iyy : Real = 0.3723953238821935;
                                attribute Izz : Real = 0.7255147558331203;
                                attribute sigma_Izz : Real = 0.37017423652493897;
                                attribute Ixy : Real = -0.046987189859727774;
                                attribute sigma_Ixy : Real = 0.02351283871158888;
                                attribute Ixz : Real = 0.025245912547133355;
                                attribute sigma_Ixz : Real = 0.022566176940390956;
                                attribute Iyz : Real = -0.013774643422691968;
                                attribute sigma_Iyz : Real = 0.02209918015384651;
                            }
                            part <'C.1.2.2.2.2.3.2'> 'Part 959' {
                                attribute POIconv : String = "+";
                                attribute Ipoint : Boolean = false;
                                attribute mass : Real = 0.823775424022926;
                                attribute sigma_mass : Real = 0.28909372274994966;
                                attribute Cx : Real = -43.416218645870686;
                                attribute sigma_Cx : Real = 28.721044428837228;
                                attribute Cy : Real = 71.37513617053628;
                                attribute sigma_Cy : Real = 28.23690002309109;
                                attribute Cz : Real = -34.72619606181979;
                                attribute sigma_Cz : Real = 29.057750463592832;
                                attribute Ixx : Real = 1.3041354088849226;
                                attribute sigma_Ixx : Real = 0.37074144170588635;
                                attribute Iyy : Real = 1.1654770404293808;
                                attribute sigma_Iyy : Real = 0.3723953238821935;
                                attribute Izz : Real = 1.1427817380818417;
                                attribute sigma_Izz : Real = 0.37017423652493897;
                                attribute Ixy : Real = 0.015010004872013545;
                                attribute sigma_Ixy : Real = 0.02351283871158888;
                                attribute Ixz : Real = 0.01782261799650988;
                                attribute sigma_Ixz : Real = 0.022566176940390956;
                                attribute Iyz : Real = 0.014099498696372635;
                                attribute sigma_Iyz : Real = 0.02209918015384651;
                            }
                            part <'C.1.2.2.2.2.3.3'> 'Part 960' {
                                attribute POIconv : String = "-";
                                attribute Ipoint : Boolean = false;
                                attribute mass : Real = 0.643063347045565;
                                attribute sigma_mass : Real = 0.28909372274994966;
                                attribute Cx : Real = 73.45139910466969;
                                attribute sigma_Cx : Real = 28.721044428837228;
                                attribute Cy : Real = -93.64247056655586;
                                attribute sigma_Cy : Real = 28.23690002309109;
                                attribute Cz : Real = 66.66100104339421;
                                attribute sigma_Cz : Real = 29.057750463592832;
                                attribute Ixx : Real = 0.6549345347317238;
                                attribute sigma_Ixx : Real = 0.37074144170588635;
                                attribute Iyy : Real = 0.8409070444321589;
                                attribute sigma_Iyy : Real = 0.3723953238821935;
                                attribute Izz : Real = 0.7583692077825698;
                                attribute sigma_Izz : Real = 0.37017423652493897;
                                attribute Ixy : Real = 0.0428066388724407;
                                attribute sigma_Ixy : Real = 0.02351283871158888;
                                attribute Ixz : Real = 0.08521091190831898;
                                attribute sigma_Ixz : Real = 0.022566176940390956;
                                attribute Iyz : Real = -0.027444675440931342;
                                attribute sigma_Iyz : Real = 0.02209918015384651;
                            }
                            part <'C.1.2.2.2.2.3.4'> 'Part 961' {
                                attribute POIconv : String = "+";
                                attribute Ipoint : Boolean = false;
                                attribute mass : Real = 0.7869032913711853;
                                attribute sigma_mass : Real = 0.28909372274994966;
                                attribute Cx : Real = 1.5268539544194937;
                                attribute sigma_Cx : Real = 28.721044428837228;
                                attribute Cy : Real = 99.22892670147121;
                                attribute sigma_Cy : Real = 28.23690002309109;
                                attribute Cz : Real = 73.58403005637228;
                                attribute sigma_Cz : Real = 29.057750463592832;
                                attribute Ixx : Real = 0.7824877417217395;
                                attribute sigma_Ixx : Real = 0.37074144170588635;
                                attribute Iyy : Real = 0.7504723209460015;
                                attribute sigma_Iyy : Real = 0.3723953238821935;
                                attribute Izz : Real = 0.76235124883583;
                                attribute sigma_Izz : Real = 0.37017423652493897;
                                attribute Ixy : Real = 0.010626578362149159;
                                attribute sigma_Ixy : Real = 0.02351283871158888;
                                attribute Ixz : Real = 0.005201274982690693;
                                attribute sigma_Ixz : Real = 0.022566176940390956;
                                attribute Iyz : Real = -0.01605734714355661;
                                attribute sigma_Iyz : Real = 0.02209918015384651;
                            }
                            part <'C.1.2.2.2.2.3.5'> 'Part 962' {
                                attribute POIconv : String = "-";
                                attribute Ipoint : Boolean = false;
                                attribute mass : Real = 0.06666130894469097;
                                attribute sigma_mass : Real = 0.28909372274994966;
                                attribute Cx : Real = -40.534817148;
                                attribute sigma_Cx : Real = 28.721044428837228;
                                attribute Cy : Real = 60.644725197926164;
                                attribute sigma_Cy : Real = 28.23690002309109;
                                attribute Cz : Real = -88.8822975102812;
                                attribute sigma_Cz : Real = 29.057750463592832;
                                attribute Ixx : Real = 0.10365734419264018;
                                attribute sigma_Ixx : Real = 0.37074144170588635;
                                attribute Iyy : Real = 0.08204556296858923;
                                attribute sigma_Iyy : Real = 0.3723953238821935;
                                attribute Izz : Real = 0.08352699397535596;
                                attribute sigma_Izz : Real = 0.37017423652493897;
                                attribute Ixy : Real = -5.733377728265961e-05;
                                attribute sigma_Ixy : Real = 0.02351283871158888;
                                attribute Ixz : Real = 0.0029487717074824634;
                                attribute sigma_Ixz : Real = 0.022566176940390956;
                                attribute Iyz : Real = -0.00039419111941320047;
                                attribute sigma_Iyz : Real = 0.02209918015384651;
                            }
                        }
                        part <'C.1.2.2.2.2.4'> 'Subassembly 273' {
                            attribute POIconv : String = "-";
                            attribute Ipoint : Boolean = false;
                            attribute mass : Real = 0.521871658581309;
                            attribute sigma_mass : Real = 0.5007250159521434;
                            attribute Cx : Real = -53.81467755493582;
                            attribute sigma_Cx : Real = 38.382464223540616;
                            attribute Cy : Real = -24.679602702850218;
                            attribute sigma_Cy : Real = 77.51194449389524;
                            attribute Cz : Real = 67.54220857547718;
                            attribute sigma_Cz : Real = 49.53557573735341;
                            attribute Ixx : Real = 2475.0093449735805;
                            attribute sigma_Ixx : Real = 5826.650499291424;
                            attribute Iyy : Real = 904.6706351257094;
                            attribute sigma_Iyy : Real = 2081.582578254174;
                            attribute Izz : Real = 1860.1765169508258;
                            attribute sigma_Izz : Real = 4513.263180477497;
                            attribute Ixy : Real = 195.863524519563;
                            attribute sigma_Ixy : Real = 1161.0569629968466;
                            attribute Ixz : Real = -8.052929678051527;
                            attribute sigma_Ixz : Real = 377.7272917279173;
                            attribute Iyz : Real = 1059.8422908081754;
                            attribute sigma_Iyz : Real = 2641.641723968717;
                            part <'C.1.2.2.2.2.4.1'> 'Part 963' {
                                attribute POIconv : String = "+";
                                attribute Ipoint : Boolean = false;
                                attribute mass : Real = 0.041582843948155646;
                                attribute sigma_mass : Real = 0.28909372274994966;
                                attribute Cx : Real = 2.6299283374100924;
                                attribute sigma_Cx : Real = 28.721044428837228;
                                attribute Cy : Real = -89.00875230319798;
                                attribute sigma_Cy : Real = 28.23690002309109;
                                attribute Cz : Real = 61.91454012878239;
                                attribute sigma_Cz : Real = 29.057750463592832;
                                attribute Ixx : Real = 0.06251470225361101;
                                attribute sigma_Ixx : Real = 0.37074144170588635;
                                attribute Iyy : Real = 0.06655216657533557;
                                attribute sigma_Iyy : Real = 0.3723953238821935;
                                attribute Izz : Real = 0.06251163909186692;
                                attribute sigma_Izz : Real = 0.37017423652493897;
                                attribute Ixy : Real = 0.0007832442366003815;
                                attribute sigma_Ixy : Real = 0.02351283871158888;
                                attribute Ixz : Real = 0.00046678940832468006;
                                attribute sigma_Ixz : Real = 0.022566176940390956;
                                attribute Iyz : Real = -0.0023940572901619975;
                                attribute sigma_Iyz : Real = 0.02209918015384651;
                            }
                            part <'C.1.2.2.2.2.4.2'> 'Part 964' {
                                attribute POIconv : String = "-";
                                attribute Ipoint : Boolean = false;
                                attribute mass : Real = 0.3805989583923947;
                                attribute sigma_mass : Real = 0.28909372274994966;
                                attribute Cx : Real = -58.100847620517015;
                                attribute sigma_Cx : Real = 28.721044428837228;
                                attribute Cy : Real = -47.9768980294466;
                                attribute sigma_Cy : Real = 28.23690002309109;
                                attribute Cz : Real = 88.36092092096806;
                                attribute sigma_Cz : Real = 29.057750463592832;
                                attribute Ixx : Real = 0.42014221032729493;
                                attribute sigma_Ixx : Real = 0.37074144170588635;
                                attribute Iyy : Real = 0.42071249358644336;
                                attribute sigma_Iyy : Real = 0.3723953238821935;
                                attribute Izz : Real = 0.38071988731261963;
                                attribute sigma_Izz : Real = 0.37017423652493897;
                                attribute Ixy : Real = 0.00327987965315247;
                                attribute sigma_Ixy : Real = 0.02351283871158888;
                                attribute Ixz : Real = -0.008576809208006127;
                                attribute sigma_Ixz : Real = 0.022566176940390956;
                                attribute Iyz : Real = 0.011310037607792516;
                                attribute sigma_Iyz : Real = 0.02209918015384651;
                            }
                            part <'C.1.2.2.2.2.4.3'> 'Part 965' {
                                attribute POIconv : String = "+";
                                attribute Ipoint : Boolean = false;
                                attribute mass : Real = 0.09968985624075867;
                                attribute sigma_mass : Real = 0.28909372274994966;
                                attribute Cx : Real = -60.995100950822234;
                                attribute sigma_Cx : Real = 28.721044428837228;
                                attribute Cy : Real = 91.09862949699163;
                                attribute sigma_Cy : Real = 28.23690002309109;
                                attribute Cz : Real = -9.59267821162939;
                                attribute sigma_Cz : Real = 29.057750463592832;
                                attribute Ixx : Real = 0.1594884376434478;
                                attribute sigma_Ixx : Real = 0.37074144170588635;
                                attribute Iyy : Real = 0.15928204896182166;
                                attribute sigma_Iyy : Real = 0.3723953238821935;
                                attribute Izz : Real = 0.16095520879840836;
                                attribute sigma_Izz : Real = 0.37017423652493897;
                                attribute Ixy : Real = -0.0016440301855379074;
                                attribute sigma_Ixy : Real = 0.02351283871158888;
                                attribute Ixz : Real = 0.00021439563241317495;
                                attribute sigma_Ixz : Real = 0.022566176940390956;
                                attribute Iyz : Real = -0.0002172842045158165;
                                attribute sigma_Iyz : Real = 0.02209918015384651;
                            }
                        }
                    }
                    part <'C.1.2.2.2.3'> 'Assembly 79' {
                        attribute POIconv : String = "-";
                        attribute Ipoint : Boolean = false;
                        attribute mass : Real = 9.06946936337091;
                        attribute sigma_mass : Real = 1.2265207905297186;
                        attribute Cx : Real = 9.649156245546267;
                        attribute sigma_Cx : Real = 9.930916568075176;
                        attribute Cy : Real = -3.2748510309521133;
                        attribute sigma_Cy : Real = 10.885049148059657;
                        attribute Cz : Real = -4.306832522817939;
                        attribute sigma_Cz : Real = 10.957069916976632;
                        attribute Ixx : Real = 64657.459793986985;
                        attribute sigma_Ixx : Real = 14888.885378310464;
                        attribute Iyy : Real = 55379.18854514236;
                        attribute sigma_Iyy : Real = 13744.54013749921;
                        attribute Izz : Real = 60287.54963006567;
                        attribute sigma_Izz : Real = 14194.453862498223;
                        attribute Ixy : Real = -5782.508908467727;
                        attribute sigma_Ixy : Real = 6744.314974617259;
                        attribute Ixz : Real = 1884.082748953625;
                        attribute sigma_Ixz : Real = 6299.741771365872;
                        attribute Iyz : Real = 3574.2709205797055;
                        attribute sigma_Iyz : Real = 7015.085812927754;
                        part <'C.1.2.2.2.3.1'> 'Subassembly 274' {
                            attribute POIconv : String = "-";
                            attribute Ipoint : Boolean = false;
                            attribute mass : Real = 1.8748611525981687;
                            attribute sigma_mass : Real = 0.6464332159373649;
                            attribute Cx : Real = 32.996299752554094;
                            attribute sigma_Cx : Real = 17.191596418755513;
                            attribute Cy : Real = 2.326209298569901;
                            attribute sigma_Cy : Real = 21.127896412916265;
                            attribute Cz : Real = 12.534645608202972;
                            attribute sigma_Cz : Real = 18.068809680563735;
                            attribute Ixx : Real = 7401.288719982533;
                            attribute sigma_Ixx : Real = 4176.623630650494;
                            attribute Iyy : Real = 3790.782671077644;
                            attribute sigma_Iyy : Real = 2695.1261457650735;
                            attribute Izz : Real = 6869.806915614263;
                            attribute sigma_Izz : Real = 4233.846265939242;
                            attribute Ixy : Real = -2404.02930660707;
                            attribute sigma_Ixy : Real = 1994.202029693715;
                            attribute Ixz : Real = -685.4994861301873;
                            attribute sigma_Ixz : Real = 1228.0708613756265;
                            attribute Iyz : Real = -2244.0385661066866;
                            attribute sigma_Iyz : Real = 1855.3718953781029;
                            part <'C.1.2.2.2.3.1.1'> 'Part 966' {
                                attribute POIconv : String = "-";
                                attribute Ipoint : Boolean = false;
                                attribute mass : Real = 0.345393353250809;
                                attribute sigma_mass : Real = 0.28909372274994966;
                                attribute Cx : Real = 49.225673638284206;
                                attribute sigma_Cx : Real = 28.721044428837228;
                                attribute Cy : Real = -13.037929870188236;
                                attribute sigma_Cy : Real = 28.23690002309109;
                                attribute Cz : Real = -34.64252627454698;
                                attribute sigma_Cz : Real = 29.057750463592832;
                                attribute Ixx : Real = 0.47913723832637867;
                                attribute sigma_Ixx : Real = 0.37074144170588635;
                                attribute Iyy : Real = 0.4586625256694213;
                                attribute sigma_Iyy : Real = 0.3723953238821935;
                                attribute Izz : Real = 0.47473932191825574;
                                attribute sigma_Izz : Real = 0.37017423652493897;
                                attribute Ixy : Real = 0.017509495424065775;
                                attribute sigma_Ixy : Real = 0.02351283871158888;
                                attribute Ixz : Real = -0.02868000192956314;
                                attribute sigma_Ixz : Real = 0.022566176940390956;
                                attribute Iyz : Real = 0.002978637095086272;
                                attribute sigma_Iyz : Real = 0.02209918015384651;
                            }
                            part <'C.1.2.2.2.3.1.2'> 'Part 967' {
                                attribute POIconv : String = "+";
                                attribute Ipoint : Boolean = false;
                                attribute mass : Real = 0.147076126674423;
                                attribute sigma_mass : Real = 0.28909372274994966;
                                attribute Cx : Real = 72.91318336501718;
                                attribute sigma_Cx : Real = 28.721044428837228;
                                attribute Cy : Real = 25.294630136340857;
                                attribute sigma_Cy : Real = 28.23690002309109;
                                attribute Cz : Real = 6.516283191740513;
                                attribute sigma_Cz : Real = 29.057750463592832;
                                attribute Ixx : Real = 0.21739396030556551;
                                attribute sigma_Ixx : Real = 0.37074144170588635;
                                attribute Iyy : Real = 0.23286888073360199;
                                attribute sigma_Iyy : Real = 0.3723953238821935;
                                attribute Izz : Real = 0.22638707764568097;
                                attribute sigma_Izz : Real = 0.37017423652493897;
                                attribute Ixy : Real = 0.0006615551163557344;
                                attribute sigma_Ixy : Real = 0.02351283871158888;
                                attribute Ixz : Real = 0.0015978837683497038;
                                attribute sigma_Ixz : Real = 0.022566176940390956;
                                attribute Iyz : Real = 0.00033473494387656984;
                                attribute sigma_Iyz : Real = 0.02209918015384651;
                            }
                            part <'C.1.2.2.2.3.1.3'> 'Part 968' {
                                attribute POIconv : String = "-";
                                attribute Ipoint : Boolean = false;
                                attribute mass : Real = 0.5250803465456702;
                                attribute sigma_mass : Real = 0.28909372274994966;
                                attribute Cx : Real = 41.28240216523409;
                                attribute sigma_Cx : Real = 28.721044428837228;
                                attribute Cy : Real = 56.341146072372794;
                                attribute sigma_Cy : Real = 28.23690002309109;
                                attribute Cz : Real = 29.793682508170605;
                                attribute sigma_Cz : Real = 29.057750463592832;
                                attribute Ixx : Real = 0.6142898985369039;
                                attribute sigma_Ixx : Real = 0.37074144170588635;
                                attribute Iyy : Real = 0.6230022973423036;
                                attribute sigma_Iyy : Real = 0.3723953238821935;
                                attribute Izz : Real = 0.6394846616925042;
                                attribute sigma_Izz : Real = 0.37017423652493897;
                                attribute Ixy : Real = 0.06041707099300492;
                                attribute sigma_Ixy : Real = 0.02351283871158888;
                                attribute Ixz : Real = 0.04082566972114808;
                                attribute sigma_Ixz : Real = 0.022566176940390956;
                                attribute Iyz : Real = -0.012794288708073476;
                                attribute sigma_Iyz : Real = 0.02209918015384651;
                            }
                            part <'C.1.2.2.2.3.1.4'> 'Part 969' {
                                attribute POIconv : String = "+";
                                attribute Ipoint : Boolean = false;
                                attribute mass : Real = 0.4892021876189392;
                                attribute sigma_mass : Real = 0.28909372274994966;
                                attribute Cx : Real = -14.718003058806062;
                                attribute sigma_Cx : Real = 28.721044428837228;
                                attribute Cy : Real = -77.48289168812335;
                                attribute sigma_Cy : Real = 28.23690002309109;
                                attribute Cz : Real = -9.802870312705636;
                                attribute sigma_Cz : Real = 29.057750463592832;
                                attribute Ixx : Real = 0.6526306182681287;
                                attribute sigma_Ixx : Real = 0.37074144170588635;
                                attribute Iyy : Real = 0.5867509579436452;
                                attribute sigma_Iyy : Real = 0.3723953238821935;
                                attribute Izz : Real = 0.5518915429797854;
                                attribute sigma_Izz : Real = 0.37017423652493897;
                                attribute Ixy : Real = 0.06013613675420441;
                                attribute sigma_Ixy : Real = 0.02351283871158888;
                                attribute Ixz : Real = 0.004444479745731449;
                                attribute sigma_Ixz : Real = 0.022566176940390956;
                                attribute Iyz : Real = -0.002495198961270224;
                                attribute sigma_Iyz : Real = 0.02209918015384651;
                            }
                            part <'C.1.2.2.2.3.1.5'> 'Part 970' {
                                attribute POIconv : String = "-";
                                attribute Ipoint : Boolean = false;
                                attribute mass : Real = 0.3681091385083273;
                                attribute sigma_mass : Real = 0.28909372274994966;
                                attribute Cx : Real = 53.410716308280826;
                                attribute sigma_Cx : Real = 28.721044428837228;
                                attribute Cy : Real = 36.58010014332831;
                                attribute sigma_Cy : Real = 28.23690002309109;
                                attribute Cz : Real = 64.2720723990351;
                                attribute sigma_Cz : Real = 29.057750463592832;
                                attribute Ixx : Real = 0.4316995717801538;
                                attribute sigma_Ixx : Real = 0.37074144170588635;
                                attribute Iyy : Real = 0.45032304653763955;
                                attribute sigma_Iyy : Real = 0.3723953238821935;
                                attribute Izz : Real = 0.40388473713453177;
                                attribute sigma_Izz : Real = 0.37017423652493897;
                                attribute Ixy : Real = -0.006765216340014524;
                                attribute sigma_Ixy : Real = 0.02351283871158888;
                                attribute Ixz : Real = -0.005028606381440707;
                                attribute sigma_Ixz : Real = 0.022566176940390956;
                                attribute Iyz : Real = -0.01898847873314777;
                                attribute sigma_Iyz : Real = 0.02209918015384651;
                            }
                        }
                        part <'C.1.2.2.2.3.2'> 'Subassembly 275' {
                            attribute POIconv : String = "-";
                            attribute Ipoint : Boolean = false;
                            attribute mass : Real = 2.1342177796440662;
                            attribute sigma_mass : Real = 0.5781874454998993;
                            attribute Cx : Real = 25.340767387752003;
                            attribute sigma_Cx : Real = 20.413016108394746;
                            attribute Cy : Real = -31.899270034148934;
                            attribute sigma_Cy : Real = 18.91106443311256;
                            attribute Cz : Real = 6.173472001982143;
                            attribute sigma_Cz : Real = 25.51019494897884;
                            attribute Ixx : Real = 13568.7715108789;
                            attribute sigma_Ixx : Real = 7065.827290488001;
                            attribute Iyy : Real = 15928.633790602304;
                            attribute sigma_Iyy : Real = 7371.7838104122275;
                            attribute Izz : Real = 7246.79010267636;
                            attribute sigma_Izz : Real = 4725.180811098052;
                            attribute Ixy : Real = 2682.972203464976;
                            attribute sigma_Ixy : Real = 2230.437644020421;
                            attribute Ixz : Real = 1358.9463414298577;
                            attribute sigma_Ixz : Real = 3022.4430010116184;
                            attribute Iyz : Real = 482.4729219214339;
                            attribute sigma_Iyz : Real = 3076.3748539002354;
                            part <'C.1.2.2.2.3.2.1'> 'Part 971' {
                                attribute POIconv : String = "+";
                                attribute Ipoint : Boolean = false;
                                attribute mass : Real = 0.2022086534788832;
                                attribute sigma_mass : Real = 0.28909372274994966;
                                attribute Cx : Real = 50.79826274886727;
                                attribute sigma_Cx : Real = 28.721044428837228;
                                attribute Cy : Real = -89.35999190434813;
                                attribute sigma_Cy : Real = 28.23690002309109;
                                attribute Cz : Real = -90.66908159293234;
                                attribute sigma_Cz : Real = 29.057750463592832;
                                attribute Ixx : Real = 0.304458476429242;
                                attribute sigma_Ixx : Real = 0.37074144170588635;
                                attribute Iyy : Real = 0.2881186650118538;
                                attribute sigma_Iyy : Real = 0.3723953238821935;
                                attribute Izz : Real = 0.3122199907550542;
                                attribute sigma_Izz : Real = 0.37017423652493897;
                                attribute Ixy : Real = 0.007494641712167683;
                                attribute sigma_Ixy : Real = 0.02351283871158888;
                                attribute Ixz : Real = 0.022637634702947024;
                                attribute sigma_Ixz : Real = 0.022566176940390956;
                                attribute Iyz : Real = -0.007655420762313105;
                                attribute sigma_Iyz : Real = 0.02209918015384651;
                            }
                            part <'C.1.2.2.2.3.2.2'> 'Part 972' {
                                attribute POIconv : String = "-";
                                attribute Ipoint : Boolean = false;
                                attribute mass : Real = 0.7260099024197553;
                                attribute sigma_mass : Real = 0.28909372274994966;
                                attribute Cx : Real = 65.38590369746089;
                                attribute sigma_Cx : Real = 28.721044428837228;
                                attribute Cy : Real = -32.00422446243465;
                                attribute sigma_Cy : Real = 28.23690002309109;
                                attribute Cz : Real = -55.6092987768352;
                                attribute sigma_Cz : Real = 29.057750463592832;
                                attribute Ixx : Real = 0.9560992614910911;
                                attribute sigma_Ixx : Real = 0.37074144170588635;
                                attribute Iyy : Real = 0.9985063911532315;
                                attribute sigma_Iyy : Real = 0.3723953238821935;
                                attribute Izz : Real = 0.9197697673823055;
                                attribute sigma_Izz : Real = 0.37017423652493897;
                                attribute Ixy : Real = -0.012492996004439965;
                                attribute sigma_Ixy : Real = 0.02351283871158888;
                                attribute Ixz : Real = 0.008983591062734532;
                                attribute sigma_Ixz : Real = 0.022566176940390956;
                                attribute Iyz : Real = 0.05464491021346929;
                                attribute sigma_Iyz : Real = 0.02209918015384651;
                            }
                            part <'C.1.2.2.2.3.2.3'> 'Part 973' {
                                attribute POIconv : String = "-";
                                attribute Ipoint : Boolean = false;
                                attribute mass : Real = 0.47460219804244114;
                                attribute sigma_mass : Real = 0.28909372274994966;
                                attribute Cx : Real = -59.95682361535728;
                                attribute sigma_Cx : Real = 28.721044428837228;
                                attribute Cy : Real = 23.87014077976346;
                                attribute sigma_Cy : Real = 28.23690002309109;
                                attribute Cz : Real = -2.4481114000082016;
                                attribute sigma_Cz : Real = 29.057750463592832;
                                attribute Ixx : Real = 0.5965026386467733;
                                attribute sigma_Ixx : Real = 0.37074144170588635;
                                attribute Iyy : Real = 0.5850507321042127;
                                attribute sigma_Iyy : Real = 0.3723953238821935;
                                attribute Izz : Real = 0.5739573068366166;
                                attribute sigma_Izz : Real = 0.37017423652493897;
                                attribute Ixy : Real = 0.017461955802500373;
                                attribute sigma_Ixy : Real = 0.02351283871158888;
                                attribute Ixz : Real = 0.0007807431255930462;
                                attribute sigma_Ixz : Real = 0.022566176940390956;
                                attribute Iyz : Real = -0.00020049108263685717;
                                attribute sigma_Iyz : Real = 0.02209918015384651;
                            }
                            part <'C.1.2.2.2.3.2.4'> 'Part 974' {
                                attribute POIconv : String = "+";
                                attribute Ipoint : Boolean = false;
                                attribute mass : Real = 0.7313970257029868;
                                attribute sigma_mass : Real = 0.28909372274994966;
                                attribute Cx : Real = 33.90182601287961;
                                attribute sigma_Cx : Real = 28.721044428837228;
                                attribute Cy : Real = -52.097645588219166;
                                attribute sigma_Cy : Real = 28.23690002309109;
                                attribute Cz : Real = 99.86968045122921;
                                attribute sigma_Cz : Real = 29.057750463592832;
                                attribute Ixx : Real = 0.8877209397004133;
                                attribute sigma_Ixx : Real = 0.37074144170588635;
                                attribute Iyy : Real = 0.9488907643141312;
                                attribute sigma_Iyy : Real = 0.3723953238821935;
                                attribute Izz : Real = 0.8792649348780672;
                                attribute sigma_Izz : Real = 0.37017423652493897;
                                attribute Ixy : Real = 0.022408164986990456;
                                attribute sigma_Ixy : Real = 0.02351283871158888;
                                attribute Ixz : Real = 0.0759425053446322;
                                attribute sigma_Ixz : Real = 0.022566176940390956;
                                attribute Iyz : Real = 0.0380751266551434;
                                attribute sigma_Iyz : Real = 0.02209918015384651;
                            }
                        }
                        part <'C.1.2.2.2.3.3'> 'Subassembly 276' {
                            attribute POIconv : String = "-";
                            attribute Ipoint : Boolean = false;
                            attribute mass : Real = 2.109700438496191;
                            attribute sigma_mass : Real = 0.5781874454998993;
                            attribute Cx : Real = -23.839168480677415;
                            attribute sigma_Cx : Real = 16.60768512117895;
                            attribute Cy : Real = 11.638745590594974;
                            attribute sigma_Cy : Real = 22.33006067026329;
                            attribute Cz : Real = -47.64626640529376;
                            attribute sigma_Cz : Real = 19.853665772765467;
                            attribute Ixx : Real = 13019.398364393299;
                            attribute sigma_Ixx : Real = 6181.649476172728;
                            attribute Iyy : Real = 4645.851338496572;
                            attribute sigma_Iyy : Real = 3500.285341631488;
                            attribute Izz : Real = 10440.393241582706;
                            attribute sigma_Izz : Real = 5463.628885742765;
                            attribute Ixy : Real = 1241.3143056761146;
                            attribute sigma_Ixy : Real = 2484.197064572544;
                            attribute Ixz : Real = -1732.949490239539;
                            attribute sigma_Ixz : Real = 1584.9692742100945;
                            attribute Iyz : Real = -244.82141486942163;
                            attribute sigma_Iyz : Real = 2800.47784550183;
                            part <'C.1.2.2.2.3.3.1'> 'Part 975' {
                                attribute POIconv : String = "-";
                                attribute Ipoint : Boolean = false;
                                attribute mass : Real = 0.7002253949027508;
                                attribute sigma_mass : Real = 0.28909372274994966;
                                attribute Cx : Real = -48.32895137369633;
                                attribute sigma_Cx : Real = 28.721044428837228;
                                attribute Cy : Real = 94.38803419470787;
                                attribute sigma_Cy : Real = 28.23690002309109;
                                attribute Cz : Real = -73.54296059347689;
                                attribute sigma_Cz : Real = 29.057750463592832;
                                attribute Ixx : Real = 0.9179289537677093;
                                attribute sigma_Ixx : Real = 0.37074144170588635;
                                attribute Iyy : Real = 0.9453526066367571;
                                attribute sigma_Iyy : Real = 0.3723953238821935;
                                attribute Izz : Real = 1.0598639204396196;
                                attribute sigma_Izz : Real = 0.37017423652493897;
                                attribute Ixy : Real = 0.005793379845730145;
                                attribute sigma_Ixy : Real = 0.02351283871158888;
                                attribute Ixz : Real = 0.009932665524244062;
                                attribute sigma_Ixz : Real = 0.022566176940390956;
                                attribute Iyz : Real = -0.003364331952347276;
                                attribute sigma_Iyz : Real = 0.02209918015384651;
                            }
                            part <'C.1.2.2.2.3.3.2'> 'Part 976' {
                                attribute POIconv : String = "+";
                                attribute Ipoint : Boolean = false;
                                attribute mass : Real = 0.7271825440614484;
                                attribute sigma_mass : Real = 0.28909372274994966;
                                attribute Cx : Real = -27.61601754464209;
                                attribute sigma_Cx : Real = 28.721044428837228;
                                attribute Cy : Real = -61.12668598070741;
                                attribute sigma_Cy : Real = 28.23690002309109;
                                attribute Cz : Real = -75.3458530176431;
                                attribute sigma_Cz : Real = 29.057750463592832;
                                attribute Ixx : Real = 0.9541210459817209;
                                attribute sigma_Ixx : Real = 0.37074144170588635;
                                attribute Iyy : Real = 0.9697491713331543;
                                attribute sigma_Iyy : Real = 0.3723953238821935;
                                attribute Izz : Real = 1.1351335287392776;
                                attribute sigma_Izz : Real = 0.37017423652493897;
                                attribute Ixy : Real = 0.005582495038339213;
                                attribute sigma_Ixy : Real = 0.02351283871158888;
                                attribute Ixz : Real = 0.006671195595068952;
                                attribute sigma_Ixz : Real = 0.022566176940390956;
                                attribute Iyz : Real = 0.0011535569103235399;
                                attribute sigma_Iyz : Real = 0.02209918015384651;
                            }
                            part <'C.1.2.2.2.3.3.3'> 'Part 977' {
                                attribute POIconv : String = "-";
                                attribute Ipoint : Boolean = false;
                                attribute mass : Real = 0.38601829275116323;
                                attribute sigma_mass : Real = 0.28909372274994966;
                                attribute Cx : Real = 10.229263873770833;
                                attribute sigma_Cx : Real = 28.721044428837228;
                                attribute Cy : Real = 32.793070236220956;
                                attribute sigma_Cy : Real = 28.23690002309109;
                                attribute Cz : Real = 30.60879916884005;
                                attribute sigma_Cz : Real = 29.057750463592832;
                                attribute Ixx : Real = 0.4794250298044296;
                                attribute sigma_Ixx : Real = 0.37074144170588635;
                                attribute Iyy : Real = 0.4519723346396494;
                                attribute sigma_Iyy : Real = 0.3723953238821935;
                                attribute Izz : Real = 0.473361332684626;
                                attribute sigma_Izz : Real = 0.37017423652493897;
                                attribute Ixy : Real = -0.02470872411088412;
                                attribute sigma_Ixy : Real = 0.02351283871158888;
                                attribute Ixz : Real = -0.016706551862551232;
                                attribute sigma_Ixz : Real = 0.022566176940390956;
                                attribute Iyz : Real = 0.00608256028791015;
                                attribute sigma_Iyz : Real = 0.02209918015384651;
                            }
                            part <'C.1.2.2.2.3.3.4'> 'Part 978' {
                                attribute POIconv : String = "-";
                                attribute Ipoint : Boolean = false;
                                attribute mass : Real = 0.29627420678082855;
                                attribute sigma_mass : Real = 0.28909372274994966;
                                attribute Cx : Real = -1.0771852917969227;
                                attribute sigma_Cx : Real = 28.721044428837228;
                                attribute Cy : Real = -32.89890778250992;
                                attribute sigma_Cy : Real = 28.23690002309109;
                                attribute Cz : Real = -20.413750782608986;
                                attribute sigma_Cz : Real = 29.057750463592832;
                                attribute Ixx : Real = 0.3830441099038879;
                                attribute sigma_Ixx : Real = 0.37074144170588635;
                                attribute Iyy : Real = 0.4326566646366207;
                                attribute sigma_Iyy : Real = 0.3723953238821935;
                                attribute Izz : Real = 0.372606716061135;
                                attribute sigma_Izz : Real = 0.37017423652493897;
                                attribute Ixy : Real = 0.019626688675236842;
                                attribute sigma_Ixy : Real = 0.02351283871158888;
                                attribute Ixz : Real = 0.011439537622117968;
                                attribute sigma_Ixz : Real = 0.022566176940390956;
                                attribute Iyz : Real = 0.01459983770374012;
                                attribute sigma_Iyz : Real = 0.02209918015384651;
                            }
                        }
                        part <'C.1.2.2.2.3.4'> 'Subassembly 277' {
                            attribute POIconv : String = "-";
                            attribute Ipoint : Boolean = false;
                            attribute mass : Real = 2.9506899926324843;
                            attribute sigma_mass : Real = 0.6464332159373649;
                            attribute Cx : Real = 7.408448298092798;
                            attribute sigma_Cx : Real = 19.352236669995303;
                            attribute Cy : Real = 3.207128526082848;
                            attribute sigma_Cy : Real = 21.298806244116093;
                            attribute Cz : Real = 8.398852386999781;
                            attribute sigma_Cz : Real = 19.04673299208444;
                            attribute Ixx : Real = 23062.09043329524;
                            attribute sigma_Ixx : Real = 9395.448274683715;
                            attribute Iyy : Real = 21880.477340752208;
                            attribute sigma_Iyy : Real = 9174.554787243773;
                            attribute Izz : Real = 29401.604487785942;
                            attribute sigma_Izz : Real = 10600.68670518317;
                            attribute Ixy : Real = -9112.712095628898;
                            attribute sigma_Ixy : Real = 4943.875844990582;
                            attribute Ixz : Real = 7009.699882945631;
                            attribute sigma_Ixz : Real = 4367.95416656933;
                            attribute Iyz : Real = 3996.678980717107;
                            attribute sigma_Iyz : Real = 4457.372854984208;
                            part <'C.1.2.2.2.3.4.1'> 'Part 979' {
                                attribute POIconv : String = "-";
                                attribute Ipoint : Boolean = false;
                                attribute mass : Real = 0.27105822088592685;
                                attribute sigma_mass : Real = 0.28909372274994966;
                                attribute Cx : Real = -9.020871249958873;
                                attribute sigma_Cx : Real = 28.721044428837228;
                                attribute Cy : Real = 94.69756302423775;
                                attribute sigma_Cy : Real = 28.23690002309109;
                                attribute Cz : Real = -74.91972697898746;
                                attribute sigma_Cz : Real = 29.057750463592832;
                                attribute Ixx : Real = 0.39951975900346126;
                                attribute sigma_Ixx : Real = 0.37074144170588635;
                                attribute Iyy : Real = 0.4168247106634905;
                                attribute sigma_Iyy : Real = 0.3723953238821935;
                                attribute Izz : Real = 0.38660585833770034;
                                attribute sigma_Izz : Real = 0.37017423652493897;
                                attribute Ixy : Real = 0.02142547459437949;
                                attribute sigma_Ixy : Real = 0.02351283871158888;
                                attribute Ixz : Real = -0.006735890149523673;
                                attribute sigma_Ixz : Real = 0.022566176940390956;
                                attribute Iyz : Real = -0.010790705266209476;
                                attribute sigma_Iyz : Real = 0.02209918015384651;
                            }
                            part <'C.1.2.2.2.3.4.2'> 'Part 980' {
                                attribute POIconv : String = "-";
                                attribute Ipoint : Boolean = false;
                                attribute mass : Real = 0.887400543800788;
                                attribute sigma_mass : Real = 0.28909372274994966;
                                attribute Cx : Real = -78.64561681635678;
                                attribute sigma_Cx : Real = 28.721044428837228;
                                attribute Cy : Real = -30.86143396794796;
                                attribute sigma_Cy : Real = 28.23690002309109;
                                attribute Cz : Real = 81.71482505276799;
                                attribute sigma_Cz : Real = 29.057750463592832;
                                attribute Ixx : Real = 1.0497478499469302;
                                attribute sigma_Ixx : Real = 0.37074144170588635;
                                attribute Iyy : Real = 1.127254465104757;
                                attribute sigma_Iyy : Real = 0.3723953238821935;
                                attribute Izz : Real = 1.0835139532825706;
                                attribute sigma_Izz : Real = 0.37017423652493897;
                                attribute Ixy : Real = 0.0013066053331645168;
                                attribute sigma_Ixy : Real = 0.02351283871158888;
                                attribute Ixz : Real = 0.025583120864450644;
                                attribute sigma_Ixz : Real = 0.022566176940390956;
                                attribute Iyz : Real = -0.05861376076331369;
                                attribute sigma_Iyz : Real = 0.02209918015384651;
                            }
                            part <'C.1.2.2.2.3.4.3'> 'Part 981' {
                                attribute POIconv : String = "+";
                                attribute Ipoint : Boolean = false;
                                attribute mass : Real = 0.18562814097455702;
                                attribute sigma_mass : Real = 0.28909372274994966;
                                attribute Cx : Real = 49.00281825102866;
                                attribute sigma_Cx : Real = 28.721044428837228;
                                attribute Cy : Real = -38.7052065692842;
                                attribute sigma_Cy : Real = 28.23690002309109;
                                attribute Cz : Real = -38.003188418224454;
                                attribute sigma_Cz : Real = 29.057750463592832;
                                attribute Ixx : Real = 0.2746480668830507;
                                attribute sigma_Ixx : Real = 0.37074144170588635;
                                attribute Iyy : Real = 0.24110169344856022;
                                attribute sigma_Iyy : Real = 0.3723953238821935;
                                attribute Izz : Real = 0.25797114857032255;
                                attribute sigma_Izz : Real = 0.37017423652493897;
                                attribute Ixy : Real = 0.011830825459521818;
                                attribute sigma_Ixy : Real = 0.02351283871158888;
                                attribute Ixz : Real = -0.0054154966043420275;
                                attribute sigma_Ixz : Real = 0.022566176940390956;
                                attribute Iyz : Real = -0.0003837476468564319;
                                attribute sigma_Iyz : Real = 0.02209918015384651;
                            }
                            part <'C.1.2.2.2.3.4.4'> 'Part 982' {
                                attribute POIconv : String = "+";
                                attribute Ipoint : Boolean = false;
                                attribute mass : Real = 0.676604886027053;
                                attribute sigma_mass : Real = 0.28909372274994966;
                                attribute Cx : Real = -4.235508479177952;
                                attribute sigma_Cx : Real = 28.721044428837228;
                                attribute Cy : Real = -88.00108162686229;
                                attribute sigma_Cy : Real = 28.23690002309109;
                                attribute Cz : Real = -14.42916439846158;
                                attribute sigma_Cz : Real = 29.057750463592832;
                                attribute Ixx : Real = 0.7873501772649654;
                                attribute sigma_Ixx : Real = 0.37074144170588635;
                                attribute Iyy : Real = 0.9006000958302612;
                                attribute sigma_Iyy : Real = 0.3723953238821935;
                                attribute Izz : Real = 0.7933242008254806;
                                attribute sigma_Izz : Real = 0.37017423652493897;
                                attribute Ixy : Real = -0.0555925947585104;
                                attribute sigma_Ixy : Real = 0.02351283871158888;
                                attribute Ixz : Real = -0.03199452924541006;
                                attribute sigma_Ixz : Real = 0.022566176940390956;
                                attribute Iyz : Real = 0.03426014756302768;
                                attribute sigma_Iyz : Real = 0.02209918015384651;
                            }
                            part <'C.1.2.2.2.3.4.5'> 'Part 983' {
                                attribute POIconv : String = "-";
                                attribute Ipoint : Boolean = false;
                                attribute mass : Real = 0.9299982009441592;
                                attribute sigma_mass : Real = 0.28909372274994966;
                                attribute Cx : Real = 94.47850789874792;
                                attribute sigma_Cx : Real = 28.721044428837228;
                                attribute Cy : Real = 83.77207573503256;
                                attribute sigma_Cy : Real = 28.23690002309109;
                                attribute Cz : Real = -11.404815874993801;
                                attribute sigma_Cz : Real = 29.057750463592832;
                                attribute Ixx : Real = 0.9704152538984083;
                                attribute sigma_Ixx : Real = 0.37074144170588635;
                                attribute Iyy : Real = 1.096893040094133;
                                attribute sigma_Iyy : Real = 0.3723953238821935;
                                attribute Izz : Real = 1.1274372848676895;
                                attribute sigma_Izz : Real = 0.37017423652493897;
                                attribute Ixy : Real = 0.12173459347731425;
                                attribute sigma_Ixy : Real = 0.02351283871158888;
                                attribute Ixz : Real = -0.0744546613558762;
                                attribute sigma_Ixz : Real = 0.022566176940390956;
                                attribute Iyz : Real = 0.0017807762575389099;
                                attribute sigma_Iyz : Real = 0.02209918015384651;
                            }
                        }
                    }
                    part <'C.1.2.2.2.4'> 'Assembly 80' {
                        attribute POIconv : String = "-";
                        attribute Ipoint : Boolean = false;
                        attribute mass : Real = 6.745652276464039;
                        attribute sigma_mass : Real = 1.081689663197327;
                        attribute Cx : Real = -8.117696370826133;
                        attribute sigma_Cx : Real = 13.931142233627474;
                        attribute Cy : Real = 20.298185416552663;
                        attribute sigma_Cy : Real = 14.826744304903137;
                        attribute Cz : Real = 23.02056498636186;
                        attribute sigma_Cz : Real = 12.60159362503603;
                        attribute Ixx : Real = 41817.90857377379;
                        attribute sigma_Ixx : Real = 14859.548937260171;
                        attribute Iyy : Real = 38078.733179869116;
                        attribute sigma_Iyy : Real = 12793.510652740768;
                        attribute Izz : Real = 47324.68430244205;
                        attribute sigma_Izz : Real = 16070.812672717431;
                        attribute Ixy : Real = 11910.139738902039;
                        attribute sigma_Ixy : Real = 7304.085376747258;
                        attribute Ixz : Real = -3204.546125531811;
                        attribute sigma_Ixz : Real = 5743.814060984076;
                        attribute Iyz : Real = -4236.520801013972;
                        attribute sigma_Iyz : Real = 6599.609281023739;
                        part <'C.1.2.2.2.4.1'> 'Subassembly 278' {
                            attribute POIconv : String = "-";
                            attribute Ipoint : Boolean = false;
                            attribute mass : Real = 1.3205692829391917;
                            attribute sigma_mass : Real = 0.5007250159521434;
                            attribute Cx : Real = 48.76800229547341;
                            attribute sigma_Cx : Real = 28.234387799674032;
                            attribute Cy : Real = -37.207230579806485;
                            attribute sigma_Cy : Real = 34.14038171882054;
                            attribute Cz : Real = 32.46048700495723;
                            attribute sigma_Cz : Real = 37.0556137772505;
                            attribute Ixx : Real = 9127.431992405913;
                            attribute sigma_Ixx : Real = 7611.5961113593075;
                            attribute Iyy : Real = 8768.164147301504;
                            attribute sigma_Iyy : Real = 6734.930887924567;
                            attribute Izz : Real = 3013.3778600145342;
                            attribute sigma_Izz : Real = 5662.603715596907;
                            attribute Ixy : Real = 1398.5861100557618;
                            attribute sigma_Ixy : Real = 2536.1929755911515;
                            attribute Ixz : Real = 2802.66310522251;
                            attribute sigma_Ixz : Real = 2637.078232694427;
                            attribute Iyz : Real = -2390.9156281102923;
                            attribute sigma_Iyz : Real = 2588.7960519261064;
                            part <'C.1.2.2.2.4.1.1'> 'Part 984' {
                                attribute POIconv : String = "-";
                                attribute Ipoint : Boolean = false;
                                attribute mass : Real = 0.9030830010336358;
                                attribute sigma_mass : Real = 0.28909372274994966;
                                attribute Cx : Real = 36.13886944949627;
                                attribute sigma_Cx : Real = 28.721044428837228;
                                attribute Cy : Real = -30.839394126087427;
                                attribute sigma_Cy : Real = 28.23690002309109;
                                attribute Cz : Real = 77.82481363974512;
                                attribute sigma_Cz : Real = 29.057750463592832;
                                attribute Ixx : Real = 1.1268388168502792;
                                attribute sigma_Ixx : Real = 0.37074144170588635;
                                attribute Iyy : Real = 1.2171843808899903;
                                attribute sigma_Iyy : Real = 0.3723953238821935;
                                attribute Izz : Real = 1.1231479180062338;
                                attribute sigma_Izz : Real = 0.37017423652493897;
                                attribute Ixy : Real = -0.08846523203018197;
                                attribute sigma_Ixy : Real = 0.02351283871158888;
                                attribute Ixz : Real = 0.09914636000065566;
                                attribute sigma_Ixz : Real = 0.022566176940390956;
                                attribute Iyz : Real = -0.08055238601559153;
                                attribute sigma_Iyz : Real = 0.02209918015384651;
                            }
                            part <'C.1.2.2.2.4.1.2'> 'Part 985' {
                                attribute POIconv : String = "-";
                                attribute Ipoint : Boolean = false;
                                attribute mass : Real = 0.3415137503563892;
                                attribute sigma_mass : Real = 0.28909372274994966;
                                attribute Cx : Real = 97.62425692752004;
                                attribute sigma_Cx : Real = 28.721044428837228;
                                attribute Cy : Real = -79.90222480148077;
                                attribute sigma_Cy : Real = 28.23690002309109;
                                attribute Cz : Real = -94.51555516570807;
                                attribute sigma_Cz : Real = 29.057750463592832;
                                attribute Ixx : Real = 0.4679269479194403;
                                attribute sigma_Ixx : Real = 0.37074144170588635;
                                attribute Iyy : Real = 0.4454066207291212;
                                attribute sigma_Iyy : Real = 0.3723953238821935;
                                attribute Izz : Real = 0.5002983039618605;
                                attribute sigma_Izz : Real = 0.37017423652493897;
                                attribute Ixy : Real = -0.0006597816268589537;
                                attribute sigma_Ixy : Real = 0.02351283871158888;
                                attribute Ixz : Real = 0.03247867099086059;
                                attribute sigma_Ixz : Real = 0.022566176940390956;
                                attribute Iyz : Real = -0.00825297436467821;
                                attribute sigma_Iyz : Real = 0.02209918015384651;
                            }
                            part <'C.1.2.2.2.4.1.3'> 'Part 986' {
                                attribute POIconv : String = "+";
                                attribute Ipoint : Boolean = false;
                                attribute mass : Real = 0.07597253154916689;
                                attribute sigma_mass : Real = 0.28909372274994966;
                                attribute Cx : Real = -20.72984711267054;
                                attribute sigma_Cx : Real = 28.721044428837228;
                                attribute Cy : Real = 79.02218238450587;
                                attribute sigma_Cy : Real = 28.23690002309109;
                                attribute Cz : Real = 64.00230983272195;
                                attribute sigma_Cz : Real = 29.057750463592832;
                                attribute Ixx : Real = 0.09544365421840321;
                                attribute sigma_Ixx : Real = 0.37074144170588635;
                                attribute Iyy : Real = 0.09426236339841801;
                                attribute sigma_Iyy : Real = 0.3723953238821935;
                                attribute Izz : Real = 0.11696165641742655;
                                attribute sigma_Izz : Real = 0.37017423652493897;
                                attribute Ixy : Real = 0.0033198360274207302;
                                attribute sigma_Ixy : Real = 0.02351283871158888;
                                attribute Ixz : Real = 1.5352305710691155e-05;
                                attribute sigma_Ixz : Real = 0.022566176940390956;
                                attribute Iyz : Real = 0.0004469069577196507;
                                attribute sigma_Iyz : Real = 0.02209918015384651;
                            }
                        }
                        part <'C.1.2.2.2.4.2'> 'Subassembly 279' {
                            attribute POIconv : String = "-";
                            attribute Ipoint : Boolean = false;
                            attribute mass : Real = 1.4727800882102455;
                            attribute sigma_mass : Real = 0.5781874454998993;
                            attribute Cx : Real = 18.08837220561968;
                            attribute sigma_Cx : Real = 28.027226868235722;
                            attribute Cy : Real = 45.288231945380545;
                            attribute sigma_Cy : Real = 30.160616124699043;
                            attribute Cz : Real = 61.133782981026066;
                            attribute sigma_Cz : Real = 22.038771979527116;
                            attribute Ixx : Real = 6198.1268459160465;
                            attribute sigma_Ixx : Real = 6651.207071723668;
                            attribute Iyy : Real = 6316.172951743592;
                            attribute sigma_Iyy : Real = 4511.293562405224;
                            attribute Izz : Real = 9357.221727197202;
                            attribute sigma_Izz : Real = 6954.081689782366;
                            attribute Ixy : Real = 3405.6398385333646;
                            attribute sigma_Ixy : Real = 2930.593885922549;
                            attribute Ixz : Real = 1506.1054693287174;
                            attribute sigma_Ixz : Real = 1979.6184351489478;
                            attribute Iyz : Real = -2435.561988517882;
                            attribute sigma_Iyz : Real = 3026.898744769537;
                            part <'C.1.2.2.2.4.2.1'> 'Part 987' {
                                attribute POIconv : String = "+";
                                attribute Ipoint : Boolean = false;
                                attribute mass : Real = 0.21710612030676565;
                                attribute sigma_mass : Real = 0.28909372274994966;
                                attribute Cx : Real = 82.39852315746248;
                                attribute sigma_Cx : Real = 28.721044428837228;
                                attribute Cy : Real = -78.42894098721445;
                                attribute sigma_Cy : Real = 28.23690002309109;
                                attribute Cz : Real = -16.184576554223895;
                                attribute sigma_Cz : Real = 29.057750463592832;
                                attribute Ixx : Real = 0.26668405798555145;
                                attribute sigma_Ixx : Real = 0.37074144170588635;
                                attribute Iyy : Real = 0.27468988228096763;
                                attribute sigma_Iyy : Real = 0.3723953238821935;
                                attribute Izz : Real = 0.2675272316883201;
                                attribute sigma_Izz : Real = 0.37017423652493897;
                                attribute Ixy : Real = 0.0029725788459559724;
                                attribute sigma_Ixy : Real = 0.02351283871158888;
                                attribute Ixz : Real = -0.0005922818851304952;
                                attribute sigma_Ixz : Real = 0.022566176940390956;
                                attribute Iyz : Real = 0.0022198716083646182;
                                attribute sigma_Iyz : Real = 0.02209918015384651;
                            }
                            part <'C.1.2.2.2.4.2.2'> 'Part 988' {
                                attribute POIconv : String = "-";
                                attribute Ipoint : Boolean = false;
                                attribute mass : Real = 0.49863429153943434;
                                attribute sigma_mass : Real = 0.28909372274994966;
                                attribute Cx : Real = -42.80372844077647;
                                attribute sigma_Cx : Real = 28.721044428837228;
                                attribute Cy : Real = 95.79207706265152;
                                attribute sigma_Cy : Real = 28.23690002309109;
                                attribute Cz : Real = 73.12487671151757;
                                attribute sigma_Cz : Real = 29.057750463592832;
                                attribute Ixx : Real = 0.5813596533493391;
                                attribute sigma_Ixx : Real = 0.37074144170588635;
                                attribute Iyy : Real = 0.5358367288501008;
                                attribute sigma_Iyy : Real = 0.3723953238821935;
                                attribute Izz : Real = 0.585394063557518;
                                attribute sigma_Izz : Real = 0.37017423652493897;
                                attribute Ixy : Real = 0.006298687734254323;
                                attribute sigma_Ixy : Real = 0.02351283871158888;
                                attribute Ixz : Real = 0.031030187734254443;
                                attribute sigma_Ixz : Real = 0.022566176940390956;
                                attribute Iyz : Real = -0.04051270492051397;
                                attribute sigma_Iyz : Real = 0.02209918015384651;
                            }
                            part <'C.1.2.2.2.4.2.3'> 'Part 989' {
                                attribute POIconv : String = "+";
                                attribute Ipoint : Boolean = false;
                                attribute mass : Real = 0.46388317182497124;
                                attribute sigma_mass : Real = 0.28909372274994966;
                                attribute Cx : Real = 2.812653360888362;
                                attribute sigma_Cx : Real = 28.721044428837228;
                                attribute Cy : Real = 51.59658817574382;
                                attribute sigma_Cy : Real = 28.23690002309109;
                                attribute Cz : Real = 82.1117902174592;
                                attribute sigma_Cz : Real = 29.057750463592832;
                                attribute Ixx : Real = 0.6308201406250765;
                                attribute sigma_Ixx : Real = 0.37074144170588635;
                                attribute Iyy : Real = 0.603732900834014;
                                attribute sigma_Iyy : Real = 0.3723953238821935;
                                attribute Izz : Real = 0.6379810658410099;
                                attribute sigma_Izz : Real = 0.37017423652493897;
                                attribute Ixy : Real = -0.01752834907061877;
                                attribute sigma_Ixy : Real = 0.02351283871158888;
                                attribute Ixz : Real = 0.003630522253380732;
                                attribute sigma_Ixz : Real = 0.022566176940390956;
                                attribute Iyz : Real = -0.007568302627131665;
                                attribute sigma_Iyz : Real = 0.02209918015384651;
                            }
                            part <'C.1.2.2.2.4.2.4'> 'Part 990' {
                                attribute POIconv : String = "-";
                                attribute Ipoint : Boolean = false;
                                attribute mass : Real = 0.2931565045390744;
                                attribute sigma_mass : Real = 0.28909372274994966;
                                attribute Cx : Real = 98.2056837528944;
                                attribute sigma_Cx : Real = 28.721044428837228;
                                attribute Cy : Real = 41.02588784880936;
                                attribute sigma_Cy : Real = 28.23690002309109;
                                attribute Cz : Real = 64.80340650305152;
                                attribute sigma_Cz : Real = 29.057750463592832;
                                attribute Ixx : Real = 0.3358473755738956;
                                attribute sigma_Ixx : Real = 0.37074144170588635;
                                attribute Iyy : Real = 0.3608381384022047;
                                attribute sigma_Iyy : Real = 0.3723953238821935;
                                attribute Izz : Real = 0.3748945659860809;
                                attribute sigma_Izz : Real = 0.37017423652493897;
                                attribute Ixy : Real = 0.010142787058466472;
                                attribute sigma_Ixy : Real = 0.02351283871158888;
                                attribute Ixz : Real = -0.0007219834211158215;
                                attribute sigma_Ixz : Real = 0.022566176940390956;
                                attribute Iyz : Real = -2.5641610775973736e-05;
                                attribute sigma_Iyz : Real = 0.02209918015384651;
                            }
                        }
                        part <'C.1.2.2.2.4.3'> 'Subassembly 280' {
                            attribute POIconv : String = "-";
                            attribute Ipoint : Boolean = false;
                            attribute mass : Real = 0.8769575745677576;
                            attribute sigma_mass : Real = 0.40884026350990615;
                            attribute Cx : Real = -33.585703860053435;
                            attribute sigma_Cx : Real = 49.807217915121804;
                            attribute Cy : Real = 55.685267804994034;
                            attribute sigma_Cy : Real = 28.42366294904372;
                            attribute Cz : Real = 33.23410580440498;
                            attribute sigma_Cz : Real = 25.565476793643175;
                            attribute Ixx : Real = 1314.7272225873608;
                            attribute sigma_Ixx : Real = 1666.1877705319582;
                            attribute Iyy : Real = 5830.520708259524;
                            attribute sigma_Iyy : Real = 5637.489826553805;
                            attribute Izz : Real = 6327.777534570033;
                            attribute sigma_Izz : Real = 6062.667693409094;
                            attribute Ixy : Real = 2215.4041614298567;
                            attribute sigma_Ixy : Real = 2323.5582981405687;
                            attribute Ixz : Real = -1487.5151234680643;
                            attribute sigma_Ixz : Real = 1833.9729317372207;
                            attribute Iyz : Real = 607.8455387868817;
                            attribute sigma_Iyz : Real = 810.4941998492229;
                            part <'C.1.2.2.2.4.3.1'> 'Part 991' {
                                attribute POIconv : String = "-";
                                attribute Ipoint : Boolean = false;
                                attribute mass : Real = 0.6313824032684788;
                                attribute sigma_mass : Real = 0.28909372274994966;
                                attribute Cx : Real = -82.62024247087538;
                                attribute sigma_Cx : Real = 28.721044428837228;
                                attribute Cy : Real = 75.72377445176244;
                                attribute sigma_Cy : Real = 28.23690002309109;
                                attribute Cz : Real = 19.779780320823193;
                                attribute sigma_Cz : Real = 29.057750463592832;
                                attribute Ixx : Real = 0.8917810433568049;
                                attribute sigma_Ixx : Real = 0.37074144170588635;
                                attribute Iyy : Real = 0.9115619872194086;
                                attribute sigma_Iyy : Real = 0.3723953238821935;
                                attribute Izz : Real = 0.9320077385812765;
                                attribute sigma_Izz : Real = 0.37017423652493897;
                                attribute Ixy : Real = -0.01827074584355858;
                                attribute sigma_Ixy : Real = 0.02351283871158888;
                                attribute Ixz : Real = -0.02323207921547763;
                                attribute sigma_Ixz : Real = 0.022566176940390956;
                                attribute Iyz : Real = -0.016588898753466086;
                                attribute sigma_Iyz : Real = 0.02209918015384651;
                            }
                            part <'C.1.2.2.2.4.3.2'> 'Part 992' {
                                attribute POIconv : String = "+";
                                attribute Ipoint : Boolean = false;
                                attribute mass : Real = 0.24557517129927875;
                                attribute sigma_mass : Real = 0.28909372274994966;
                                attribute Cx : Real = 92.48381964862347;
                                attribute sigma_Cx : Real = 28.721044428837228;
                                attribute Cy : Real = 4.165562381967902;
                                attribute sigma_Cy : Real = 28.23690002309109;
                                attribute Cz : Real = 67.82564986497164;
                                attribute sigma_Cz : Real = 29.057750463592832;
                                attribute Ixx : Real = 0.3425471784754824;
                                attribute sigma_Ixx : Real = 0.37074144170588635;
                                attribute Iyy : Real = 0.3258620340522138;
                                attribute sigma_Iyy : Real = 0.3723953238821935;
                                attribute Izz : Real = 0.351794054832525;
                                attribute sigma_Izz : Real = 0.37017423652493897;
                                attribute Ixy : Real = -0.01275755595874368;
                                attribute sigma_Ixy : Real = 0.02351283871158888;
                                attribute Ixz : Real = 0.013639279830247812;
                                attribute sigma_Ixz : Real = 0.022566176940390956;
                                attribute Iyz : Real = 0.01231523268030764;
                                attribute sigma_Iyz : Real = 0.02209918015384651;
                            }
                        }
                        part <'C.1.2.2.2.4.4'> 'Subassembly 281' {
                            attribute POIconv : String = "-";
                            attribute Ipoint : Boolean = false;
                            attribute mass : Real = 3.075345330746844;
                            attribute sigma_mass : Real = 0.6464332159373649;
                            attribute Cx : Real = -37.832382164467795;
                            attribute sigma_Cx : Real = 15.63171838080459;
                            attribute Cy : Real = 22.932710070719583;
                            attribute sigma_Cy : Real = 20.886795893475774;
                            attribute Cz : Real = -2.1978392102042212;
                            attribute sigma_Cz : Real = 16.206536109585365;
                            attribute Ixx : Real = 14467.03495207232;
                            attribute sigma_Ixx : Real = 7905.347890773187;
                            attribute Iyy : Real = 4290.4992732876135;
                            attribute sigma_Iyy : Real = 3395.467041571997;
                            attribute Izz : Real = 13651.076950109116;
                            attribute sigma_Izz : Real = 7616.966563963361;
                            attribute Ixy : Real = 504.02792961526563;
                            attribute sigma_Ixy : Real = 3149.6333523774974;
                            attribute Ixz : Real = -1769.2306914784479;
                            attribute sigma_Ixz : Real = 1686.315230465649;
                            attribute Iyz : Real = 780.6308281852641;
                            attribute sigma_Iyz : Real = 3416.6872680737383;
                            part <'C.1.2.2.2.4.4.1'> 'Part 993' {
                                attribute POIconv : String = "+";
                                attribute Ipoint : Boolean = false;
                                attribute mass : Real = 0.987849029772915;
                                attribute sigma_mass : Real = 0.28909372274994966;
                                attribute Cx : Real = -49.96312544681132;
                                attribute sigma_Cx : Real = 28.721044428837228;
                                attribute Cy : Real = -51.87025321647525;
                                attribute sigma_Cy : Real = 28.23690002309109;
                                attribute Cz : Real = -14.14846871048212;
                                attribute sigma_Cz : Real = 29.057750463592832;
                                attribute Ixx : Real = 1.4704006816222968;
                                attribute sigma_Ixx : Real = 0.37074144170588635;
                                attribute Iyy : Real = 1.4577969816124652;
                                attribute sigma_Iyy : Real = 0.3723953238821935;
                                attribute Izz : Real = 1.376753891657765;
                                attribute sigma_Izz : Real = 0.37017423652493897;
                                attribute Ixy : Real = 0.031299230820461495;
                                attribute sigma_Ixy : Real = 0.02351283871158888;
                                attribute Ixz : Real = 0.06320668326105389;
                                attribute sigma_Ixz : Real = 0.022566176940390956;
                                attribute Iyz : Real = 0.002905841821107236;
                                attribute sigma_Iyz : Real = 0.02209918015384651;
                            }
                            part <'C.1.2.2.2.4.4.2'> 'Part 994' {
                                attribute POIconv : String = "+";
                                attribute Ipoint : Boolean = false;
                                attribute mass : Real = 0.9620267251112964;
                                attribute sigma_mass : Real = 0.28909372274994966;
                                attribute Cx : Real = -51.747614378109574;
                                attribute sigma_Cx : Real = 28.721044428837228;
                                attribute Cy : Real = 86.72565501183271;
                                attribute sigma_Cy : Real = 28.23690002309109;
                                attribute Cz : Real = -31.803484773263335;
                                attribute sigma_Cz : Real = 29.057750463592832;
                                attribute Ixx : Real = 1.152836859204256;
                                attribute sigma_Ixx : Real = 0.37074144170588635;
                                attribute Iyy : Real = 1.1308468342306088;
                                attribute sigma_Iyy : Real = 0.3723953238821935;
                                attribute Izz : Real = 1.2019860712454171;
                                attribute sigma_Izz : Real = 0.37017423652493897;
                                attribute Ixy : Real = -0.03274092054828336;
                                attribute sigma_Ixy : Real = 0.02351283871158888;
                                attribute Ixz : Real = -0.0693662484351279;
                                attribute sigma_Ixz : Real = 0.022566176940390956;
                                attribute Iyz : Real = 0.06692376995962773;
                                attribute sigma_Iyz : Real = 0.02209918015384651;
                            }
                            part <'C.1.2.2.2.4.4.3'> 'Part 995' {
                                attribute POIconv : String = "+";
                                attribute Ipoint : Boolean = false;
                                attribute mass : Real = 0.5036204764358699;
                                attribute sigma_mass : Real = 0.28909372274994966;
                                attribute Cx : Real = -44.637550646439195;
                                attribute sigma_Cx : Real = 28.721044428837228;
                                attribute Cy : Real = 72.92668838053942;
                                attribute sigma_Cy : Real = 28.23690002309109;
                                attribute Cz : Real = 22.411220660433173;
                                attribute sigma_Cz : Real = 29.057750463592832;
                                attribute Ixx : Real = 0.6675448327208635;
                                attribute sigma_Ixx : Real = 0.37074144170588635;
                                attribute Iyy : Real = 0.6936215132887461;
                                attribute sigma_Iyy : Real = 0.3723953238821935;
                                attribute Izz : Real = 0.6079922988006617;
                                attribute sigma_Izz : Real = 0.37017423652493897;
                                attribute Ixy : Real = -0.009897934627693127;
                                attribute sigma_Ixy : Real = 0.02351283871158888;
                                attribute Ixz : Real = -0.052925781095782734;
                                attribute sigma_Ixz : Real = 0.022566176940390956;
                                attribute Iyz : Real = 0.016357303494848038;
                                attribute sigma_Iyz : Real = 0.02209918015384651;
                            }
                            part <'C.1.2.2.2.4.4.4'> 'Part 996' {
                                attribute POIconv : String = "-";
                                attribute Ipoint : Boolean = false;
                                attribute mass : Real = 0.5350742662933189;
                                attribute sigma_mass : Real = 0.28909372274994966;
                                attribute Cx : Real = 11.9660132098943;
                                attribute sigma_Cx : Real = 28.721044428837228;
                                attribute Cy : Real = 18.348637269809842;
                                attribute sigma_Cy : Real = 28.23690002309109;
                                attribute Cz : Real = 44.33038090355694;
                                attribute sigma_Cz : Real = 29.057750463592832;
                                attribute Ixx : Real = 0.5921547951577714;
                                attribute sigma_Ixx : Real = 0.37074144170588635;
                                attribute Iyy : Real = 0.669506709333052;
                                attribute sigma_Iyy : Real = 0.3723953238821935;
                                attribute Izz : Real = 0.6754079509520082;
                                attribute sigma_Izz : Real = 0.37017423652493897;
                                attribute Ixy : Real = -0.009678963877177461;
                                attribute sigma_Ixy : Real = 0.02351283871158888;
                                attribute Ixz : Real = 0.004621268934198031;
                                attribute sigma_Ixz : Real = 0.022566176940390956;
                                attribute Iyz : Real = 0.0010303968120061496;
                                attribute sigma_Iyz : Real = 0.02209918015384651;
                            }
                            part <'C.1.2.2.2.4.4.5'> 'Part 997' {
                                attribute POIconv : String = "+";
                                attribute Ipoint : Boolean = false;
                                attribute mass : Real = 0.0867748331334442;
                                attribute sigma_mass : Real = 0.28909372274994966;
                                attribute Cx : Real = -13.0377440713346;
                                attribute sigma_Cx : Real = 28.721044428837228;
                                attribute Cy : Real = -94.63196410797536;
                                attribute sigma_Cy : Real = 28.23690002309109;
                                attribute Cz : Real = 32.34167182818055;
                                attribute sigma_Cz : Real = 29.057750463592832;
                                attribute Ixx : Real = 0.12903011300564224;
                                attribute sigma_Ixx : Real = 0.37074144170588635;
                                attribute Iyy : Real = 0.13199233109532665;
                                attribute sigma_Iyy : Real = 0.3723953238821935;
                                attribute Izz : Real = 0.13243203648030988;
                                attribute sigma_Izz : Real = 0.37017423652493897;
                                attribute Ixy : Real = 0.0024587243176823915;
                                attribute sigma_Ixy : Real = 0.02351283871158888;
                                attribute Ixz : Real = 0.0040101692353868065;
                                attribute sigma_Ixz : Real = 0.022566176940390956;
                                attribute Iyz : Real = -0.0036114126380190764;
                                attribute sigma_Iyz : Real = 0.02209918015384651;
                            }
                        }
                    }
                }
                part <'C.1.2.2.3'> 'Subsystem 22' {
                    attribute POIconv : String = "-";
                    attribute Ipoint : Boolean = false;
                    attribute mass : Real = 8.964613624533872;
                    attribute sigma_mass : Real = 1.2928664318747298;
                    attribute Cx : Real = -16.3982611890541;
                    attribute sigma_Cx : Real = 11.198327664884758;
                    attribute Cy : Real = 24.034389442460974;
                    attribute sigma_Cy : Real = 12.787756582101737;
                    attribute Cz : Real = -5.8477340064440515;
                    attribute sigma_Cz : Real = 11.633510783180343;
                    attribute Ixx : Real = 68897.78078762477;
                    attribute sigma_Ixx : Real = 17866.8271241795;
                    attribute Iyy : Real = 55034.87344614034;
                    attribute sigma_Iyy : Real = 15186.677634302796;
                    attribute Izz : Real = 68446.57398882412;
                    attribute sigma_Izz : Real = 17172.31808820513;
                    attribute Ixy : Real = 12190.704253570952;
                    attribute sigma_Ixy : Real = 7812.4895321346985;
                    attribute Ixz : Real = 3423.7004119440107;
                    attribute sigma_Ixz : Real = 6978.667457801035;
                    attribute Iyz : Real = -17818.161158498864;
                    attribute sigma_Iyz : Real = 8635.220798112943;
                    part <'C.1.2.2.3.1'> 'Assembly 81' {
                        attribute POIconv : String = "-";
                        attribute Ipoint : Boolean = false;
                        attribute mass : Real = 2.1475061277218632;
                        attribute sigma_mass : Real = 0.6464332159373648;
                        attribute Cx : Real = 2.1792556623517805;
                        attribute sigma_Cx : Real = 21.01385969410202;
                        attribute Cy : Real = 8.173501515071822;
                        attribute sigma_Cy : Real = 29.73464085789338;
                        attribute Cz : Real = 24.85755367044584;
                        attribute sigma_Cz : Real = 27.161763243964394;
                        attribute Ixx : Real = 18887.409273873778;
                        attribute sigma_Ixx : Real = 11494.848372350374;
                        attribute Iyy : Real = 10602.389808387668;
                        attribute sigma_Iyy : Real = 7553.0658984522415;
                        attribute Izz : Real = 11940.697145406888;
                        attribute sigma_Izz : Real = 8885.267774978956;
                        attribute Ixy : Real = 3371.2938834887045;
                        attribute sigma_Ixy : Real = 3549.6619781470663;
                        attribute Ixz : Real = 2287.7555509072736;
                        attribute sigma_Ixz : Real = 3043.804673818893;
                        attribute Iyz : Real = -8835.49131259046;
                        attribute sigma_Iyz : Real = 5754.322053028651;
                        part <'C.1.2.2.3.1.1'> 'Subassembly 282' {
                            attribute POIconv : String = "-";
                            attribute Ipoint : Boolean = false;
                            attribute mass : Real = 0.7863786534115207;
                            attribute sigma_mass : Real = 0.40884026350990615;
                            attribute Cx : Real = 0.3372799404289653;
                            attribute sigma_Cx : Real = 26.60722651719523;
                            attribute Cy : Real = -28.929144529650483;
                            attribute sigma_Cy : Real = 56.7432452410883;
                            attribute Cz : Real = -33.13906405128876;
                            attribute sigma_Cz : Real = 46.243939667456466;
                            attribute Ixx : Real = 10584.562333060827;
                            attribute sigma_Ixx : Real = 8527.394398201232;
                            attribute Iyy : Real = 4580.576146178148;
                            attribute sigma_Iyy : Real = 4096.729105046824;
                            attribute Izz : Real = 7211.109608607898;
                            attribute sigma_Izz : Real = 6020.0474540130945;
                            attribute Ixy : Real = 1996.2667365104867;
                            attribute sigma_Ixy : Real = 2061.5039604167705;
                            attribute Ixz : Real = 1548.674777810348;
                            attribute sigma_Ixz : Real = 1623.4237025318691;
                            attribute Iyz : Real = -5125.80508505107;
                            attribute sigma_Iyz : Real = 4157.906420915521;
                            part <'C.1.2.2.3.1.1.1'> 'Part 998' {
                                attribute POIconv : String = "+";
                                attribute Ipoint : Boolean = false;
                                attribute mass : Real = 0.2682770018510055;
                                attribute sigma_mass : Real = 0.28909372274994966;
                                attribute Cx : Real = -38.14990087412298;
                                attribute sigma_Cx : Real = 28.721044428837228;
                                attribute Cy : Real = 98.45185899175704;
                                attribute sigma_Cy : Real = 28.23690002309109;
                                attribute Cz : Real = 65.6827942468226;
                                attribute sigma_Cz : Real = 29.057750463592832;
                                attribute Ixx : Real = 0.2734833661725806;
                                attribute sigma_Ixx : Real = 0.37074144170588635;
                                attribute Iyy : Real = 0.2794214069698289;
                                attribute sigma_Iyy : Real = 0.3723953238821935;
                                attribute Izz : Real = 0.2675526860049357;
                                attribute sigma_Izz : Real = 0.37017423652493897;
                                attribute Ixy : Real = 0.00351054849216403;
                                attribute sigma_Ixy : Real = 0.02351283871158888;
                                attribute Ixz : Real = -0.0041970819578815224;
                                attribute sigma_Ixz : Real = 0.022566176940390956;
                                attribute Iyz : Real = -0.005158917155448491;
                                attribute sigma_Iyz : Real = 0.02209918015384651;
                            }
                            part <'C.1.2.2.3.1.1.2'> 'Part 999' {
                                attribute POIconv : String = "+";
                                attribute Ipoint : Boolean = false;
                                attribute mass : Real = 0.5181016515605151;
                                attribute sigma_mass : Real = 0.28909372274994966;
                                attribute Cx : Real = 20.26623683050275;
                                attribute sigma_Cx : Real = 28.721044428837228;
                                attribute Cy : Real = -94.88800340332091;
                                attribute sigma_Cy : Real = 28.23690002309109;
                                attribute Cz : Real = -84.30977887474;
                                attribute sigma_Cz : Real = 29.057750463592832;
                                attribute Ixx : Real = 0.6617302139178972;
                                attribute sigma_Ixx : Real = 0.37074144170588635;
                                attribute Iyy : Real = 0.5890508131589117;
                                attribute sigma_Iyy : Real = 0.3723953238821935;
                                attribute Izz : Real = 0.6030236177772124;
                                attribute sigma_Izz : Real = 0.37017423652493897;
                                attribute Ixy : Real = 0.007426176634679011;
                                attribute sigma_Ixy : Real = 0.02351283871158888;
                                attribute Ixz : Real = 0.036556870971465254;
                                attribute sigma_Ixz : Real = 0.022566176940390956;
                                attribute Iyz : Real = 0.05498798482147681;
                                attribute sigma_Iyz : Real = 0.02209918015384651;
                            }
                        }
                        part <'C.1.2.2.3.1.2'> 'Subassembly 283' {
                            attribute POIconv : String = "-";
                            attribute Ipoint : Boolean = false;
                            attribute mass : Real = 1.3611274743103423;
                            attribute sigma_mass : Real = 0.5007250159521434;
                            attribute Cx : Real = 3.24343988841503;
                            attribute sigma_Cx : Real = 29.36759264800858;
                            attribute Cy : Real = 29.60920785803306;
                            attribute sigma_Cy : Real = 30.65584864527599;
                            attribute Cz : Real = 58.364556509800586;
                            attribute sigma_Cz : Real = 25.8316898909462;
                            attribute Ixx : Real = 2421.656036347307;
                            attribute sigma_Ixx : Real = 4186.091854549142;
                            attribute Iyy : Real = 1844.3708470365507;
                            attribute sigma_Iyy : Real = 3833.596224174484;
                            attribute Izz : Real = 3017.4203580060534;
                            attribute sigma_Izz : Real = 5306.451823628542;
                            attribute Ixy : Real = 1459.8193877307367;
                            attribute sigma_Ixy : Real = 2646.4713531458187;
                            attribute Ixz : Real = 871.6228879306093;
                            attribute sigma_Ixz : Real = 1831.572083593821;
                            attribute Iyz : Real = -1039.9099030395064;
                            attribute sigma_Iyz : Real = 1969.819925957618;
                            part <'C.1.2.2.3.1.2.1'> 'Part 1000' {
                                attribute POIconv : String = "-";
                                attribute Ipoint : Boolean = false;
                                attribute mass : Real = 0.08781051513529382;
                                attribute sigma_mass : Real = 0.28909372274994966;
                                attribute Cx : Real = 93.75454084947705;
                                attribute sigma_Cx : Real = 28.721044428837228;
                                attribute Cy : Real = -64.90565417334437;
                                attribute sigma_Cy : Real = 28.23690002309109;
                                attribute Cz : Real = -7.389143481850624;
                                attribute sigma_Cz : Real = 29.057750463592832;
                                attribute Ixx : Real = 0.11349920599823053;
                                attribute sigma_Ixx : Real = 0.37074144170588635;
                                attribute Iyy : Real = 0.11743811639927669;
                                attribute sigma_Iyy : Real = 0.3723953238821935;
                                attribute Izz : Real = 0.11701770605778841;
                                attribute sigma_Izz : Real = 0.37017423652493897;
                                attribute Ixy : Real = 0.0026483268710255107;
                                attribute sigma_Ixy : Real = 0.02351283871158888;
                                attribute Ixz : Real = -0.0024529174055099986;
                                attribute sigma_Ixz : Real = 0.022566176940390956;
                                attribute Iyz : Real = -0.005056335373681012;
                                attribute sigma_Iyz : Real = 0.02209918015384651;
                            }
                            part <'C.1.2.2.3.1.2.2'> 'Part 1001' {
                                attribute POIconv : String = "-";
                                attribute Ipoint : Boolean = false;
                                attribute mass : Real = 0.36019444992020727;
                                attribute sigma_mass : Real = 0.28909372274994966;
                                attribute Cx : Real = -32.9376395791769;
                                attribute sigma_Cx : Real = 28.721044428837228;
                                attribute Cy : Real = 79.80054975487292;
                                attribute sigma_Cy : Real = 28.23690002309109;
                                attribute Cz : Real = 83.71249507181346;
                                attribute sigma_Cz : Real = 29.057750463592832;
                                attribute Ixx : Real = 0.37424472474082926;
                                attribute sigma_Ixx : Real = 0.37074144170588635;
                                attribute Iyy : Real = 0.3537332332729534;
                                attribute sigma_Iyy : Real = 0.3723953238821935;
                                attribute Izz : Real = 0.36519784775002373;
                                attribute sigma_Izz : Real = 0.37017423652493897;
                                attribute Ixy : Real = 0.028299732583257065;
                                attribute sigma_Ixy : Real = 0.02351283871158888;
                                attribute Ixz : Real = -0.0017474358014942146;
                                attribute sigma_Ixz : Real = 0.022566176940390956;
                                attribute Iyz : Real = 0.0016867036581789156;
                                attribute sigma_Iyz : Real = 0.02209918015384651;
                            }
                            part <'C.1.2.2.3.1.2.3'> 'Part 1002' {
                                attribute POIconv : String = "-";
                                attribute Ipoint : Boolean = false;
                                attribute mass : Real = 0.9131225092548412;
                                attribute sigma_mass : Real = 0.28909372274994966;
                                attribute Cx : Real = 8.811583882197738;
                                attribute sigma_Cx : Real = 28.721044428837228;
                                attribute Cy : Real = 18.899534223601222;
                                attribute sigma_Cy : Real = 28.23690002309109;
                                attribute Cz : Real = 54.688904574140906;
                                attribute sigma_Cz : Real = 29.057750463592832;
                                attribute Ixx : Real = 1.206763664569927;
                                attribute sigma_Ixx : Real = 0.37074144170588635;
                                attribute Iyy : Real = 1.281416933150703;
                                attribute sigma_Iyy : Real = 0.3723953238821935;
                                attribute Izz : Real = 1.2006552373138228;
                                attribute sigma_Izz : Real = 0.37017423652493897;
                                attribute Ixy : Real = 0.043673574884466715;
                                attribute sigma_Ixy : Real = 0.02351283871158888;
                                attribute Ixz : Real = -0.0003940934767997017;
                                attribute sigma_Ixz : Real = 0.022566176940390956;
                                attribute Iyz : Real = 0.011064303191600802;
                                attribute sigma_Iyz : Real = 0.02209918015384651;
                            }
                        }
                    }
                    part <'C.1.2.2.3.2'> 'Assembly 82' {
                        attribute POIconv : String = "-";
                        attribute Ipoint : Boolean = false;
                        attribute mass : Real = 6.8171074968120084;
                        attribute sigma_mass : Real = 1.1196551737036593;
                        attribute Cx : Real = -22.250498563176073;
                        attribute sigma_Cx : Real = 13.00026664290757;
                        attribute Cy : Real = 29.030841974727274;
                        attribute sigma_Cy : Real = 13.860272593332754;
                        attribute Cz : Real = -15.520427809559246;
                        attribute sigma_Cz : Real = 12.24022636431991;
                        attribute Ixx : Real = 46637.4264982407;
                        attribute sigma_Ixx : Real = 12885.906461381466;
                        attribute Iyy : Real = 40795.33474162899;
                        attribute sigma_Iyy : Real = 12391.461210093907;
                        attribute Izz : Real = 54820.814448381;
                        attribute sigma_Izz : Real = 14384.207203125503;
                        attribute Ixy : Real = 7987.299862902753;
                        attribute sigma_Ixy : Real = 6780.570738160281;
                        attribute Ixz : Real = 2746.83780844784;
                        attribute sigma_Ixz : Real = 5935.44223527049;
                        attribute Iyz : Real = -10357.998567517157;
                        attribute sigma_Iyz : Real = 5970.2093194385;
                        part <'C.1.2.2.3.2.1'> 'Subassembly 284' {
                            attribute POIconv : String = "-";
                            attribute Ipoint : Boolean = false;
                            attribute mass : Real = 1.371050164234126;
                            attribute sigma_mass : Real = 0.5007250159521434;
                            attribute Cx : Real = -13.855696240397197;
                            attribute sigma_Cx : Real = 21.904243156411567;
                            attribute Cy : Real = 84.57425039782783;
                            attribute sigma_Cy : Real = 19.401888438669513;
                            attribute Cz : Real = -50.01968732854361;
                            attribute sigma_Cz : Real = 20.386535553725064;
                            attribute Ixx : Real = 951.5012918670866;
                            attribute sigma_Ixx : Real = 1332.3703228267648;
                            attribute Iyy : Real = 1683.2140456407735;
                            attribute sigma_Iyy : Real = 1755.0591691781442;
                            attribute Izz : Real = 1519.2553017889225;
                            attribute sigma_Izz : Real = 1645.4323814600184;
                            attribute Ixy : Real = 106.74244758931832;
                            attribute sigma_Ixy : Real = 710.4577122419246;
                            attribute Ixz : Real = 71.56498341413075;
                            attribute sigma_Ixz : Real = 770.070670353466;
                            attribute Iyz : Real = -466.7077727731203;
                            attribute sigma_Iyz : Real = 661.1018720142499;
                            part <'C.1.2.2.3.2.1.1'> 'Part 1003' {
                                attribute POIconv : String = "-";
                                attribute Ipoint : Boolean = false;
                                attribute mass : Real = 0.3176887161303312;
                                attribute sigma_mass : Real = 0.28909372274994966;
                                attribute Cx : Real = -65.99662681110203;
                                attribute sigma_Cx : Real = 28.721044428837228;
                                attribute Cy : Real = 88.88293546624482;
                                attribute sigma_Cy : Real = 28.23690002309109;
                                attribute Cz : Real = -47.47326597571373;
                                attribute sigma_Cz : Real = 29.057750463592832;
                                attribute Ixx : Real = 0.37047545833452283;
                                attribute sigma_Ixx : Real = 0.37074144170588635;
                                attribute Iyy : Real = 0.4026334890313699;
                                attribute sigma_Iyy : Real = 0.3723953238821935;
                                attribute Izz : Real = 0.42084579870170047;
                                attribute sigma_Izz : Real = 0.37017423652493897;
                                attribute Ixy : Real = -0.009684507846894837;
                                attribute sigma_Ixy : Real = 0.02351283871158888;
                                attribute Ixz : Real = 0.012490113221948936;
                                attribute sigma_Ixz : Real = 0.022566176940390956;
                                attribute Iyz : Real = 0.02777157782135361;
                                attribute sigma_Iyz : Real = 0.02209918015384651;
                            }
                            part <'C.1.2.2.3.2.1.2'> 'Part 1004' {
                                attribute POIconv : String = "+";
                                attribute Ipoint : Boolean = false;
                                attribute mass : Real = 0.7609557169706095;
                                attribute sigma_mass : Real = 0.28909372274994966;
                                attribute Cx : Real = 1.4426170382648706;
                                attribute sigma_Cx : Real = 28.721044428837228;
                                attribute Cy : Real = 95.131212240085;
                                attribute sigma_Cy : Real = 28.23690002309109;
                                attribute Cz : Real = -36.56750405207276;
                                attribute sigma_Cz : Real = 29.057750463592832;
                                attribute Ixx : Real = 0.7739821382407648;
                                attribute sigma_Ixx : Real = 0.37074144170588635;
                                attribute Iyy : Real = 0.7590513650103857;
                                attribute sigma_Iyy : Real = 0.3723953238821935;
                                attribute Izz : Real = 0.7131505687926795;
                                attribute sigma_Izz : Real = 0.37017423652493897;
                                attribute Ixy : Real = 0.024479287743045974;
                                attribute sigma_Ixy : Real = 0.02351283871158888;
                                attribute Ixz : Real = -0.02176595292603893;
                                attribute sigma_Ixz : Real = 0.022566176940390956;
                                attribute Iyz : Real = 0.024230138917593402;
                                attribute sigma_Iyz : Real = 0.02209918015384651;
                            }
                            part <'C.1.2.2.3.2.1.3'> 'Part 1005' {
                                attribute POIconv : String = "+";
                                attribute Ipoint : Boolean = false;
                                attribute mass : Real = 0.29240573113318535;
                                attribute sigma_mass : Real = 0.28909372274994966;
                                attribute Cx : Real = 2.9813415370881557;
                                attribute sigma_Cx : Real = 28.721044428837228;
                                attribute Cy : Real = 52.419610135257244;
                                attribute sigma_Cy : Real = 28.23690002309109;
                                attribute Cz : Real = -87.7942037768662;
                                attribute sigma_Cz : Real = 29.057750463592832;
                                attribute Ixx : Real = 0.325210686802862;
                                attribute sigma_Ixx : Real = 0.37074144170588635;
                                attribute Iyy : Real = 0.37241270770813645;
                                attribute sigma_Iyy : Real = 0.3723953238821935;
                                attribute Izz : Real = 0.4123770118399169;
                                attribute sigma_Izz : Real = 0.37017423652493897;
                                attribute Ixy : Real = 0.00301387373979163;
                                attribute sigma_Ixy : Real = 0.02351283871158888;
                                attribute Ixz : Real = 0.02151111045569789;
                                attribute sigma_Ixz : Real = 0.022566176940390956;
                                attribute Iyz : Real = -0.004386168386778359;
                                attribute sigma_Iyz : Real = 0.02209918015384651;
                            }
                        }
                        part <'C.1.2.2.3.2.2'> 'Subassembly 285' {
                            attribute POIconv : String = "-";
                            attribute Ipoint : Boolean = false;
                            attribute mass : Real = 1.7582966634533368;
                            attribute sigma_mass : Real = 0.5781874454998993;
                            attribute Cx : Real = -22.342269428418362;
                            attribute sigma_Cx : Real = 28.07695655272803;
                            attribute Cy : Real = 6.8455407657870335;
                            attribute sigma_Cy : Real = 33.083166642948235;
                            attribute Cz : Real = -28.47421434364611;
                            attribute sigma_Cz : Real = 22.27072584475422;
                            attribute Ixx : Real = 18416.379852590275;
                            attribute sigma_Ixx : Real = 8268.269932507923;
                            attribute Iyy : Real = 11559.015273225286;
                            attribute sigma_Iyy : Real = 6717.054184721371;
                            attribute Izz : Real = 22458.53765756423;
                            attribute sigma_Izz : Real = 9950.434908704809;
                            attribute Ixy : Real = 5358.550591659136;
                            attribute sigma_Ixy : Real = 4738.211439427871;
                            attribute Ixz : Real = 2269.0517816961737;
                            attribute sigma_Ixz : Real = 3149.6908852252445;
                            attribute Iyz : Real = -7154.29841714274;
                            attribute sigma_Iyz : Real = 3803.913431101301;
                            part <'C.1.2.2.3.2.2.1'> 'Part 1006' {
                                attribute POIconv : String = "-";
                                attribute Ipoint : Boolean = false;
                                attribute mass : Real = 0.20961525726504623;
                                attribute sigma_mass : Real = 0.28909372274994966;
                                attribute Cx : Real = 82.92951546609402;
                                attribute sigma_Cx : Real = 28.721044428837228;
                                attribute Cy : Real = 87.53000176511705;
                                attribute sigma_Cy : Real = 28.23690002309109;
                                attribute Cz : Real = 31.493828119710088;
                                attribute sigma_Cz : Real = 29.057750463592832;
                                attribute Ixx : Real = 0.26866215960934225;
                                attribute sigma_Ixx : Real = 0.37074144170588635;
                                attribute Iyy : Real = 0.28258058165029315;
                                attribute sigma_Iyy : Real = 0.3723953238821935;
                                attribute Izz : Real = 0.29801919076629313;
                                attribute sigma_Izz : Real = 0.37017423652493897;
                                attribute Ixy : Real = -0.0057529824619327995;
                                attribute sigma_Ixy : Real = 0.02351283871158888;
                                attribute Ixz : Real = -0.005598120417871369;
                                attribute sigma_Ixz : Real = 0.022566176940390956;
                                attribute Iyz : Real = -0.007110050984442776;
                                attribute sigma_Iyz : Real = 0.02209918015384651;
                            }
                            part <'C.1.2.2.3.2.2.2'> 'Part 1007' {
                                attribute POIconv : String = "+";
                                attribute Ipoint : Boolean = false;
                                attribute mass : Real = 0.5236412878341508;
                                attribute sigma_mass : Real = 0.28909372274994966;
                                attribute Cx : Real = 40.28734490275383;
                                attribute sigma_Cx : Real = 28.721044428837228;
                                attribute Cy : Real = -96.53971642255783;
                                attribute sigma_Cy : Real = 28.23690002309109;
                                attribute Cz : Real = -88.59279761090875;
                                attribute sigma_Cz : Real = 29.057750463592832;
                                attribute Ixx : Real = 0.6576317562732735;
                                attribute sigma_Ixx : Real = 0.37074144170588635;
                                attribute Iyy : Real = 0.7321373599512839;
                                attribute sigma_Iyy : Real = 0.3723953238821935;
                                attribute Izz : Real = 0.5767785828398014;
                                attribute sigma_Izz : Real = 0.37017423652493897;
                                attribute Ixy : Real = 0.041556770873983365;
                                attribute sigma_Ixy : Real = 0.02351283871158888;
                                attribute Ixz : Real = -0.0018276718436292454;
                                attribute sigma_Ixz : Real = 0.022566176940390956;
                                attribute Iyz : Real = -0.04015842932084851;
                                attribute sigma_Iyz : Real = 0.02209918015384651;
                            }
                            part <'C.1.2.2.3.2.2.3'> 'Part 1008' {
                                attribute POIconv : String = "-";
                                attribute Ipoint : Boolean = false;
                                attribute mass : Real = 0.3170905596860684;
                                attribute sigma_mass : Real = 0.28909372274994966;
                                attribute Cx : Real = -43.32383400760591;
                                attribute sigma_Cx : Real = 28.721044428837228;
                                attribute Cy : Real = -74.38644138164818;
                                attribute sigma_Cy : Real = 28.23690002309109;
                                attribute Cz : Real = -50.76702176593244;
                                attribute sigma_Cz : Real = 29.057750463592832;
                                attribute Ixx : Real = 0.3545937751506153;
                                attribute sigma_Ixx : Real = 0.37074144170588635;
                                attribute Iyy : Real = 0.3919489871103486;
                                attribute sigma_Iyy : Real = 0.3723953238821935;
                                attribute Izz : Real = 0.4047535362964869;
                                attribute sigma_Izz : Real = 0.37017423652493897;
                                attribute Ixy : Real = 0.02109445813379975;
                                attribute sigma_Ixy : Real = 0.02351283871158888;
                                attribute Ixz : Real = -0.030998759528186412;
                                attribute sigma_Ixz : Real = 0.022566176940390956;
                                attribute Iyz : Real = 0.007082155674338354;
                                attribute sigma_Iyz : Real = 0.02209918015384651;
                            }
                            part <'C.1.2.2.3.2.2.4'> 'Part 1009' {
                                attribute POIconv : String = "+";
                                attribute Ipoint : Boolean = false;
                                attribute mass : Real = 0.7079495586680714;
                                attribute sigma_mass : Real = 0.28909372274994966;
                                attribute Cx : Real = -90.43888384476304;
                                attribute sigma_Cx : Real = 28.721044428837228;
                                attribute Cy : Real = 95.80949177034199;
                                attribute sigma_Cy : Real = 28.23690002309109;
                                attribute Cz : Real = 8.222177624702454;
                                attribute sigma_Cz : Real = 29.057750463592832;
                                attribute Ixx : Real = 0.7643217213278611;
                                attribute sigma_Ixx : Real = 0.37074144170588635;
                                attribute Iyy : Real = 0.8899502003034849;
                                attribute sigma_Iyy : Real = 0.3723953238821935;
                                attribute Izz : Real = 0.8161325789900538;
                                attribute sigma_Izz : Real = 0.37017423652493897;
                                attribute Ixy : Real = -0.020719804189385148;
                                attribute sigma_Ixy : Real = 0.02351283871158888;
                                attribute Ixz : Real = 0.02030532740862295;
                                attribute sigma_Ixz : Real = 0.022566176940390956;
                                attribute Iyz : Real = 0.06275005787363168;
                                attribute sigma_Iyz : Real = 0.02209918015384651;
                            }
                        }
                        part <'C.1.2.2.3.2.3'> 'Subassembly 286' {
                            attribute POIconv : String = "-";
                            attribute Ipoint : Boolean = false;
                            attribute mass : Real = 1.394820179206552;
                            attribute sigma_mass : Real = 0.5781874454998993;
                            attribute Cx : Real = -42.714602422463365;
                            attribute sigma_Cx : Real = 27.562312868997953;
                            attribute Cy : Real = 44.82072136583057;
                            attribute sigma_Cy : Real = 25.616419084912266;
                            attribute Cz : Real = 21.090122212576667;
                            attribute sigma_Cz : Real = 29.699185690698233;
                            attribute Ixx : Real = 7850.963870653959;
                            attribute sigma_Ixx : Real = 5028.848332847179;
                            attribute Iyy : Real = 9319.28797991731;
                            attribute sigma_Iyy : Real = 5880.3929282367335;
                            attribute Izz : Real = 6880.561745012542;
                            attribute sigma_Izz : Real = 4402.633008268086;
                            attribute Ixy : Real = 3188.4300009965227;
                            attribute sigma_Ixy : Real = 2122.0933289444497;
                            attribute Ixz : Real = 4002.3522424551893;
                            attribute sigma_Ixz : Real = 2882.783352274638;
                            attribute Iyz : Real = -2467.3141025128457;
                            attribute sigma_Iyz : Real = 2257.5835066683244;
                            part <'C.1.2.2.3.2.3.1'> 'Part 1010' {
                                attribute POIconv : String = "-";
                                attribute Ipoint : Boolean = false;
                                attribute mass : Real = 0.00490983270178549;
                                attribute sigma_mass : Real = 0.28909372274994966;
                                attribute Cx : Real = -8.017859747633338;
                                attribute sigma_Cx : Real = 28.721044428837228;
                                attribute Cy : Real = 11.19074528105557;
                                attribute sigma_Cy : Real = 28.23690002309109;
                                attribute Cz : Real = 51.94290429353714;
                                attribute sigma_Cz : Real = 29.057750463592832;
                                attribute Ixx : Real = 0.006025597062580873;
                                attribute sigma_Ixx : Real = 0.37074144170588635;
                                attribute Iyy : Real = 0.0063606194350507165;
                                attribute sigma_Iyy : Real = 0.3723953238821935;
                                attribute Izz : Real = 0.006147788323704245;
                                attribute sigma_Izz : Real = 0.37017423652493897;
                                attribute Ixy : Real = -0.00010238701415248559;
                                attribute sigma_Ixy : Real = 0.02351283871158888;
                                attribute Ixz : Real = 0.0003089362430248738;
                                attribute sigma_Ixz : Real = 0.022566176940390956;
                                attribute Iyz : Real = -0.0005072236912534451;
                                attribute sigma_Iyz : Real = 0.02209918015384651;
                            }
                            part <'C.1.2.2.3.2.3.2'> 'Part 1011' {
                                attribute POIconv : String = "+";
                                attribute Ipoint : Boolean = false;
                                attribute mass : Real = 0.23015673840255477;
                                attribute sigma_mass : Real = 0.28909372274994966;
                                attribute Cx : Real = -7.633649092167616;
                                attribute sigma_Cx : Real = 28.721044428837228;
                                attribute Cy : Real = -11.86889042146504;
                                attribute sigma_Cy : Real = 28.23690002309109;
                                attribute Cz : Real = 52.535229129716754;
                                attribute sigma_Cz : Real = 29.057750463592832;
                                attribute Ixx : Real = 0.2501456030298357;
                                attribute sigma_Ixx : Real = 0.37074144170588635;
                                attribute Iyy : Real = 0.25709420167183045;
                                attribute sigma_Iyy : Real = 0.3723953238821935;
                                attribute Izz : Real = 0.24923941688212842;
                                attribute sigma_Izz : Real = 0.37017423652493897;
                                attribute Ixy : Real = 0.010666510238599467;
                                attribute sigma_Ixy : Real = 0.02351283871158888;
                                attribute Ixz : Real = 0.009097009448384053;
                                attribute sigma_Ixz : Real = 0.022566176940390956;
                                attribute Iyz : Real = -0.01014688042309085;
                                attribute sigma_Iyz : Real = 0.02209918015384651;
                            }
                            part <'C.1.2.2.3.2.3.3'> 'Part 1012' {
                                attribute POIconv : String = "-";
                                attribute Ipoint : Boolean = false;
                                attribute mass : Real = 0.405842741121538;
                                attribute sigma_mass : Real = 0.28909372274994966;
                                attribute Cx : Real = 28.45844253897667;
                                attribute sigma_Cx : Real = 28.721044428837228;
                                attribute Cy : Real = 2.3775546345859766;
                                attribute sigma_Cy : Real = 28.23690002309109;
                                attribute Cz : Real = -73.55268327519298;
                                attribute sigma_Cz : Real = 29.057750463592832;
                                attribute Ixx : Real = 0.4223758790032171;
                                attribute sigma_Ixx : Real = 0.37074144170588635;
                                attribute Iyy : Real = 0.42987435048775297;
                                attribute sigma_Iyy : Real = 0.3723953238821935;
                                attribute Izz : Real = 0.447437250621488;
                                attribute sigma_Izz : Real = 0.37017423652493897;
                                attribute Ixy : Real = -0.012859265413095882;
                                attribute sigma_Ixy : Real = 0.02351283871158888;
                                attribute Ixz : Real = 0.01219929930809871;
                                attribute sigma_Ixz : Real = 0.022566176940390956;
                                attribute Iyz : Real = -0.021227213646902998;
                                attribute sigma_Iyz : Real = 0.02209918015384651;
                            }
                            part <'C.1.2.2.3.2.3.4'> 'Part 1013' {
                                attribute POIconv : String = "+";
                                attribute Ipoint : Boolean = false;
                                attribute mass : Real = 0.7539108669806738;
                                attribute sigma_mass : Real = 0.28909372274994966;
                                attribute Cx : Real = -91.96384167298675;
                                attribute sigma_Cx : Real = 28.721044428837228;
                                attribute Cy : Real = 85.1940150372684;
                                attribute sigma_Cy : Real = 28.23690002309109;
                                attribute Cz : Real = 62.23730780184269;
                                attribute sigma_Cz : Real = 29.057750463592832;
                                attribute Ixx : Real = 1.173633832226925;
                                attribute sigma_Ixx : Real = 0.37074144170588635;
                                attribute Iyy : Real = 1.0665241032263855;
                                attribute sigma_Iyy : Real = 0.3723953238821935;
                                attribute Izz : Real = 1.0795789652396484;
                                attribute sigma_Izz : Real = 0.37017423652493897;
                                attribute Ixy : Real = 0.009276259752856897;
                                attribute sigma_Ixy : Real = 0.02351283871158888;
                                attribute Ixz : Real = 0.043136850591862196;
                                attribute sigma_Ixz : Real = 0.022566176940390956;
                                attribute Iyz : Real = -0.0018029021425642155;
                                attribute sigma_Iyz : Real = 0.02209918015384651;
                            }
                        }
                        part <'C.1.2.2.3.2.4'> 'Subassembly 287' {
                            attribute POIconv : String = "-";
                            attribute Ipoint : Boolean = false;
                            attribute mass : Real = 2.292940489917994;
                            attribute sigma_mass : Real = 0.5781874454998993;
                            attribute Cx : Real = -14.751215267024612;
                            attribute sigma_Cx : Real = 23.326293844138814;
                            attribute Cy : Real = 3.2262034290086454;
                            attribute sigma_Cy : Real = 20.98723817787065;
                            attribute Cz : Real = -7.229030273382956;
                            attribute sigma_Cz : Real = 20.016387560833035;
                            attribute Ixx : Real = 8494.783248527068;
                            attribute sigma_Ixx : Real = 5244.135711065885;
                            attribute Iyy : Real = 13470.083939856215;
                            attribute sigma_Iyy : Real = 7170.836774067162;
                            attribute Izz : Real = 16182.971334034792;
                            attribute sigma_Izz : Real = 7529.522023026675;
                            attribute Ixy : Real = -917.9792911187803;
                            attribute sigma_Ixy : Real = 3383.1003276438664;
                            attribute Ixz : Real = -4893.545151088506;
                            attribute sigma_Ixz : Real = 3412.2239006063373;
                            attribute Iyz : Real = -2075.8649892414765;
                            attribute sigma_Iyz : Real = 2507.760624949797;
                            part <'C.1.2.2.3.2.4.1'> 'Part 1014' {
                                attribute POIconv : String = "-";
                                attribute Ipoint : Boolean = false;
                                attribute mass : Real = 0.6338044687181246;
                                attribute sigma_mass : Real = 0.28909372274994966;
                                attribute Cx : Real = -37.18947251327336;
                                attribute sigma_Cx : Real = 28.721044428837228;
                                attribute Cy : Real = -75.01696199178696;
                                attribute sigma_Cy : Real = 28.23690002309109;
                                attribute Cz : Real = -38.12561030499637;
                                attribute sigma_Cz : Real = 29.057750463592832;
                                attribute Ixx : Real = 0.8006787546998893;
                                attribute sigma_Ixx : Real = 0.37074144170588635;
                                attribute Iyy : Real = 0.6991374430848829;
                                attribute sigma_Iyy : Real = 0.3723953238821935;
                                attribute Izz : Real = 0.8404919150082512;
                                attribute sigma_Izz : Real = 0.37017423652493897;
                                attribute Ixy : Real = -0.024535888686501674;
                                attribute sigma_Ixy : Real = 0.02351283871158888;
                                attribute Ixz : Real = -0.03505527345171007;
                                attribute sigma_Ixz : Real = 0.022566176940390956;
                                attribute Iyz : Real = 0.06594037674886585;
                                attribute sigma_Iyz : Real = 0.02209918015384651;
                            }
                            part <'C.1.2.2.3.2.4.2'> 'Part 1015' {
                                attribute POIconv : String = "-";
                                attribute Ipoint : Boolean = false;
                                attribute mass : Real = 0.030522787004010753;
                                attribute sigma_mass : Real = 0.28909372274994966;
                                attribute Cx : Real = 37.39647245965898;
                                attribute sigma_Cx : Real = 28.721044428837228;
                                attribute Cy : Real = -49.916549073532224;
                                attribute sigma_Cy : Real = 28.23690002309109;
                                attribute Cz : Real = -64.78401878848672;
                                attribute sigma_Cz : Real = 29.057750463592832;
                                attribute Ixx : Real = 0.039653479324651145;
                                attribute sigma_Ixx : Real = 0.37074144170588635;
                                attribute Iyy : Real = 0.03988449348235366;
                                attribute sigma_Iyy : Real = 0.3723953238821935;
                                attribute Izz : Real = 0.04167912098722391;
                                attribute sigma_Izz : Real = 0.37017423652493897;
                                attribute Ixy : Real = -0.0008866876591976072;
                                attribute sigma_Ixy : Real = 0.02351283871158888;
                                attribute Ixz : Real = 0.0008401707250535846;
                                attribute sigma_Ixz : Real = 0.022566176940390956;
                                attribute Iyz : Real = -0.0011150046633223952;
                                attribute sigma_Iyz : Real = 0.02209918015384651;
                            }
                            part <'C.1.2.2.3.2.4.3'> 'Part 1016' {
                                attribute POIconv : String = "+";
                                attribute Ipoint : Boolean = false;
                                attribute mass : Real = 0.6805104270665906;
                                attribute sigma_mass : Real = 0.28909372274994966;
                                attribute Cx : Real = 85.85417056456208;
                                attribute sigma_Cx : Real = 28.721044428837228;
                                attribute Cy : Real = 29.997750418260694;
                                attribute sigma_Cy : Real = 28.23690002309109;
                                attribute Cz : Real = 46.22967317700386;
                                attribute sigma_Cz : Real = 29.057750463592832;
                                attribute Ixx : Real = 0.8726368522280162;
                                attribute sigma_Ixx : Real = 0.37074144170588635;
                                attribute Iyy : Real = 0.8710918434618221;
                                attribute sigma_Iyy : Real = 0.3723953238821935;
                                attribute Izz : Real = 0.8806345565258799;
                                attribute sigma_Izz : Real = 0.37017423652493897;
                                attribute Ixy : Real = -0.005378031021421724;
                                attribute sigma_Ixy : Real = 0.02351283871158888;
                                attribute Ixz : Real = 0.0009754780818239108;
                                attribute sigma_Ixz : Real = 0.022566176940390956;
                                attribute Iyz : Real = 0.0012612562220211878;
                                attribute sigma_Iyz : Real = 0.02209918015384651;
                            }
                            part <'C.1.2.2.3.2.4.4'> 'Part 1017' {
                                attribute POIconv : String = "-";
                                attribute Ipoint : Boolean = false;
                                attribute mass : Real = 0.9481028071292676;
                                attribute sigma_mass : Real = 0.28909372274994966;
                                attribute Cx : Real = -73.64065079018474;
                                attribute sigma_Cx : Real = 28.721044428837228;
                                attribute Cy : Real = 38.0268766079098;
                                attribute sigma_Cy : Real = 28.23690002309109;
                                attribute Cz : Real = -23.092368990182877;
                                attribute sigma_Cz : Real = 29.057750463592832;
                                attribute Ixx : Real = 1.246507812897894;
                                attribute sigma_Ixx : Real = 0.37074144170588635;
                                attribute Iyy : Real = 1.1209699773329378;
                                attribute sigma_Iyy : Real = 0.3723953238821935;
                                attribute Izz : Real = 1.0497519594501963;
                                attribute sigma_Izz : Real = 0.37017423652493897;
                                attribute Ixy : Real = 0.012960458026935231;
                                attribute sigma_Ixy : Real = 0.02351283871158888;
                                attribute Ixz : Real = -0.07955311331156094;
                                attribute sigma_Ixz : Real = 0.022566176940390956;
                                attribute Iyz : Real = 0.14042367031222563;
                                attribute sigma_Iyz : Real = 0.02209918015384651;
                            }
                        }
                    }
                }
            }
            part <'C.1.2.3'> 'Element 7' {
                attribute POIconv : String = "-";
                attribute Ipoint : Boolean = false;
                attribute mass : Real = 121.68784572148232;
                attribute sigma_mass : Real = 4.570973105735384;
                attribute Cx : Real = 1.5103164699858047;
                attribute sigma_Cx : Real = 3.17150176415287;
                attribute Cy : Real = -3.551420833318365;
                attribute sigma_Cy : Real = 3.1065003775136226;
                attribute Cz : Real = -0.8871604534277792;
                attribute sigma_Cz : Real = 3.1786494954446045;
                attribute Ixx : Real = 795661.1347347103;
                attribute sigma_Ixx : Real = 58817.29990161638;
                attribute Iyy : Real = 798008.6186482063;
                attribute sigma_Iyy : Real = 58958.01746443926;
                attribute Izz : Real = 790794.4674035937;
                attribute sigma_Izz : Real = 58437.45426042405;
                attribute Ixy : Real = -37223.74110740408;
                attribute sigma_Ixy : Real = 27216.395091700262;
                attribute Ixz : Real = -27940.516102099857;
                attribute sigma_Ixz : Real = 27652.34506923407;
                attribute Iyz : Real = -28878.45156199348;
                attribute sigma_Iyz : Real = 27628.126458815732;
                part <'C.1.2.3.1'> 'Subsystem 23' {
                    attribute POIconv : String = "-";
                    attribute Ipoint : Boolean = false;
                    attribute mass : Real = 27.228420881233184;
                    attribute sigma_mass : Real = 2.182609743038185;
                    attribute Cx : Real = -1.0001543390379433;
                    attribute sigma_Cx : Real = 6.917353316943819;
                    attribute Cy : Real = -11.848902329230333;
                    attribute sigma_Cy : Real = 6.337255949992637;
                    attribute Cz : Real = -4.5332597989617565;
                    attribute sigma_Cz : Real = 6.770864896682537;
                    attribute Ixx : Real = 173391.34000124704;
                    attribute sigma_Ixx : Real = 27091.817082976413;
                    attribute Iyy : Real = 182813.1241527726;
                    attribute sigma_Iyy : Real = 29524.602620241065;
                    attribute Izz : Real = 168806.24963433854;
                    attribute sigma_Izz : Real = 28470.81854652819;
                    attribute Ixy : Real = -7993.590311050721;
                    attribute sigma_Ixy : Real = 13215.483161346127;
                    attribute Ixz : Real = -23616.99784916739;
                    attribute sigma_Ixz : Real = 13606.675987660927;
                    attribute Iyz : Real = -20703.90897188583;
                    attribute sigma_Iyz : Real = 12699.10877721972;
                    part <'C.1.2.3.1.1'> 'Assembly 83' {
                        attribute POIconv : String = "-";
                        attribute Ipoint : Boolean = false;
                        attribute mass : Real = 3.0309456110133324;
                        attribute sigma_mass : Real = 0.7081321085790055;
                        attribute Cx : Real = 47.404811999496246;
                        attribute sigma_Cx : Real = 18.431368061388316;
                        attribute Cy : Real = -33.79612429039057;
                        attribute sigma_Cy : Real = 14.757595131000222;
                        attribute Cz : Real = 8.644511491861227;
                        attribute sigma_Cz : Real = 20.325169062414528;
                        attribute Ixx : Real = 15225.43843507667;
                        attribute sigma_Ixx : Real = 7304.596174075059;
                        attribute Iyy : Real = 21451.407460521237;
                        attribute sigma_Iyy : Real = 8657.581503029247;
                        attribute Izz : Real = 12515.325674638287;
                        attribute sigma_Izz : Real = 5943.930297128182;
                        attribute Ixy : Real = -2249.151157105823;
                        attribute sigma_Ixy : Real = 2745.8740240955244;
                        attribute Ixz : Real = -7572.017766221594;
                        attribute sigma_Ixz : Real = 4114.047886761228;
                        attribute Iyz : Real = -4551.210561016525;
                        attribute sigma_Iyz : Real = 3229.952733134226;
                        part <'C.1.2.3.1.1.1'> 'Subassembly 288' {
                            attribute POIconv : String = "-";
                            attribute Ipoint : Boolean = false;
                            attribute mass : Real = 1.8108087949331384;
                            attribute sigma_mass : Real = 0.5781874454998993;
                            attribute Cx : Real = 14.209555143464167;
                            attribute sigma_Cx : Real = 22.069697895214997;
                            attribute Cy : Real = -33.405608692261964;
                            attribute sigma_Cy : Real = 19.244347560637166;
                            attribute Cz : Real = -13.924524890640845;
                            attribute sigma_Cz : Real = 27.396838734282234;
                            attribute Ixx : Real = 11672.428622528514;
                            attribute sigma_Ixx : Real = 6400.747648539791;
                            attribute Iyy : Real = 13229.411862280635;
                            attribute sigma_Iyy : Real = 6803.777027989324;
                            attribute Izz : Real = 7269.219270560516;
                            attribute sigma_Izz : Real = 4375.893041106513;
                            attribute Ixy : Real = -2310.2487429978805;
                            attribute sigma_Ixy : Real = 2044.5299427192017;
                            attribute Ixz : Real = -4206.9361835835725;
                            attribute sigma_Ixz : Real = 3027.4715639756446;
                            attribute Iyz : Real = -4062.4293128175777;
                            attribute sigma_Iyz : Real = 2885.2495014647525;
                            part <'C.1.2.3.1.1.1.1'> 'Part 1018' {
                                attribute POIconv : String = "+";
                                attribute Ipoint : Boolean = false;
                                attribute mass : Real = 0.2714737224543933;
                                attribute sigma_mass : Real = 0.28909372274994966;
                                attribute Cx : Real = 79.75672213360667;
                                attribute sigma_Cx : Real = 28.721044428837228;
                                attribute Cy : Real = -47.84345794469118;
                                attribute sigma_Cy : Real = 28.23690002309109;
                                attribute Cz : Real = 37.33013062737882;
                                attribute sigma_Cz : Real = 29.057750463592832;
                                attribute Ixx : Real = 0.338813851766033;
                                attribute sigma_Ixx : Real = 0.37074144170588635;
                                attribute Iyy : Real = 0.32808673555829204;
                                attribute sigma_Iyy : Real = 0.3723953238821935;
                                attribute Izz : Real = 0.2635997353238293;
                                attribute sigma_Izz : Real = 0.37017423652493897;
                                attribute Ixy : Real = -0.00348121279006372;
                                attribute sigma_Ixy : Real = 0.02351283871158888;
                                attribute Ixz : Real = -0.0059289411663554226;
                                attribute sigma_Ixz : Real = 0.022566176940390956;
                                attribute Iyz : Real = 0.0010905838823576167;
                                attribute sigma_Iyz : Real = 0.02209918015384651;
                            }
                            part <'C.1.2.3.1.1.1.2'> 'Part 1019' {
                                attribute POIconv : String = "-";
                                attribute Ipoint : Boolean = false;
                                attribute mass : Real = 0.6140720751190092;
                                attribute sigma_mass : Real = 0.28909372274994966;
                                attribute Cx : Real = 41.76371074281633;
                                attribute sigma_Cx : Real = 28.721044428837228;
                                attribute Cy : Real = -13.316352106630802;
                                attribute sigma_Cy : Real = 28.23690002309109;
                                attribute Cz : Real = -30.140276066958904;
                                attribute sigma_Cz : Real = 29.057750463592832;
                                attribute Ixx : Real = 0.9758292338339816;
                                attribute sigma_Ixx : Real = 0.37074144170588635;
                                attribute Iyy : Real = 0.9945128023725424;
                                attribute sigma_Iyy : Real = 0.3723953238821935;
                                attribute Izz : Real = 0.9677428445822156;
                                attribute sigma_Izz : Real = 0.37017423652493897;
                                attribute Ixy : Real = 0.01581042094337401;
                                attribute sigma_Ixy : Real = 0.02351283871158888;
                                attribute Ixz : Real = 0.002628492911459966;
                                attribute sigma_Ixz : Real = 0.022566176940390956;
                                attribute Iyz : Real = 0.012784974508136617;
                                attribute sigma_Iyz : Real = 0.02209918015384651;
                            }
                            part <'C.1.2.3.1.1.1.3'> 'Part 1020' {
                                attribute POIconv : String = "-";
                                attribute Ipoint : Boolean = false;
                                attribute mass : Real = 0.3992901132279076;
                                attribute sigma_mass : Real = 0.28909372274994966;
                                attribute Cx : Real = 22.544915741309524;
                                attribute sigma_Cx : Real = 28.721044428837228;
                                attribute Cy : Real = 16.845566825941205;
                                attribute sigma_Cy : Real = 28.23690002309109;
                                attribute Cz : Real = 88.00809560343623;
                                attribute sigma_Cz : Real = 29.057750463592832;
                                attribute Ixx : Real = 0.49613217247505165;
                                attribute sigma_Ixx : Real = 0.37074144170588635;
                                attribute Iyy : Real = 0.5586903756185922;
                                attribute sigma_Iyy : Real = 0.3723953238821935;
                                attribute Izz : Real = 0.455115033082299;
                                attribute sigma_Izz : Real = 0.37017423652493897;
                                attribute Ixy : Real = 0.003961459110997396;
                                attribute sigma_Ixy : Real = 0.02351283871158888;
                                attribute Ixz : Real = -0.004567387177313131;
                                attribute sigma_Ixz : Real = 0.022566176940390956;
                                attribute Iyz : Real = 0.027750189879247933;
                                attribute sigma_Iyz : Real = 0.02209918015384651;
                            }
                            part <'C.1.2.3.1.1.1.4'> 'Part 1021' {
                                attribute POIconv : String = "-";
                                attribute Ipoint : Boolean = false;
                                attribute mass : Real = 0.5259728841318283;
                                attribute sigma_mass : Real = 0.28909372274994966;
                                attribute Cx : Real = -58.118884498253465;
                                attribute sigma_Cx : Real = 28.721044428837228;
                                attribute Cy : Real = -87.555838143453;
                                attribute sigma_Cy : Real = 28.23690002309109;
                                attribute Cz : Real = -98.82878721691668;
                                attribute sigma_Cz : Real = 29.057750463592832;
                                attribute Ixx : Real = 0.6712742996562501;
                                attribute sigma_Ixx : Real = 0.37074144170588635;
                                attribute Iyy : Real = 0.6522892461739314;
                                attribute sigma_Iyy : Real = 0.3723953238821935;
                                attribute Izz : Real = 0.6461367813144506;
                                attribute sigma_Izz : Real = 0.37017423652493897;
                                attribute Ixy : Real = 0.0046570648083672245;
                                attribute sigma_Ixy : Real = 0.02351283871158888;
                                attribute Ixz : Real = -0.021496487245712896;
                                attribute sigma_Ixz : Real = 0.022566176940390956;
                                attribute Iyz : Real = 0.05979432298398718;
                                attribute sigma_Iyz : Real = 0.02209918015384651;
                            }
                        }
                        part <'C.1.2.3.1.1.2'> 'Subassembly 289' {
                            attribute POIconv : String = "-";
                            attribute Ipoint : Boolean = false;
                            attribute mass : Real = 1.220136816080194;
                            attribute sigma_mass : Real = 0.40884026350990615;
                            attribute Cx : Real = 96.6699946189974;
                            attribute sigma_Cx : Real = 22.440039418562073;
                            attribute Cy : Real = -34.37568968857407;
                            attribute sigma_Cy : Real = 22.981103551657693;
                            attribute Cz : Real = 42.139287680890384;
                            attribute sigma_Cz : Real = 25.605959286779502;
                            attribute Ixx : Real = 1261.0961789399564;
                            attribute sigma_Ixx : Real = 1641.1925723387974;
                            attribute Iyy : Real = 974.0492471889995;
                            attribute sigma_Iyy : Real = 1405.9443876197852;
                            attribute Izz : Real = 288.7017028669125;
                            attribute sigma_Izz : Real = 686.7607858953487;
                            attribute Ixy : Real = 2.78576200941095;
                            attribute sigma_Ixy : Real = 335.59016754703737;
                            attribute Ixz : Real = 4.928939461749861;
                            attribute sigma_Ixz : Real = 617.533205295129;
                            attribute Iyz : Real = -528.4267216605684;
                            attribute sigma_Iyz : Real = 778.7770230688279;
                            part <'C.1.2.3.1.1.2.1'> 'Part 1022' {
                                attribute POIconv : String = "+";
                                attribute Ipoint : Boolean = false;
                                attribute mass : Real = 0.3233482847209089;
                                attribute sigma_mass : Real = 0.28909372274994966;
                                attribute Cx : Real = 96.91439098678529;
                                attribute sigma_Cx : Real = 28.721044428837228;
                                attribute Cy : Real = -59.92609802633524;
                                attribute sigma_Cy : Real = 28.23690002309109;
                                attribute Cz : Real = -4.8784935381263494;
                                attribute sigma_Cz : Real = 29.057750463592832;
                                attribute Ixx : Real = 0.3794431984809574;
                                attribute sigma_Ixx : Real = 0.37074144170588635;
                                attribute Iyy : Real = 0.39538334417695803;
                                attribute sigma_Iyy : Real = 0.3723953238821935;
                                attribute Izz : Real = 0.3882085156366992;
                                attribute sigma_Izz : Real = 0.37017423652493897;
                                attribute Ixy : Real = -0.00833593018547131;
                                attribute sigma_Ixy : Real = 0.02351283871158888;
                                attribute Ixz : Real = 0.01595120031159023;
                                attribute sigma_Ixz : Real = 0.022566176940390956;
                                attribute Iyz : Real = -0.016044849710204007;
                                attribute sigma_Iyz : Real = 0.02209918015384651;
                            }
                            part <'C.1.2.3.1.1.2.2'> 'Part 1023' {
                                attribute POIconv : String = "-";
                                attribute Ipoint : Boolean = false;
                                attribute mass : Real = 0.8967885313592852;
                                attribute sigma_mass : Real = 0.28909372274994966;
                                attribute Cx : Real = 96.58187446184456;
                                attribute sigma_Cx : Real = 28.721044428837228;
                                attribute Cy : Real = -25.16317144036293;
                                attribute sigma_Cy : Real = 28.23690002309109;
                                attribute Cz : Real = 59.0921348426491;
                                attribute sigma_Cz : Real = 29.057750463592832;
                                attribute Ixx : Real = 0.9634658175781806;
                                attribute sigma_Ixx : Real = 0.37074144170588635;
                                attribute Iyy : Real = 1.074516750064507;
                                attribute sigma_Iyy : Real = 0.3723953238821935;
                                attribute Izz : Real = 1.0870171880647128;
                                attribute sigma_Izz : Real = 0.37017423652493897;
                                attribute Ixy : Real = 0.030280719388407304;
                                attribute sigma_Ixy : Real = 0.02351283871158888;
                                attribute Ixz : Real = -0.11039760567095933;
                                attribute sigma_Ixz : Real = 0.022566176940390956;
                                attribute Iyz : Real = 0.06213998552283999;
                                attribute sigma_Iyz : Real = 0.02209918015384651;
                            }
                        }
                    }
                    part <'C.1.2.3.1.2'> 'Assembly 84' {
                        attribute POIconv : String = "-";
                        attribute Ipoint : Boolean = false;
                        attribute mass : Real = 5.089248216057197;
                        attribute sigma_mass : Real = 1.081689663197327;
                        attribute Cx : Real = -20.370668668255668;
                        attribute sigma_Cx : Real = 15.523581824006042;
                        attribute Cy : Real = -7.227335082045519;
                        attribute sigma_Cy : Real = 14.265998479901054;
                        attribute Cz : Real = -44.54660967239568;
                        attribute sigma_Cz : Real = 12.94090087986855;
                        attribute Ixx : Real = 18352.096923253117;
                        attribute sigma_Ixx : Real = 7768.425903598372;
                        attribute Iyy : Real = 15723.3782134768;
                        attribute sigma_Iyy : Real = 8865.188515733409;
                        attribute Izz : Real = 24328.53026135546;
                        attribute sigma_Izz : Real = 10032.600768293156;
                        attribute Ixy : Real = 1632.7040683149419;
                        attribute sigma_Ixy : Real = 3874.9365373767773;
                        attribute Ixz : Real = -3284.4234599283404;
                        attribute sigma_Ixz : Real = 3265.8360939556555;
                        attribute Iyz : Real = -957.1585537832796;
                        attribute sigma_Iyz : Real = 3620.8018199452476;
                        part <'C.1.2.3.1.2.1'> 'Subassembly 290' {
                            attribute POIconv : String = "-";
                            attribute Ipoint : Boolean = false;
                            attribute mass : Real = 1.1110594704328105;
                            attribute sigma_mass : Real = 0.5781874454998993;
                            attribute Cx : Real = 43.43805389889171;
                            attribute sigma_Cx : Real = 34.97526626651218;
                            attribute Cy : Real = -24.29065540627002;
                            attribute sigma_Cy : Real = 21.209015776025815;
                            attribute Cz : Real = -13.332961598010973;
                            attribute sigma_Cz : Real = 15.74220075515541;
                            attribute Ixx : Real = 1051.2112202693104;
                            attribute sigma_Ixx : Real = 1132.3446287344261;
                            attribute Iyy : Real = 3732.3888156779158;
                            attribute sigma_Iyy : Real = 4022.0951441143425;
                            attribute Izz : Real = 4553.828243521498;
                            attribute sigma_Izz : Real = 4411.790862263671;
                            attribute Ixy : Real = 1007.1615621922922;
                            attribute sigma_Ixy : Real = 1474.1253334521077;
                            attribute Ixz : Real = -270.21347250632414;
                            attribute sigma_Ixz : Real = 941.1789495596643;
                            attribute Iyz : Real = 280.6498430003078;
                            attribute sigma_Iyz : Real = 521.1229184684073;
                            part <'C.1.2.3.1.2.1.1'> 'Part 1024' {
                                attribute POIconv : String = "-";
                                attribute Ipoint : Boolean = false;
                                attribute mass : Real = 0.36056349496007895;
                                attribute sigma_mass : Real = 0.28909372274994966;
                                attribute Cx : Real = 74.903594981879;
                                attribute sigma_Cx : Real = 28.721044428837228;
                                attribute Cy : Real = -43.962585320696235;
                                attribute sigma_Cy : Real = 28.23690002309109;
                                attribute Cz : Real = -14.050036296248436;
                                attribute sigma_Cz : Real = 29.057750463592832;
                                attribute Ixx : Real = 0.37645157575398197;
                                attribute sigma_Ixx : Real = 0.37074144170588635;
                                attribute Iyy : Real = 0.4339364569021059;
                                attribute sigma_Iyy : Real = 0.3723953238821935;
                                attribute Izz : Real = 0.4222303506634136;
                                attribute sigma_Izz : Real = 0.37017423652493897;
                                attribute Ixy : Real = -0.012832195169406983;
                                attribute sigma_Ixy : Real = 0.02351283871158888;
                                attribute Ixz : Real = -0.028196857768589087;
                                attribute sigma_Ixz : Real = 0.022566176940390956;
                                attribute Iyz : Real = -0.006867982665523601;
                                attribute sigma_Iyz : Real = 0.02209918015384651;
                            }
                            part <'C.1.2.3.1.2.1.2'> 'Part 1025' {
                                attribute POIconv : String = "-";
                                attribute Ipoint : Boolean = false;
                                attribute mass : Real = 0.28386467407946475;
                                attribute sigma_mass : Real = 0.28909372274994966;
                                attribute Cx : Real = 68.0945314001292;
                                attribute sigma_Cx : Real = 28.721044428837228;
                                attribute Cy : Real = -54.774394957348704;
                                attribute sigma_Cy : Real = 28.23690002309109;
                                attribute Cz : Real = 2.8109159786254168;
                                attribute sigma_Cz : Real = 29.057750463592832;
                                attribute Ixx : Real = 0.3455054282681242;
                                attribute sigma_Ixx : Real = 0.37074144170588635;
                                attribute Iyy : Real = 0.319335019885562;
                                attribute sigma_Iyy : Real = 0.3723953238821935;
                                attribute Izz : Real = 0.3377785699564937;
                                attribute sigma_Izz : Real = 0.37017423652493897;
                                attribute Ixy : Real = -0.019487729589842406;
                                attribute sigma_Ixy : Real = 0.02351283871158888;
                                attribute Ixz : Real = -0.030441392086136818;
                                attribute sigma_Ixz : Real = 0.022566176940390956;
                                attribute Iyz : Real = 0.012651754000112921;
                                attribute sigma_Iyz : Real = 0.02209918015384651;
                            }
                            part <'C.1.2.3.1.2.1.3'> 'Part 1026' {
                                attribute POIconv : String = "+";
                                attribute Ipoint : Boolean = false;
                                attribute mass : Real = 0.23156337600271218;
                                attribute sigma_mass : Real = 0.28909372274994966;
                                attribute Cx : Real = -67.61877932585776;
                                attribute sigma_Cx : Real = 28.721044428837228;
                                attribute Cy : Real = 7.986530475318432;
                                attribute sigma_Cy : Real = 28.23690002309109;
                                attribute Cz : Real = -22.457342129200697;
                                attribute sigma_Cz : Real = 29.057750463592832;
                                attribute Ixx : Real = 0.29036869938459164;
                                attribute sigma_Ixx : Real = 0.37074144170588635;
                                attribute Iyy : Real = 0.3037983540131558;
                                attribute sigma_Iyy : Real = 0.3723953238821935;
                                attribute Izz : Real = 0.3033854697711728;
                                attribute sigma_Izz : Real = 0.37017423652493897;
                                attribute Ixy : Real = -0.015408500102457081;
                                attribute sigma_Ixy : Real = 0.02351283871158888;
                                attribute Ixz : Real = 0.008693896622724785;
                                attribute sigma_Ixz : Real = 0.022566176940390956;
                                attribute Iyz : Real = -0.02130395195673237;
                                attribute sigma_Iyz : Real = 0.02209918015384651;
                            }
                            part <'C.1.2.3.1.2.1.4'> 'Part 1027' {
                                attribute POIconv : String = "-";
                                attribute Ipoint : Boolean = false;
                                attribute mass : Real = 0.2350679253905546;
                                attribute sigma_mass : Real = 0.28909372274994966;
                                attribute Cx : Real = 74.80033696629107;
                                attribute sigma_Cx : Real = 28.721044428837228;
                                attribute Cy : Real = 10.899268742650747;
                                attribute sigma_Cy : Real = 28.23690002309109;
                                attribute Cz : Real = -22.739830799400806;
                                attribute sigma_Cz : Real = 29.057750463592832;
                                attribute Ixx : Real = 0.2970339860488817;
                                attribute sigma_Ixx : Real = 0.37074144170588635;
                                attribute Iyy : Real = 0.298674204183194;
                                attribute sigma_Iyy : Real = 0.3723953238821935;
                                attribute Izz : Real = 0.32429851049119174;
                                attribute sigma_Izz : Real = 0.37017423652493897;
                                attribute Ixy : Real = 0.0021527023303478036;
                                attribute sigma_Ixy : Real = 0.02351283871158888;
                                attribute Ixz : Real = 0.010038598246872399;
                                attribute sigma_Ixz : Real = 0.022566176940390956;
                                attribute Iyz : Real = 0.0004260807488943631;
                                attribute sigma_Iyz : Real = 0.02209918015384651;
                            }
                        }
                        part <'C.1.2.3.1.2.2'> 'Subassembly 291' {
                            attribute POIconv : String = "-";
                            attribute Ipoint : Boolean = false;
                            attribute mass : Real = 2.137433945090277;
                            attribute sigma_mass : Real = 0.6464332159373649;
                            attribute Cx : Real = -39.10439068984298;
                            attribute sigma_Cx : Real = 17.40357952355306;
                            attribute Cy : Real = 16.75278502002286;
                            attribute sigma_Cy : Real = 22.97047800266084;
                            attribute Cz : Real = -29.51950989335581;
                            attribute sigma_Cz : Real = 17.047592232197207;
                            attribute Ixx : Real = 7463.678748209302;
                            attribute sigma_Ixx : Real = 4703.849015183828;
                            attribute Iyy : Real = 1307.3245654039515;
                            attribute sigma_Iyy : Real = 1475.2680265144302;
                            attribute Izz : Real = 8169.865665346993;
                            attribute sigma_Izz : Real = 4797.722824012194;
                            attribute Ixy : Real = 56.67935849811613;
                            attribute sigma_Ixy : Real = 2094.630371456308;
                            attribute Ixz : Real = 73.8419290060479;
                            attribute sigma_Ixz : Real = 643.9254691787272;
                            attribute Iyz : Real = 1067.5665084810657;
                            attribute sigma_Iyz : Real = 2097.852506831811;
                            part <'C.1.2.3.1.2.2.1'> 'Part 1028' {
                                attribute POIconv : String = "-";
                                attribute Ipoint : Boolean = false;
                                attribute mass : Real = 0.9854304553838447;
                                attribute sigma_mass : Real = 0.28909372274994966;
                                attribute Cx : Real = -46.41855643130839;
                                attribute sigma_Cx : Real = 28.721044428837228;
                                attribute Cy : Real = 69.41389311105013;
                                attribute sigma_Cy : Real = 28.23690002309109;
                                attribute Cz : Real = -34.333817986771464;
                                attribute sigma_Cz : Real = 29.057750463592832;
                                attribute Ixx : Real = 1.1745379913630323;
                                attribute sigma_Ixx : Real = 0.37074144170588635;
                                attribute Iyy : Real = 1.2318771445603012;
                                attribute sigma_Iyy : Real = 0.3723953238821935;
                                attribute Izz : Real = 1.0344128409711042;
                                attribute sigma_Izz : Real = 0.37017423652493897;
                                attribute Ixy : Real = -0.0248720546664876;
                                attribute sigma_Ixy : Real = 0.02351283871158888;
                                attribute Ixz : Real = 0.11754377707019359;
                                attribute sigma_Ixz : Real = 0.022566176940390956;
                                attribute Iyz : Real = 0.07310842433924039;
                                attribute sigma_Iyz : Real = 0.02209918015384651;
                            }
                            part <'C.1.2.3.1.2.2.2'> 'Part 1029' {
                                attribute POIconv : String = "-";
                                attribute Ipoint : Boolean = false;
                                attribute mass : Real = 0.4805381577296648;
                                attribute sigma_mass : Real = 0.28909372274994966;
                                attribute Cx : Real = -51.79176856763661;
                                attribute sigma_Cx : Real = 28.721044428837228;
                                attribute Cy : Real = -68.34773179143667;
                                attribute sigma_Cy : Real = 28.23690002309109;
                                attribute Cz : Real = -19.806827697902918;
                                attribute sigma_Cz : Real = 29.057750463592832;
                                attribute Ixx : Real = 0.4252615031969518;
                                attribute sigma_Ixx : Real = 0.37074144170588635;
                                attribute Iyy : Real = 0.4468632274660892;
                                attribute sigma_Iyy : Real = 0.3723953238821935;
                                attribute Izz : Real = 0.4520839455535829;
                                attribute sigma_Izz : Real = 0.37017423652493897;
                                attribute Ixy : Real = -0.015775196673174598;
                                attribute sigma_Ixy : Real = 0.02351283871158888;
                                attribute Ixz : Real = 0.0024492739737420996;
                                attribute sigma_Ixz : Real = 0.022566176940390956;
                                attribute Iyz : Real = -0.007405177985282297;
                                attribute sigma_Iyz : Real = 0.02209918015384651;
                            }
                            part <'C.1.2.3.1.2.2.3'> 'Part 1030' {
                                attribute POIconv : String = "+";
                                attribute Ipoint : Boolean = false;
                                attribute mass : Real = 0.19013544256146997;
                                attribute sigma_mass : Real = 0.28909372274994966;
                                attribute Cx : Real = -61.670681508257985;
                                attribute sigma_Cx : Real = 28.721044428837228;
                                attribute Cy : Real = -26.477308245375752;
                                attribute sigma_Cy : Real = 28.23690002309109;
                                attribute Cz : Real = -12.132368283346295;
                                attribute sigma_Cz : Real = 29.057750463592832;
                                attribute Ixx : Real = 0.25479736142580073;
                                attribute sigma_Ixx : Real = 0.37074144170588635;
                                attribute Iyy : Real = 0.2763441582313683;
                                attribute sigma_Iyy : Real = 0.3723953238821935;
                                attribute Izz : Real = 0.22144415543644014;
                                attribute sigma_Izz : Real = 0.37017423652493897;
                                attribute Ixy : Real = -0.006838077576182519;
                                attribute sigma_Ixy : Real = 0.02351283871158888;
                                attribute Ixz : Real = 0.005283864889242323;
                                attribute sigma_Ixz : Real = 0.022566176940390956;
                                attribute Iyz : Real = -0.00043688253103186885;
                                attribute sigma_Iyz : Real = 0.02209918015384651;
                            }
                            part <'C.1.2.3.1.2.2.4'> 'Part 1031' {
                                attribute POIconv : String = "-";
                                attribute Ipoint : Boolean = false;
                                attribute mass : Real = 0.11593558303709142;
                                attribute sigma_mass : Real = 0.28909372274994966;
                                attribute Cx : Real = -32.33528942801058;
                                attribute sigma_Cx : Real = 28.721044428837228;
                                attribute Cy : Real = 72.48143367469311;
                                attribute sigma_Cy : Real = 28.23690002309109;
                                attribute Cz : Real = -67.7624145988375;
                                attribute sigma_Cz : Real = 29.057750463592832;
                                attribute Ixx : Real = 0.16064184465428846;
                                attribute sigma_Ixx : Real = 0.37074144170588635;
                                attribute Iyy : Real = 0.1581539359278079;
                                attribute sigma_Iyy : Real = 0.3723953238821935;
                                attribute Izz : Real = 0.13849539528318897;
                                attribute sigma_Izz : Real = 0.37017423652493897;
                                attribute Ixy : Real = 0.00633287031607507;
                                attribute sigma_Ixy : Real = 0.02351283871158888;
                                attribute Ixz : Real = -0.007801961933453122;
                                attribute sigma_Ixz : Real = 0.022566176940390956;
                                attribute Iyz : Real = -0.00675677936258264;
                                attribute sigma_Iyz : Real = 0.02209918015384651;
                            }
                            part <'C.1.2.3.1.2.2.5'> 'Part 1032' {
                                attribute POIconv : String = "-";
                                attribute Ipoint : Boolean = false;
                                attribute mass : Real = 0.36539430637820625;
                                attribute sigma_mass : Real = 0.28909372274994966;
                                attribute Cx : Real = 6.901369569823146;
                                attribute sigma_Cx : Real = 28.721044428837228;
                                attribute Cy : Real = -8.53817998431623;
                                attribute sigma_Cy : Real = 28.23690002309109;
                                attribute Cz : Real = -26.222652290016413;
                                attribute sigma_Cz : Real = 29.057750463592832;
                                attribute Ixx : Real = 0.47870142572940394;
                                attribute sigma_Ixx : Real = 0.37074144170588635;
                                attribute Iyy : Real = 0.45534335620023697;
                                attribute sigma_Iyy : Real = 0.3723953238821935;
                                attribute Izz : Real = 0.4424887476004629;
                                attribute sigma_Izz : Real = 0.37017423652493897;
                                attribute Ixy : Real = 0.057474077807164646;
                                attribute sigma_Ixy : Real = 0.02351283871158888;
                                attribute Ixz : Real = 0.025208377588377406;
                                attribute sigma_Ixz : Real = 0.022566176940390956;
                                attribute Iyz : Real = 0.01665357844630759;
                                attribute sigma_Iyz : Real = 0.02209918015384651;
                            }
                        }
                        part <'C.1.2.3.1.2.3'> 'Subassembly 292' {
                            attribute POIconv : String = "-";
                            attribute Ipoint : Boolean = false;
                            attribute mass : Real = 1.8407548005341088;
                            attribute sigma_mass : Real = 0.6464332159373649;
                            attribute Cx : Real = -37.13183214786232;
                            attribute sigma_Cx : Real = 22.546882752239927;
                            attribute Cy : Real = -24.7731587087844;
                            attribute sigma_Cy : Real = 23.297119516413456;
                            attribute Cz : Real = -80.83588211889318;
                            attribute sigma_Cz : Real = 22.61822431868798;
                            attribute Ixx : Real = 3728.6349905163543;
                            attribute sigma_Ixx : Real = 3880.040154329244;
                            attribute Iyy : Real = 903.385509782588;
                            attribute sigma_Iyy : Real = 3244.435089279269;
                            attribute Izz : Real = 3694.5228155310438;
                            attribute sigma_Izz : Real = 3791.7426454677043;
                            attribute Ixy : Real = -1059.715358921331;
                            attribute sigma_Ixy : Real = 1596.4381611798606;
                            attribute Ixz : Real = -357.2280616177601;
                            attribute sigma_Ixz : Real = 1265.1985700248367;
                            attribute Iyz : Real = -954.851810752022;
                            attribute sigma_Iyz : Real = 1796.0166326167048;
                            part <'C.1.2.3.1.2.3.1'> 'Part 1033' {
                                attribute POIconv : String = "-";
                                attribute Ipoint : Boolean = false;
                                attribute mass : Real = 0.8863196952578146;
                                attribute sigma_mass : Real = 0.28909372274994966;
                                attribute Cx : Real = -52.10150717757642;
                                attribute sigma_Cx : Real = 28.721044428837228;
                                attribute Cy : Real = -67.03568380326033;
                                attribute sigma_Cy : Real = 28.23690002309109;
                                attribute Cz : Real = -95.41013021953404;
                                attribute sigma_Cz : Real = 29.057750463592832;
                                attribute Ixx : Real = 1.0591793710191624;
                                attribute sigma_Ixx : Real = 0.37074144170588635;
                                attribute Iyy : Real = 1.2510701729432208;
                                attribute sigma_Iyy : Real = 0.3723953238821935;
                                attribute Izz : Real = 1.0887818618774248;
                                attribute sigma_Izz : Real = 0.37017423652493897;
                                attribute Ixy : Real = -0.040112172222578915;
                                attribute sigma_Ixy : Real = 0.02351283871158888;
                                attribute Ixz : Real = -0.005120049018534828;
                                attribute sigma_Ixz : Real = 0.022566176940390956;
                                attribute Iyz : Real = 0.024889461881570832;
                                attribute sigma_Iyz : Real = 0.02209918015384651;
                            }
                            part <'C.1.2.3.1.2.3.2'> 'Part 1034' {
                                attribute POIconv : String = "+";
                                attribute Ipoint : Boolean = false;
                                attribute mass : Real = 0.006527662138221786;
                                attribute sigma_mass : Real = 0.28909372274994966;
                                attribute Cx : Real = 43.002137867733836;
                                attribute sigma_Cx : Real = 28.721044428837228;
                                attribute Cy : Real = 1.2415521778166294;
                                attribute sigma_Cy : Real = 28.23690002309109;
                                attribute Cz : Real = -43.24038987979293;
                                attribute sigma_Cz : Real = 29.057750463592832;
                                attribute Ixx : Real = 0.007583466824313199;
                                attribute sigma_Ixx : Real = 0.37074144170588635;
                                attribute Iyy : Real = 0.007143444902016918;
                                attribute sigma_Iyy : Real = 0.3723953238821935;
                                attribute Izz : Real = 0.006801558438289208;
                                attribute sigma_Izz : Real = 0.37017423652493897;
                                attribute Ixy : Real = 0.0001073007562773667;
                                attribute sigma_Ixy : Real = 0.02351283871158888;
                                attribute Ixz : Real = -0.0004781643862808727;
                                attribute sigma_Ixz : Real = 0.022566176940390956;
                                attribute Iyz : Real = -0.0007264905940677425;
                                attribute sigma_Iyz : Real = 0.02209918015384651;
                            }
                            part <'C.1.2.3.1.2.3.3'> 'Part 1035' {
                                attribute POIconv : String = "-";
                                attribute Ipoint : Boolean = false;
                                attribute mass : Real = 0.01258344086725265;
                                attribute sigma_mass : Real = 0.28909372274994966;
                                attribute Cx : Real = -64.23425571992993;
                                attribute sigma_Cx : Real = 28.721044428837228;
                                attribute Cy : Real = 23.354554967954755;
                                attribute sigma_Cy : Real = 28.23690002309109;
                                attribute Cz : Real = -5.638757953420281;
                                attribute sigma_Cz : Real = 29.057750463592832;
                                attribute Ixx : Real = 0.017135310471390098;
                                attribute sigma_Ixx : Real = 0.37074144170588635;
                                attribute Iyy : Real = 0.01609576890067113;
                                attribute sigma_Iyy : Real = 0.3723953238821935;
                                attribute Izz : Real = 0.017034289421131867;
                                attribute sigma_Izz : Real = 0.37017423652493897;
                                attribute Ixy : Real = 0.0007043150609314924;
                                attribute sigma_Ixy : Real = 0.02351283871158888;
                                attribute Ixz : Real = 0.00013538241598545948;
                                attribute sigma_Ixz : Real = 0.022566176940390956;
                                attribute Iyz : Real = 0.0006950651548896436;
                                attribute sigma_Iyz : Real = 0.02209918015384651;
                            }
                            part <'C.1.2.3.1.2.3.4'> 'Part 1036' {
                                attribute POIconv : String = "+";
                                attribute Ipoint : Boolean = false;
                                attribute mass : Real = 0.268131818715483;
                                attribute sigma_mass : Real = 0.28909372274994966;
                                attribute Cx : Real = -24.453301914036274;
                                attribute sigma_Cx : Real = 28.721044428837228;
                                attribute Cy : Real = 37.71373191848397;
                                attribute sigma_Cy : Real = 28.23690002309109;
                                attribute Cz : Real = -80.053954385221;
                                attribute sigma_Cz : Real = 29.057750463592832;
                                attribute Ixx : Real = 0.40041169517935266;
                                attribute sigma_Ixx : Real = 0.37074144170588635;
                                attribute Iyy : Real = 0.327437737724792;
                                attribute sigma_Iyy : Real = 0.3723953238821935;
                                attribute Izz : Real = 0.3363708239324448;
                                attribute sigma_Izz : Real = 0.37017423652493897;
                                attribute Ixy : Real = -0.029975816930480827;
                                attribute sigma_Ixy : Real = 0.02351283871158888;
                                attribute Ixz : Real = 0.012019934535980445;
                                attribute sigma_Ixz : Real = 0.022566176940390956;
                                attribute Iyz : Real = 0.0012284113063380474;
                                attribute sigma_Iyz : Real = 0.02209918015384651;
                            }
                            part <'C.1.2.3.1.2.3.5'> 'Part 1037' {
                                attribute POIconv : String = "+";
                                attribute Ipoint : Boolean = false;
                                attribute mass : Real = 0.6671921835553367;
                                attribute sigma_mass : Real = 0.28909372274994966;
                                attribute Cx : Real = -22.613744344562292;
                                attribute sigma_Cx : Real = 28.721044428837228;
                                attribute Cy : Real = 5.095232650637627;
                                attribute sigma_Cy : Real = 28.23690002309109;
                                attribute Cz : Real = -63.575286930426955;
                                attribute sigma_Cz : Real = 29.057750463592832;
                                attribute Ixx : Real = 0.7633558794777816;
                                attribute sigma_Ixx : Real = 0.37074144170588635;
                                attribute Iyy : Real = 0.6969343406144651;
                                attribute sigma_Iyy : Real = 0.3723953238821935;
                                attribute Izz : Real = 0.7637621574057223;
                                attribute sigma_Izz : Real = 0.37017423652493897;
                                attribute Ixy : Real = 0.03459677537013358;
                                attribute sigma_Ixy : Real = 0.02351283871158888;
                                attribute Ixz : Real = -0.029188026897170583;
                                attribute sigma_Ixz : Real = 0.022566176940390956;
                                attribute Iyz : Real = -0.04084380930445912;
                                attribute sigma_Iyz : Real = 0.02209918015384651;
                            }
                        }
                    }
                    part <'C.1.2.3.1.3'> 'Assembly 85' {
                        attribute POIconv : String = "-";
                        attribute Ipoint : Boolean = false;
                        attribute mass : Real = 3.135163911749609;
                        attribute sigma_mass : Real = 0.7648700959862226;
                        attribute Cx : Real = -20.83304455097569;
                        attribute sigma_Cx : Real = 18.16527440231117;
                        attribute Cy : Real = -47.409585483785825;
                        attribute sigma_Cy : Real = 15.260266008881365;
                        attribute Cz : Real = -4.135041982444642;
                        attribute sigma_Cz : Real = 18.358663759174565;
                        attribute Ixx : Real = 14740.57081685723;
                        attribute sigma_Ixx : Real = 6604.845853965839;
                        attribute Iyy : Real = 15133.218533021638;
                        attribute sigma_Iyy : Real = 7534.313639669852;
                        attribute Izz : Real = 10301.14989542552;
                        attribute sigma_Izz : Real = 6251.666436327098;
                        attribute Ixy : Real = -2814.7624226920593;
                        attribute sigma_Ixy : Real = 2618.5867638609207;
                        attribute Ixz : Real = 1550.4243387972117;
                        attribute sigma_Ixz : Real = 3911.9193445607393;
                        attribute Iyz : Real = 4599.318496161658;
                        attribute sigma_Iyz : Real = 3131.9613029204893;
                        part <'C.1.2.3.1.3.1'> 'Subassembly 293' {
                            attribute POIconv : String = "-";
                            attribute Ipoint : Boolean = false;
                            attribute mass : Real = 2.172597040888155;
                            attribute sigma_mass : Real = 0.6464332159373649;
                            attribute Cx : Real = -22.816302334568217;
                            attribute sigma_Cx : Real = 17.65489063142221;
                            attribute Cy : Real = -34.29623435260856;
                            attribute sigma_Cy : Real = 17.53342789254737;
                            attribute Cz : Real = -37.37221692247987;
                            attribute sigma_Cz : Real = 16.407927292241457;
                            attribute Ixx : Real = 5679.668537919446;
                            attribute sigma_Ixx : Real = 3559.0179271565075;
                            attribute Iyy : Real = 5789.123980304152;
                            attribute sigma_Iyy : Real = 3813.1774545331878;
                            attribute Izz : Real = 7537.311485474801;
                            attribute sigma_Izz : Real = 4356.459529409189;
                            attribute Ixy : Real = -3183.556945344523;
                            attribute sigma_Ixy : Real = 2141.4367188462265;
                            attribute Ixz : Real = 1952.702871199474;
                            attribute sigma_Ixz : Real = 1854.9127141223535;
                            attribute Iyz : Real = 1523.031875912324;
                            attribute sigma_Iyz : Real = 1741.346833423178;
                            part <'C.1.2.3.1.3.1.1'> 'Part 1038' {
                                attribute POIconv : String = "+";
                                attribute Ipoint : Boolean = false;
                                attribute mass : Real = 0.5550174316570629;
                                attribute sigma_mass : Real = 0.28909372274994966;
                                attribute Cx : Real = -83.23413799516857;
                                attribute sigma_Cx : Real = 28.721044428837228;
                                attribute Cy : Real = -75.53682094439864;
                                attribute sigma_Cy : Real = 28.23690002309109;
                                attribute Cz : Real = 11.247013928368688;
                                attribute sigma_Cz : Real = 29.057750463592832;
                                attribute Ixx : Real = 0.7261047515231042;
                                attribute sigma_Ixx : Real = 0.37074144170588635;
                                attribute Iyy : Real = 0.8144103175995534;
                                attribute sigma_Iyy : Real = 0.3723953238821935;
                                attribute Izz : Real = 0.7389736737162942;
                                attribute sigma_Izz : Real = 0.37017423652493897;
                                attribute Ixy : Real = -0.0006030436115606549;
                                attribute sigma_Ixy : Real = 0.02351283871158888;
                                attribute Ixz : Real = 0.011390652148165729;
                                attribute sigma_Ixz : Real = 0.022566176940390956;
                                attribute Iyz : Real = 0.005607807353903772;
                                attribute sigma_Iyz : Real = 0.02209918015384651;
                            }
                            part <'C.1.2.3.1.3.1.2'> 'Part 1039' {
                                attribute POIconv : String = "+";
                                attribute Ipoint : Boolean = false;
                                attribute mass : Real = 0.6380803078019526;
                                attribute sigma_mass : Real = 0.28909372274994966;
                                attribute Cx : Real = 28.728295722976327;
                                attribute sigma_Cx : Real = 28.721044428837228;
                                attribute Cy : Real = 16.28398336470127;
                                attribute sigma_Cy : Real = 28.23690002309109;
                                attribute Cz : Real = -48.897430719807744;
                                attribute sigma_Cz : Real = 29.057750463592832;
                                attribute Ixx : Real = 0.736063269747002;
                                attribute sigma_Ixx : Real = 0.37074144170588635;
                                attribute Iyy : Real = 0.7347650639624751;
                                attribute sigma_Iyy : Real = 0.3723953238821935;
                                attribute Izz : Real = 0.8064009702170114;
                                attribute sigma_Izz : Real = 0.37017423652493897;
                                attribute Ixy : Real = 0.00041781764174185656;
                                attribute sigma_Ixy : Real = 0.02351283871158888;
                                attribute Ixz : Real = 0.0028424401788568494;
                                attribute sigma_Ixz : Real = 0.022566176940390956;
                                attribute Iyz : Real = -0.010720685006515032;
                                attribute sigma_Iyz : Real = 0.02209918015384651;
                            }
                            part <'C.1.2.3.1.3.1.3'> 'Part 1040' {
                                attribute POIconv : String = "-";
                                attribute Ipoint : Boolean = false;
                                attribute mass : Real = 0.3094720288219396;
                                attribute sigma_mass : Real = 0.28909372274994966;
                                attribute Cx : Real = -24.840944446623325;
                                attribute sigma_Cx : Real = 28.721044428837228;
                                attribute Cy : Real = -5.2813556510955095;
                                attribute sigma_Cy : Real = 28.23690002309109;
                                attribute Cz : Real = -75.69127320311964;
                                attribute sigma_Cz : Real = 29.057750463592832;
                                attribute Ixx : Real = 0.36016045845070477;
                                attribute sigma_Ixx : Real = 0.37074144170588635;
                                attribute Iyy : Real = 0.35454182068610607;
                                attribute sigma_Iyy : Real = 0.3723953238821935;
                                attribute Izz : Real = 0.35479705701181236;
                                attribute sigma_Izz : Real = 0.37017423652493897;
                                attribute Ixy : Real = 0.0039038446238540627;
                                attribute sigma_Ixy : Real = 0.02351283871158888;
                                attribute Ixz : Real = -0.001795304792344311;
                                attribute sigma_Ixz : Real = 0.022566176940390956;
                                attribute Iyz : Real = -0.008648017760423093;
                                attribute sigma_Iyz : Real = 0.02209918015384651;
                            }
                            part <'C.1.2.3.1.3.1.4'> 'Part 1041' {
                                attribute POIconv : String = "-";
                                attribute Ipoint : Boolean = false;
                                attribute mass : Real = 0.16986004425073042;
                                attribute sigma_mass : Real = 0.28909372274994966;
                                attribute Cx : Real = -0.2717094961553812;
                                attribute sigma_Cx : Real = 28.721044428837228;
                                attribute Cy : Real = -21.255956683307886;
                                attribute sigma_Cy : Real = 28.23690002309109;
                                attribute Cz : Real = -38.88189485296607;
                                attribute sigma_Cz : Real = 29.057750463592832;
                                attribute Ixx : Real = 0.21849133361234896;
                                attribute sigma_Ixx : Real = 0.37074144170588635;
                                attribute Iyy : Real = 0.18388470079723432;
                                attribute sigma_Iyy : Real = 0.3723953238821935;
                                attribute Izz : Real = 0.2200873704419569;
                                attribute sigma_Izz : Real = 0.37017423652493897;
                                attribute Ixy : Real = 0.006259424424891615;
                                attribute sigma_Ixy : Real = 0.02351283871158888;
                                attribute Ixz : Real = 0.0003844146779999202;
                                attribute sigma_Ixz : Real = 0.022566176940390956;
                                attribute Iyz : Real = 0.00026529433137622075;
                                attribute sigma_Iyz : Real = 0.02209918015384651;
                            }
                            part <'C.1.2.3.1.3.1.5'> 'Part 1042' {
                                attribute POIconv : String = "-";
                                attribute Ipoint : Boolean = false;
                                attribute mass : Real = 0.5001672283564694;
                                attribute sigma_mass : Real = 0.28909372274994966;
                                attribute Cx : Real = -27.933583734557033;
                                attribute sigma_Cx : Real = 28.721044428837228;
                                attribute Cy : Real = -75.44109709560871;
                                attribute sigma_Cy : Real = 28.23690002309109;
                                attribute Cz : Real = -52.39798869006336;
                                attribute sigma_Cz : Real = 29.057750463592832;
                                attribute Ixx : Real = 0.6248696392366354;
                                attribute sigma_Ixx : Real = 0.37074144170588635;
                                attribute Iyy : Real = 0.6197903049561545;
                                attribute sigma_Iyy : Real = 0.3723953238821935;
                                attribute Izz : Real = 0.6683337745048498;
                                attribute sigma_Izz : Real = 0.37017423652493897;
                                attribute Ixy : Real = -0.0188628541866031;
                                attribute sigma_Ixy : Real = 0.02351283871158888;
                                attribute Ixz : Real = -0.0006235961041831588;
                                attribute sigma_Ixz : Real = 0.022566176940390956;
                                attribute Iyz : Real = 0.008185718381841973;
                                attribute sigma_Iyz : Real = 0.02209918015384651;
                            }
                        }
                        part <'C.1.2.3.1.3.2'> 'Subassembly 294' {
                            attribute POIconv : String = "-";
                            attribute Ipoint : Boolean = false;
                            attribute mass : Real = 0.9625668708614539;
                            attribute sigma_mass : Real = 0.40884026350990615;
                            attribute Cx : Real = -16.356659457755796;
                            attribute sigma_Cx : Real = 43.67263915812166;
                            attribute Cy : Real = -77.00755807786214;
                            attribute sigma_Cy : Real = 25.860273018421562;
                            attribute Cz : Real = 70.88414900381579;
                            attribute sigma_Cz : Real = 26.27703657915194;
                            attribute Ixx : Real = 26.756343503540297;
                            attribute sigma_Ixx : Real = 138.19455182308033;
                            attribute Iyy : Real = 1498.9619819437385;
                            attribute sigma_Iyy : Real = 4024.6788389395088;
                            attribute Izz : Real = 1519.1581685532706;
                            attribute sigma_Izz : Real = 4077.1665583830254;
                            attribute Ixy : Real = 184.7591171023769;
                            attribute sigma_Ixy : Real = 669.916225865432;
                            attribute Ixz : Real = 64.17866135698071;
                            attribute sigma_Ixz : Real = 503.1339113753832;
                            attribute Iyz : Real = -7.940261416233691;
                            attribute sigma_Iyz : Real = 65.21392332853092;
                            part <'C.1.2.3.1.3.2.1'> 'Part 1043' {
                                attribute POIconv : String = "+";
                                attribute Ipoint : Boolean = false;
                                attribute mass : Real = 0.8633369037602097;
                                attribute sigma_mass : Real = 0.28909372274994966;
                                attribute Cx : Real = -29.717338038608432;
                                attribute sigma_Cx : Real = 28.721044428837228;
                                attribute Cy : Real = -75.35580983385444;
                                attribute sigma_Cy : Real = 28.23690002309109;
                                attribute Cz : Real = 71.45699337124825;
                                attribute sigma_Cz : Real = 29.057750463592832;
                                attribute Ixx : Real = 1.0316033114297507;
                                attribute sigma_Ixx : Real = 0.37074144170588635;
                                attribute Iyy : Real = 1.130442947356974;
                                attribute sigma_Iyy : Real = 0.3723953238821935;
                                attribute Izz : Real = 1.2345906690436015;
                                attribute sigma_Izz : Real = 0.37017423652493897;
                                attribute Ixy : Real = 0.051741394502052014;
                                attribute sigma_Ixy : Real = 0.02351283871158888;
                                attribute Ixz : Real = -0.07750720716025238;
                                attribute sigma_Ixz : Real = 0.022566176940390956;
                                attribute Iyz : Real = 0.013980486910605699;
                                attribute sigma_Iyz : Real = 0.02209918015384651;
                            }
                            part <'C.1.2.3.1.3.2.2'> 'Part 1044' {
                                attribute POIconv : String = "+";
                                attribute Ipoint : Boolean = false;
                                attribute mass : Real = 0.09922996710124425;
                                attribute sigma_mass : Real = 0.28909372274994966;
                                attribute Cx : Real = 99.88611694425344;
                                attribute sigma_Cx : Real = 28.721044428837228;
                                attribute Cy : Real = -91.37837020680308;
                                attribute sigma_Cy : Real = 28.23690002309109;
                                attribute Cz : Real = 65.90019408613443;
                                attribute sigma_Cz : Real = 29.057750463592832;
                                attribute Ixx : Real = 0.12816754401706107;
                                attribute sigma_Ixx : Real = 0.37074144170588635;
                                attribute Iyy : Real = 0.13774139237629984;
                                attribute sigma_Iyy : Real = 0.3723953238821935;
                                attribute Izz : Real = 0.12952318542842847;
                                attribute sigma_Izz : Real = 0.37017423652493897;
                                attribute Ixy : Real = 0.00564019582603183;
                                attribute sigma_Ixy : Real = 0.02351283871158888;
                                attribute Ixz : Real = -0.004769807480596106;
                                attribute sigma_Ixz : Real = 0.022566176940390956;
                                attribute Iyz : Real = 0.0022006033112167366;
                                attribute sigma_Iyz : Real = 0.02209918015384651;
                            }
                        }
                    }
                    part <'C.1.2.3.1.4'> 'Assembly 86' {
                        attribute POIconv : String = "-";
                        attribute Ipoint : Boolean = false;
                        attribute mass : Real = 7.55242718391656;
                        attribute sigma_mass : Real = 1.1563748909997986;
                        attribute Cx : Real = 7.363234107828627;
                        attribute sigma_Cx : Real = 13.68404868899623;
                        attribute Cy : Real = -9.115689921426421;
                        attribute sigma_Cy : Real = 12.477818492444857;
                        attribute Cz : Real = 19.44214432571307;
                        attribute sigma_Cz : Real = 13.150890570513871;
                        attribute Ixx : Real = 40064.535747170485;
                        attribute sigma_Ixx : Real = 15381.492589311467;
                        attribute Iyy : Real = 45315.9687752499;
                        attribute sigma_Iyy : Real = 17986.871104870796;
                        attribute Izz : Real = 43780.481709667845;
                        attribute sigma_Izz : Real = 17801.80550463168;
                        attribute Ixy : Real = -7888.196365473831;
                        attribute sigma_Ixy : Real = 8480.496099510132;
                        attribute Ixz : Real = -9522.547487242486;
                        attribute sigma_Ixz : Real = 7793.774253192641;
                        attribute Iyz : Real = -8007.830768370253;
                        attribute sigma_Iyz : Real = 6785.155546640796;
                        part <'C.1.2.3.1.4.1'> 'Subassembly 295' {
                            attribute POIconv : String = "-";
                            attribute Ipoint : Boolean = false;
                            attribute mass : Real = 0.8966527120447718;
                            attribute sigma_mass : Real = 0.40884026350990615;
                            attribute Cx : Real = -62.31782971512749;
                            attribute sigma_Cx : Real = 56.15560851138507;
                            attribute Cy : Real = 24.4245921338566;
                            attribute sigma_Cy : Real = 45.87652040064551;
                            attribute Cz : Real = 27.891411084339047;
                            attribute sigma_Cz : Real = 30.613863104193175;
                            attribute Ixx : Real = 473.4474212955698;
                            attribute sigma_Ixx : Real = 4207.97788526009;
                            attribute Iyy : Real = 793.2265952756817;
                            attribute sigma_Iyy : Real = 7049.829467215431;
                            attribute Izz : Real = 1171.9387627873461;
                            attribute sigma_Izz : Real = 10413.941639463994;
                            attribute Ixy : Real = 563.2765273553238;
                            attribute sigma_Ixy : Real = 5009.336706331433;
                            attribute Ixz : Real = -186.97913957368723;
                            attribute sigma_Ixz : Real = 1672.699028396224;
                            attribute Iyz : Real = 141.28635863939382;
                            attribute sigma_Iyz : Real = 1264.2328743400417;
                            part <'C.1.2.3.1.4.1.1'> 'Part 1045' {
                                attribute POIconv : String = "+";
                                attribute Ipoint : Boolean = false;
                                attribute mass : Real = 0.8652523746620864;
                                attribute sigma_mass : Real = 0.28909372274994966;
                                attribute Cx : Real = -67.81035801395774;
                                attribute sigma_Cx : Real = 28.721044428837228;
                                attribute Cy : Real = 28.574663773179054;
                                attribute sigma_Cy : Real = 28.23690002309109;
                                attribute Cz : Real = 26.51412351988256;
                                attribute sigma_Cz : Real = 29.057750463592832;
                                attribute Ixx : Real = 0.9952737849813976;
                                attribute sigma_Ixx : Real = 0.37074144170588635;
                                attribute Iyy : Real = 0.9357890231830773;
                                attribute sigma_Iyy : Real = 0.3723953238821935;
                                attribute Izz : Real = 0.9740654577356895;
                                attribute sigma_Izz : Real = 0.37017423652493897;
                                attribute Ixy : Real = -0.07900628699054632;
                                attribute sigma_Ixy : Real = 0.02351283871158888;
                                attribute Ixz : Real = 0.07016981104621788;
                                attribute sigma_Ixz : Real = 0.022566176940390956;
                                attribute Iyz : Real = -0.061090488446185656;
                                attribute sigma_Iyz : Real = 0.02209918015384651;
                            }
                            part <'C.1.2.3.1.4.1.2'> 'Part 1046' {
                                attribute POIconv : String = "+";
                                attribute Ipoint : Boolean = false;
                                attribute mass : Real = 0.03140033738268539;
                                attribute sigma_mass : Real = 0.28909372274994966;
                                attribute Cx : Real = 89.0315999276936;
                                attribute sigma_Cx : Real = 28.721044428837228;
                                attribute Cy : Real = -89.93275687098503;
                                attribute sigma_Cy : Real = 28.23690002309109;
                                attribute Cz : Real = 65.84327514283359;
                                attribute sigma_Cz : Real = 29.057750463592832;
                                attribute Ixx : Real = 0.04006659707022646;
                                attribute sigma_Ixx : Real = 0.37074144170588635;
                                attribute Iyy : Real = 0.042851373811632544;
                                attribute sigma_Iyy : Real = 0.3723953238821935;
                                attribute Izz : Real = 0.041866582474210295;
                                attribute sigma_Izz : Real = 0.37017423652493897;
                                attribute Ixy : Real = -0.00011134199603787096;
                                attribute sigma_Ixy : Real = 0.02351283871158888;
                                attribute Ixz : Real = 0.00019898372714573546;
                                attribute sigma_Ixz : Real = 0.022566176940390956;
                                attribute Iyz : Real = 0.00018332563179450815;
                                attribute sigma_Iyz : Real = 0.02209918015384651;
                            }
                        }
                        part <'C.1.2.3.1.4.2'> 'Subassembly 296' {
                            attribute POIconv : String = "-";
                            attribute Ipoint : Boolean = false;
                            attribute mass : Real = 2.1527884380111937;
                            attribute sigma_mass : Real = 0.6464332159373649;
                            attribute Cx : Real = 12.940880141110132;
                            attribute sigma_Cx : Real = 24.286011828362106;
                            attribute Cy : Real = -46.57914977170801;
                            attribute sigma_Cy : Real = 22.79039792313275;
                            attribute Cz : Real = -32.91621434197114;
                            attribute sigma_Cz : Real = 21.87589504377272;
                            attribute Ixx : Real = 11310.49058022119;
                            attribute sigma_Ixx : Real = 6224.127909846258;
                            attribute Iyy : Real = 12832.360459650963;
                            attribute sigma_Iyy : Real = 7475.401759484276;
                            attribute Izz : Real = 16903.18917359919;
                            attribute sigma_Izz : Real = 7836.208249362416;
                            attribute Ixy : Real = -6371.878067543017;
                            attribute sigma_Ixy : Real = 3733.926181437585;
                            attribute Ixz : Real = -4323.627964705714;
                            attribute sigma_Ixz : Real = 3622.3246581954872;
                            attribute Iyz : Real = -1169.049368919917;
                            attribute sigma_Iyz : Real = 2490.333023685407;
                            part <'C.1.2.3.1.4.2.1'> 'Part 1047' {
                                attribute POIconv : String = "+";
                                attribute Ipoint : Boolean = false;
                                attribute mass : Real = 0.2642831369091291;
                                attribute sigma_mass : Real = 0.28909372274994966;
                                attribute Cx : Real = 96.24938839115202;
                                attribute sigma_Cx : Real = 28.721044428837228;
                                attribute Cy : Real = -64.10846440121531;
                                attribute sigma_Cy : Real = 28.23690002309109;
                                attribute Cz : Real = 68.2395697105676;
                                attribute sigma_Cz : Real = 29.057750463592832;
                                attribute Ixx : Real = 0.3765125075978308;
                                attribute sigma_Ixx : Real = 0.37074144170588635;
                                attribute Iyy : Real = 0.3205503440554988;
                                attribute sigma_Iyy : Real = 0.3723953238821935;
                                attribute Izz : Real = 0.344764225930941;
                                attribute sigma_Izz : Real = 0.37017423652493897;
                                attribute Ixy : Real = -0.013281969353616255;
                                attribute sigma_Ixy : Real = 0.02351283871158888;
                                attribute Ixz : Real = -0.042489145372811676;
                                attribute sigma_Ixz : Real = 0.022566176940390956;
                                attribute Iyz : Real = -0.008543652033743514;
                                attribute sigma_Iyz : Real = 0.02209918015384651;
                            }
                            part <'C.1.2.3.1.4.2.2'> 'Part 1048' {
                                attribute POIconv : String = "-";
                                attribute Ipoint : Boolean = false;
                                attribute mass : Real = 0.999615342994919;
                                attribute sigma_mass : Real = 0.28909372274994966;
                                attribute Cx : Real = -51.21070072054863;
                                attribute sigma_Cx : Real = 28.721044428837228;
                                attribute Cy : Real = -89.31024805642664;
                                attribute sigma_Cy : Real = 28.23690002309109;
                                attribute Cz : Real = -62.562374444678426;
                                attribute sigma_Cz : Real = 29.057750463592832;
                                attribute Ixx : Real = 1.2056185845625573;
                                attribute sigma_Ixx : Real = 0.37074144170588635;
                                attribute Iyy : Real = 1.1665602386299811;
                                attribute sigma_Iyy : Real = 0.3723953238821935;
                                attribute Izz : Real = 1.2714362956349599;
                                attribute sigma_Izz : Real = 0.37017423652493897;
                                attribute Ixy : Real = 0.040719956767876625;
                                attribute sigma_Ixy : Real = 0.02351283871158888;
                                attribute Ixz : Real = -0.0028392401073712376;
                                attribute sigma_Ixz : Real = 0.022566176940390956;
                                attribute Iyz : Real = -0.0039137879003151715;
                                attribute sigma_Iyz : Real = 0.02209918015384651;
                            }
                            part <'C.1.2.3.1.4.2.3'> 'Part 1049' {
                                attribute POIconv : String = "+";
                                attribute Ipoint : Boolean = false;
                                attribute mass : Real = 0.12687110711215063;
                                attribute sigma_mass : Real = 0.28909372274994966;
                                attribute Cx : Real = -24.90128637291491;
                                attribute sigma_Cx : Real = 28.721044428837228;
                                attribute Cy : Real = -84.25761237740517;
                                attribute sigma_Cy : Real = 28.23690002309109;
                                attribute Cz : Real = -28.610008023679256;
                                attribute sigma_Cz : Real = 29.057750463592832;
                                attribute Ixx : Real = 0.14988434141791196;
                                attribute sigma_Ixx : Real = 0.37074144170588635;
                                attribute Iyy : Real = 0.14728455865374115;
                                attribute sigma_Iyy : Real = 0.3723953238821935;
                                attribute Izz : Real = 0.1630007169630277;
                                attribute sigma_Izz : Real = 0.37017423652493897;
                                attribute Ixy : Real = 0.0032933174822273974;
                                attribute sigma_Ixy : Real = 0.02351283871158888;
                                attribute Ixz : Real = 0.0003048478651590396;
                                attribute sigma_Ixz : Real = 0.022566176940390956;
                                attribute Iyz : Real = 0.008232396454768759;
                                attribute sigma_Iyz : Real = 0.02209918015384651;
                            }
                            part <'C.1.2.3.1.4.2.4'> 'Part 1050' {
                                attribute POIconv : String = "+";
                                attribute Ipoint : Boolean = false;
                                attribute mass : Real = 0.12058695780276321;
                                attribute sigma_mass : Real = 0.28909372274994966;
                                attribute Cx : Real = 37.75184159167111;
                                attribute sigma_Cx : Real = 28.721044428837228;
                                attribute Cy : Real = -97.41140520200133;
                                attribute sigma_Cy : Real = 28.23690002309109;
                                attribute Cz : Real = -43.341012205928564;
                                attribute sigma_Cz : Real = 29.057750463592832;
                                attribute Ixx : Real = 0.16137069474304677;
                                attribute sigma_Ixx : Real = 0.37074144170588635;
                                attribute Iyy : Real = 0.17364600231446742;
                                attribute sigma_Iyy : Real = 0.3723953238821935;
                                attribute Izz : Real = 0.15561126203617454;
                                attribute sigma_Izz : Real = 0.37017423652493897;
                                attribute Ixy : Real = -0.019312389766490683;
                                attribute sigma_Ixy : Real = 0.02351283871158888;
                                attribute Ixz : Real = -0.0005302972116278399;
                                attribute sigma_Ixz : Real = 0.022566176940390956;
                                attribute Iyz : Real = -0.004469059817591223;
                                attribute sigma_Iyz : Real = 0.02209918015384651;
                            }
                            part <'C.1.2.3.1.4.2.5'> 'Part 1051' {
                                attribute POIconv : String = "-";
                                attribute Ipoint : Boolean = false;
                                attribute mass : Real = 0.6414318931922317;
                                attribute sigma_mass : Real = 0.28909372274994966;
                                attribute Cx : Real = 81.41123573295772;
                                attribute sigma_Cx : Real = 28.721044428837228;
                                attribute Cy : Real = 44.24480153247714;
                                attribute sigma_Cy : Real = 28.23690002309109;
                                attribute Cz : Real = -27.285452745854855;
                                attribute sigma_Cz : Real = 29.057750463592832;
                                attribute Ixx : Real = 0.6513690223782906;
                                attribute sigma_Ixx : Real = 0.37074144170588635;
                                attribute Iyy : Real = 0.8085106982083033;
                                attribute sigma_Iyy : Real = 0.3723953238821935;
                                attribute Izz : Real = 0.8175795258224554;
                                attribute sigma_Izz : Real = 0.37017423652493897;
                                attribute Ixy : Real = 0.038210789931354565;
                                attribute sigma_Ixy : Real = 0.02351283871158888;
                                attribute Ixz : Real = 0.03261761625926242;
                                attribute sigma_Ixz : Real = 0.022566176940390956;
                                attribute Iyz : Real = 0.00020372727072478797;
                                attribute sigma_Iyz : Real = 0.02209918015384651;
                            }
                        }
                        part <'C.1.2.3.1.4.3'> 'Subassembly 297' {
                            attribute POIconv : String = "-";
                            attribute Ipoint : Boolean = false;
                            attribute mass : Real = 1.2655437552137299;
                            attribute sigma_mass : Real = 0.5781874454998993;
                            attribute Cx : Real = -25.761671313665214;
                            attribute sigma_Cx : Real = 19.96130708603539;
                            attribute Cy : Real = -30.17606038746919;
                            attribute sigma_Cy : Real = 23.557565048313396;
                            attribute Cz : Real = 15.756459509072384;
                            attribute sigma_Cz : Real = 26.640977453338312;
                            attribute Ixx : Real = 4893.59245322191;
                            attribute sigma_Ixx : Real = 3592.76930548611;
                            attribute Iyy : Real = 3998.7838170524037;
                            attribute sigma_Iyy : Real = 2893.213706711536;
                            attribute Izz : Real = 3322.412171255944;
                            attribute sigma_Izz : Real = 2533.2248183360402;
                            attribute Ixy : Real = -1142.7518620518997;
                            attribute sigma_Ixy : Real = 1166.500950628374;
                            attribute Ixz : Real = -57.748063263142306;
                            attribute sigma_Ixz : Real = 1185.162962652149;
                            attribute Iyz : Real = 1605.3181540093005;
                            attribute sigma_Iyz : Real = 1719.9042688746656;
                            part <'C.1.2.3.1.4.3.1'> 'Part 1052' {
                                attribute POIconv : String = "+";
                                attribute Ipoint : Boolean = false;
                                attribute mass : Real = 0.16340611016773618;
                                attribute sigma_mass : Real = 0.28909372274994966;
                                attribute Cx : Real = -12.414421234279871;
                                attribute sigma_Cx : Real = 28.721044428837228;
                                attribute Cy : Real = 0.26108059100806713;
                                attribute sigma_Cy : Real = 28.23690002309109;
                                attribute Cz : Real = -35.56481748819351;
                                attribute sigma_Cz : Real = 29.057750463592832;
                                attribute Ixx : Real = 0.16654416391940294;
                                attribute sigma_Ixx : Real = 0.37074144170588635;
                                attribute Iyy : Real = 0.17144562127916171;
                                attribute sigma_Iyy : Real = 0.3723953238821935;
                                attribute Izz : Real = 0.1461097597527174;
                                attribute sigma_Izz : Real = 0.37017423652493897;
                                attribute Ixy : Real = -0.004029189984110122;
                                attribute sigma_Ixy : Real = 0.02351283871158888;
                                attribute Ixz : Real = 0.006847152148634688;
                                attribute sigma_Ixz : Real = 0.022566176940390956;
                                attribute Iyz : Real = -0.003419139572301038;
                                attribute sigma_Iyz : Real = 0.02209918015384651;
                            }
                            part <'C.1.2.3.1.4.3.2'> 'Part 1053' {
                                attribute POIconv : String = "-";
                                attribute Ipoint : Boolean = false;
                                attribute mass : Real = 0.3966979910978116;
                                attribute sigma_mass : Real = 0.28909372274994966;
                                attribute Cx : Real = -58.24294341728091;
                                attribute sigma_Cx : Real = 28.721044428837228;
                                attribute Cy : Real = -33.98464969359338;
                                attribute sigma_Cy : Real = 28.23690002309109;
                                attribute Cz : Real = -24.631404550746083;
                                attribute sigma_Cz : Real = 29.057750463592832;
                                attribute Ixx : Real = 0.37043131602739643;
                                attribute sigma_Ixx : Real = 0.37074144170588635;
                                attribute Iyy : Real = 0.37487626307375166;
                                attribute sigma_Iyy : Real = 0.3723953238821935;
                                attribute Izz : Real = 0.37484620368636934;
                                attribute sigma_Izz : Real = 0.37017423652493897;
                                attribute Ixy : Real = 0.011610541711058808;
                                attribute sigma_Ixy : Real = 0.02351283871158888;
                                attribute Ixz : Real = 0.01043426834880536;
                                attribute sigma_Ixz : Real = 0.022566176940390956;
                                attribute Iyz : Real = -0.007016248461573873;
                                attribute sigma_Iyz : Real = 0.02209918015384651;
                            }
                            part <'C.1.2.3.1.4.3.3'> 'Part 1054' {
                                attribute POIconv : String = "+";
                                attribute Ipoint : Boolean = false;
                                attribute mass : Real = 0.34402778986585325;
                                attribute sigma_mass : Real = 0.28909372274994966;
                                attribute Cx : Real = -40.55429487489164;
                                attribute sigma_Cx : Real = 28.721044428837228;
                                attribute Cy : Real = -88.74849979765713;
                                attribute sigma_Cy : Real = 28.23690002309109;
                                attribute Cz : Real = 86.19010825641453;
                                attribute sigma_Cz : Real = 29.057750463592832;
                                attribute Ixx : Real = 0.46355154857513636;
                                attribute sigma_Ixx : Real = 0.37074144170588635;
                                attribute Iyy : Real = 0.5196562143003289;
                                attribute sigma_Iyy : Real = 0.3723953238821935;
                                attribute Izz : Real = 0.4823439154859447;
                                attribute sigma_Izz : Real = 0.37017423652493897;
                                attribute Ixy : Real = -0.020006168681553842;
                                attribute sigma_Ixy : Real = 0.02351283871158888;
                                attribute Ixz : Real = -0.007743641368593271;
                                attribute sigma_Ixz : Real = 0.022566176940390956;
                                attribute Iyz : Real = 0.01510937372590955;
                                attribute sigma_Iyz : Real = 0.02209918015384651;
                            }
                            part <'C.1.2.3.1.4.3.4'> 'Part 1055' {
                                attribute POIconv : String = "+";
                                attribute Ipoint : Boolean = false;
                                attribute mass : Real = 0.36141186408232895;
                                attribute sigma_mass : Real = 0.28909372274994966;
                                attribute Cx : Real = 17.937244893983006;
                                attribute sigma_Cx : Real = 28.721044428837228;
                                attribute Cy : Real = 15.997829986736178;
                                attribute sigma_Cy : Real = 28.23690002309109;
                                attribute Cz : Real = 16.24582437798381;
                                attribute sigma_Cz : Real = 29.057750463592832;
                                attribute Ixx : Real = 0.3978110265653177;
                                attribute sigma_Ixx : Real = 0.37074144170588635;
                                attribute Iyy : Real = 0.3962637160353485;
                                attribute sigma_Iyy : Real = 0.3723953238821935;
                                attribute Izz : Real = 0.39378280426432843;
                                attribute sigma_Izz : Real = 0.37017423652493897;
                                attribute Ixy : Real = 0.010911645268354458;
                                attribute sigma_Ixy : Real = 0.02351283871158888;
                                attribute Ixz : Real = -0.0023715896487131703;
                                attribute sigma_Ixz : Real = 0.022566176940390956;
                                attribute Iyz : Real = 0.00512747725977481;
                                attribute sigma_Iyz : Real = 0.02209918015384651;
                            }
                        }
                        part <'C.1.2.3.1.4.4'> 'Subassembly 298' {
                            attribute POIconv : String = "-";
                            attribute Ipoint : Boolean = false;
                            attribute mass : Real = 2.3578399748364465;
                            attribute sigma_mass : Real = 0.5007250159521434;
                            attribute Cx : Real = 18.27604720304858;
                            attribute sigma_Cx : Real = 17.426230697154374;
                            attribute Cy : Real = 11.838282932209589;
                            attribute sigma_Cy : Real = 17.151754730110063;
                            attribute Cz : Real = 52.055692522599074;
                            attribute sigma_Cz : Real = 17.281741746095207;
                            attribute Ixx : Real = 1897.5938849604522;
                            attribute sigma_Ixx : Real = 2328.075980581729;
                            attribute Iyy : Real = 1910.3016817253692;
                            attribute sigma_Iyy : Real = 2362.240938507303;
                            attribute Izz : Real = 2574.0188846842734;
                            attribute sigma_Izz : Real = 2733.057496725441;
                            attribute Ixy : Real = 1113.9152167062507;
                            attribute sigma_Ixy : Real = 1364.1267577212127;
                            attribute Ixz : Real = -715.9183009265224;
                            attribute sigma_Ixz : Real = 1181.7873624926067;
                            attribute Iyz : Real = 881.1847149472675;
                            attribute sigma_Iyz : Real = 1172.851990927592;
                            part <'C.1.2.3.1.4.4.1'> 'Part 1056' {
                                attribute POIconv : String = "+";
                                attribute Ipoint : Boolean = false;
                                attribute mass : Real = 0.882149980786955;
                                attribute sigma_mass : Real = 0.28909372274994966;
                                attribute Cx : Real = 47.88799895904958;
                                attribute sigma_Cx : Real = 28.721044428837228;
                                attribute Cy : Real = -10.57063271291554;
                                attribute sigma_Cy : Real = 28.23690002309109;
                                attribute Cz : Real = 65.87203093804419;
                                attribute sigma_Cz : Real = 29.057750463592832;
                                attribute Ixx : Real = 1.1688060181363202;
                                attribute sigma_Ixx : Real = 0.37074144170588635;
                                attribute Iyy : Real = 1.1635226655013726;
                                attribute sigma_Iyy : Real = 0.3723953238821935;
                                attribute Izz : Real = 1.1479625672645903;
                                attribute sigma_Izz : Real = 0.37017423652493897;
                                attribute Ixy : Real = 0.01930441876696838;
                                attribute sigma_Ixy : Real = 0.02351283871158888;
                                attribute Ixz : Real = -0.011765484472756993;
                                attribute sigma_Ixz : Real = 0.022566176940390956;
                                attribute Iyz : Real = -0.015910416597707207;
                                attribute sigma_Iyz : Real = 0.02209918015384651;
                            }
                            part <'C.1.2.3.1.4.4.2'> 'Part 1057' {
                                attribute POIconv : String = "-";
                                attribute Ipoint : Boolean = false;
                                attribute mass : Real = 0.6235593824088573;
                                attribute sigma_mass : Real = 0.28909372274994966;
                                attribute Cx : Real = 7.771596126258373;
                                attribute sigma_Cx : Real = 28.721044428837228;
                                attribute Cy : Real = 2.2334241308271885;
                                attribute sigma_Cy : Real = 28.23690002309109;
                                attribute Cz : Real = 61.70614478178322;
                                attribute sigma_Cz : Real = 29.057750463592832;
                                attribute Ixx : Real = 0.8180365352892478;
                                attribute sigma_Ixx : Real = 0.37074144170588635;
                                attribute Iyy : Real = 0.7994194940059788;
                                attribute sigma_Iyy : Real = 0.3723953238821935;
                                attribute Izz : Real = 0.8366687939019364;
                                attribute sigma_Izz : Real = 0.37017423652493897;
                                attribute Ixy : Real = -0.02938419950643506;
                                attribute sigma_Ixy : Real = 0.02351283871158888;
                                attribute Ixz : Real = 0.01285629030817942;
                                attribute sigma_Ixz : Real = 0.022566176940390956;
                                attribute Iyz : Real = 0.007194026996384556;
                                attribute sigma_Iyz : Real = 0.02209918015384651;
                            }
                            part <'C.1.2.3.1.4.4.3'> 'Part 1058' {
                                attribute POIconv : String = "-";
                                attribute Ipoint : Boolean = false;
                                attribute mass : Real = 0.852130611640634;
                                attribute sigma_mass : Real = 0.28909372274994966;
                                attribute Cx : Real = -4.6923022251576185;
                                attribute sigma_Cx : Real = 28.721044428837228;
                                attribute Cy : Real = 42.065133107826114;
                                attribute sigma_Cy : Real = 28.23690002309109;
                                attribute Cz : Real = 30.690760351717472;
                                attribute sigma_Cz : Real = 29.057750463592832;
                                attribute Ixx : Real = 1.1105258109156457;
                                attribute sigma_Ixx : Real = 0.37074144170588635;
                                attribute Iyy : Real = 1.0355550546965706;
                                attribute sigma_Iyy : Real = 0.3723953238821935;
                                attribute Izz : Real = 1.0972395006960478;
                                attribute sigma_Izz : Real = 0.37017423652493897;
                                attribute Ixy : Real = -0.09355479906332526;
                                attribute sigma_Ixy : Real = 0.02351283871158888;
                                attribute Ixz : Real = -0.08673590560438557;
                                attribute sigma_Ixz : Real = 0.022566176940390956;
                                attribute Iyz : Real = -0.05994350970063276;
                                attribute sigma_Iyz : Real = 0.02209918015384651;
                            }
                        }
                        part <'C.1.2.3.1.4.5'> 'Subassembly 299' {
                            attribute POIconv : String = "-";
                            attribute Ipoint : Boolean = false;
                            attribute mass : Real = 0.8796023038104177;
                            attribute sigma_mass : Real = 0.40884026350990615;
                            attribute Cx : Real = 83.15040851478382;
                            attribute sigma_Cx : Real = 34.186246131170265;
                            attribute Cy : Real = 22.51635984161162;
                            attribute sigma_Cy : Real = 36.96233423524969;
                            attribute Cz : Real = 56.85368681495074;
                            attribute sigma_Cz : Real = 56.08354616501837;
                            attribute Ixx : Real = 5260.702448745409;
                            attribute sigma_Ixx : Real = 8815.015898667414;
                            attribute Iyy : Real = 4917.211695985421;
                            attribute sigma_Iyy : Real = 8257.548957520406;
                            attribute Izz : Real = 2159.861705730275;
                            attribute sigma_Izz : Real = 3752.3162946025363;
                            attribute Ixy : Real = -1065.4819469007825;
                            attribute sigma_Ixy : Real = 1855.8159314250506;
                            attribute Ixz : Real = -1907.248670332994;
                            attribute sigma_Ixz : Real = 3264.004623792314;
                            attribute Iyz : Real = -2239.2513010711255;
                            attribute sigma_Iyz : Real = 3788.227354351955;
                            part <'C.1.2.3.1.4.5.1'> 'Part 1059' {
                                attribute POIconv : String = "-";
                                attribute Ipoint : Boolean = false;
                                attribute mass : Real = 0.7318226899350994;
                                attribute sigma_mass : Real = 0.28909372274994966;
                                attribute Cx : Real = 97.58448014035821;
                                attribute sigma_Cx : Real = 28.721044428837228;
                                attribute Cy : Real = 39.462982304394245;
                                attribute sigma_Cy : Real = 28.23690002309109;
                                attribute Cz : Real = 87.18860587105155;
                                attribute sigma_Cz : Real = 29.057750463592832;
                                attribute Ixx : Real = 1.194259308780735;
                                attribute sigma_Ixx : Real = 0.37074144170588635;
                                attribute Iyy : Real = 1.164746794612592;
                                attribute sigma_Iyy : Real = 0.3723953238821935;
                                attribute Izz : Real = 1.1818874468366765;
                                attribute sigma_Izz : Real = 0.37017423652493897;
                                attribute Ixy : Real = 0.007191862197908598;
                                attribute sigma_Ixy : Real = 0.02351283871158888;
                                attribute Ixz : Real = 0.0042229771623906506;
                                attribute sigma_Ixz : Real = 0.022566176940390956;
                                attribute Iyz : Real = 0.004750707336135576;
                                attribute sigma_Iyz : Real = 0.02209918015384651;
                            }
                            part <'C.1.2.3.1.4.5.2'> 'Part 1060' {
                                attribute POIconv : String = "-";
                                attribute Ipoint : Boolean = false;
                                attribute mass : Real = 0.14777961387531832;
                                attribute sigma_mass : Real = 0.28909372274994966;
                                attribute Cx : Real = 11.671123607084155;
                                attribute sigma_Cx : Real = 28.721044428837228;
                                attribute Cy : Real = -61.40538356266916;
                                attribute sigma_Cy : Real = 28.23690002309109;
                                attribute Cz : Real = -93.36853586137295;
                                attribute sigma_Cz : Real = 29.057750463592832;
                                attribute Ixx : Real = 0.21730305139269704;
                                attribute sigma_Ixx : Real = 0.37074144170588635;
                                attribute Iyy : Real = 0.19940687540370183;
                                attribute sigma_Iyy : Real = 0.3723953238821935;
                                attribute Izz : Real = 0.19978219411696613;
                                attribute sigma_Izz : Real = 0.37017423652493897;
                                attribute Ixy : Real = 0.0016795468598082381;
                                attribute sigma_Ixy : Real = 0.02351283871158888;
                                attribute Ixz : Real = 0.004897994911134354;
                                attribute sigma_Ixz : Real = 0.022566176940390956;
                                attribute Iyz : Real = -0.0003125191342217973;
                                attribute sigma_Iyz : Real = 0.02209918015384651;
                            }
                        }
                    }
                    part <'C.1.2.3.1.5'> 'Assembly 87' {
                        attribute POIconv : String = "-";
                        attribute Ipoint : Boolean = false;
                        attribute mass : Real = 8.420635958496481;
                        attribute sigma_mass : Real = 1.081689663197327;
                        attribute Cx : Real = -6.832966209856059;
                        attribute sigma_Cx : Real = 12.000358969007326;
                        attribute Cy : Real = 4.046181686264532;
                        attribute sigma_Cy : Real = 11.888079860844027;
                        attribute Cz : Real = -6.7449942416743625;
                        attribute sigma_Cz : Real = 11.842044017180127;
                        attribute Ixx : Real = 64233.972009855686;
                        attribute sigma_Ixx : Real = 15991.108838711725;
                        attribute Iyy : Real = 61072.46234992563;
                        attribute sigma_Iyy : Real = 15102.272840120577;
                        attribute Izz : Real = 59104.433794933495;
                        attribute sigma_Izz : Real = 15438.429640000235;
                        attribute Ixy : Real = 1253.3545423365476;
                        attribute sigma_Ixy : Real = 7450.8578699689415;
                        attribute Ixz : Real = 2687.7349749088307;
                        attribute sigma_Ixz : Real = 7139.157561528382;
                        attribute Iyz : Real = -13450.270596633669;
                        attribute sigma_Iyz : Real = 7690.940576123911;
                        part <'C.1.2.3.1.5.1'> 'Subassembly 300' {
                            attribute POIconv : String = "-";
                            attribute Ipoint : Boolean = false;
                            attribute mass : Real = 1.51665116684488;
                            attribute sigma_mass : Real = 0.5007250159521434;
                            attribute Cx : Real = 47.642228811938395;
                            attribute sigma_Cx : Real = 23.138395534634547;
                            attribute Cy : Real = 29.731469625274656;
                            attribute sigma_Cy : Real = 36.61384571733807;
                            attribute Cz : Real = 11.637992073128654;
                            attribute sigma_Cz : Real = 31.742072617573847;
                            attribute Ixx : Real = 19797.65066102324;
                            attribute sigma_Ixx : Real = 9926.357691008803;
                            attribute Iyy : Real = 10709.219565832565;
                            attribute sigma_Iyy : Real = 6125.138079360598;
                            attribute Izz : Real = 10429.002935383673;
                            attribute sigma_Izz : Real = 7595.686558644344;
                            attribute Ixy : Real = -1674.466341158297;
                            attribute sigma_Ixy : Real = 3260.1982548474434;
                            attribute Ixz : Real = -962.1147864179056;
                            attribute sigma_Ixz : Real = 2506.4471540997324;
                            attribute Iyz : Real = -9349.076594242548;
                            attribute sigma_Iyz : Real = 4517.731239464954;
                            part <'C.1.2.3.1.5.1.1'> 'Part 1061' {
                                attribute POIconv : String = "-";
                                attribute Ipoint : Boolean = false;
                                attribute mass : Real = 0.13081390101742;
                                attribute sigma_mass : Real = 0.28909372274994966;
                                attribute Cx : Real = -19.102863036096096;
                                attribute sigma_Cx : Real = 28.721044428837228;
                                attribute Cy : Real = -94.51505299657583;
                                attribute sigma_Cy : Real = 28.23690002309109;
                                attribute Cz : Real = -30.995140364393592;
                                attribute sigma_Cz : Real = 29.057750463592832;
                                attribute Ixx : Real = 0.17326094199496697;
                                attribute sigma_Ixx : Real = 0.37074144170588635;
                                attribute Iyy : Real = 0.18656678027267268;
                                attribute sigma_Iyy : Real = 0.3723953238821935;
                                attribute Izz : Real = 0.18495806080878255;
                                attribute sigma_Izz : Real = 0.37017423652493897;
                                attribute Ixy : Real = -0.002505082775948407;
                                attribute sigma_Ixy : Real = 0.02351283871158888;
                                attribute Ixz : Real = -0.005244796713303929;
                                attribute sigma_Ixz : Real = 0.022566176940390956;
                                attribute Iyz : Real = -0.0004939127134549158;
                                attribute sigma_Iyz : Real = 0.02209918015384651;
                            }
                            part <'C.1.2.3.1.5.1.2'> 'Part 1062' {
                                attribute POIconv : String = "-";
                                attribute Ipoint : Boolean = false;
                                attribute mass : Real = 0.5286573092150502;
                                attribute sigma_mass : Real = 0.28909372274994966;
                                attribute Cx : Real = 47.875435557216406;
                                attribute sigma_Cx : Real = 28.721044428837228;
                                attribute Cy : Real = -52.51263650134206;
                                attribute sigma_Cy : Real = 28.23690002309109;
                                attribute Cz : Real = -91.2951922044158;
                                attribute sigma_Cz : Real = 29.057750463592832;
                                attribute Ixx : Real = 0.6986659873372394;
                                attribute sigma_Ixx : Real = 0.37074144170588635;
                                attribute Iyy : Real = 0.7396714403046946;
                                attribute sigma_Iyy : Real = 0.3723953238821935;
                                attribute Izz : Real = 0.674014184708664;
                                attribute sigma_Izz : Real = 0.37017423652493897;
                                attribute Ixy : Real = -0.04783515283733443;
                                attribute sigma_Ixy : Real = 0.02351283871158888;
                                attribute Ixz : Real = 0.02057330101918691;
                                attribute sigma_Ixz : Real = 0.022566176940390956;
                                attribute Iyz : Real = -0.01870429998461142;
                                attribute sigma_Iyz : Real = 0.02209918015384651;
                            }
                            part <'C.1.2.3.1.5.1.3'> 'Part 1063' {
                                attribute POIconv : String = "+";
                                attribute Ipoint : Boolean = false;
                                attribute mass : Real = 0.85717995661241;
                                attribute sigma_mass : Real = 0.28909372274994966;
                                attribute Cx : Real = 57.68434344790876;
                                attribute sigma_Cx : Real = 28.721044428837228;
                                attribute Cy : Real = 99.41592700779438;
                                attribute sigma_Cy : Real = 28.23690002309109;
                                attribute Cz : Real = 81.6272471100092;
                                attribute sigma_Cz : Real = 29.057750463592832;
                                attribute Ixx : Real = 1.182030803572393;
                                attribute sigma_Ixx : Real = 0.37074144170588635;
                                attribute Iyy : Real = 1.1502833640526458;
                                attribute sigma_Iyy : Real = 0.3723953238821935;
                                attribute Izz : Real = 1.2221753209991009;
                                attribute sigma_Izz : Real = 0.37017423652493897;
                                attribute Ixy : Real = -0.10069200301187747;
                                attribute sigma_Ixy : Real = 0.02351283871158888;
                                attribute Ixz : Real = 0.12211406421555307;
                                attribute sigma_Ixz : Real = 0.022566176940390956;
                                attribute Iyz : Real = 0.10060626178265794;
                                attribute sigma_Iyz : Real = 0.02209918015384651;
                            }
                        }
                        part <'C.1.2.3.1.5.2'> 'Subassembly 301' {
                            attribute POIconv : String = "-";
                            attribute Ipoint : Boolean = false;
                            attribute mass : Real = 3.323552264295053;
                            attribute sigma_mass : Real = 0.6464332159373649;
                            attribute Cx : Real = -26.522298617745456;
                            attribute sigma_Cx : Real = 19.626943296681585;
                            attribute Cy : Real = -29.90440648000507;
                            attribute sigma_Cy : Real = 15.444711011335377;
                            attribute Cz : Real = -4.2944243787254495;
                            attribute sigma_Cz : Real = 17.523462361309903;
                            attribute Ixx : Real = 13883.372667421143;
                            attribute sigma_Ixx : Real = 6976.268291556007;
                            attribute Iyy : Real = 20545.0522780701;
                            attribute sigma_Iyy : Real = 9092.802760000413;
                            attribute Izz : Real = 16189.648537354027;
                            attribute sigma_Izz : Real = 7906.770204155671;
                            attribute Ixy : Real = -473.12695235141035;
                            attribute sigma_Ixy : Real = 3329.0356917729405;
                            attribute Ixz : Real = 1948.113844315621;
                            attribute sigma_Ixz : Real = 4039.3231068815353;
                            attribute Iyz : Real = -5865.883195908988;
                            attribute sigma_Iyz : Real = 3398.2792791643933;
                            part <'C.1.2.3.1.5.2.1'> 'Part 1064' {
                                attribute POIconv : String = "+";
                                attribute Ipoint : Boolean = false;
                                attribute mass : Real = 0.08062984849116765;
                                attribute sigma_mass : Real = 0.28909372274994966;
                                attribute Cx : Real = 79.90733310580254;
                                attribute sigma_Cx : Real = 28.721044428837228;
                                attribute Cy : Real = -52.6643521618098;
                                attribute sigma_Cy : Real = 28.23690002309109;
                                attribute Cz : Real = 46.963507775217295;
                                attribute sigma_Cz : Real = 29.057750463592832;
                                attribute Ixx : Real = 0.10656009206662402;
                                attribute sigma_Ixx : Real = 0.37074144170588635;
                                attribute Iyy : Real = 0.10668314444170682;
                                attribute sigma_Iyy : Real = 0.3723953238821935;
                                attribute Izz : Real = 0.11445963451343098;
                                attribute sigma_Izz : Real = 0.37017423652493897;
                                attribute Ixy : Real = 0.0005375566486369059;
                                attribute sigma_Ixy : Real = 0.02351283871158888;
                                attribute Ixz : Real = -0.00035912182300382655;
                                attribute sigma_Ixz : Real = 0.022566176940390956;
                                attribute Iyz : Real = 7.922446231387598e-05;
                                attribute sigma_Iyz : Real = 0.02209918015384651;
                            }
                            part <'C.1.2.3.1.5.2.2'> 'Part 1065' {
                                attribute POIconv : String = "-";
                                attribute Ipoint : Boolean = false;
                                attribute mass : Real = 0.8785589387393556;
                                attribute sigma_mass : Real = 0.28909372274994966;
                                attribute Cx : Real = -50.994906621053815;
                                attribute sigma_Cx : Real = 28.721044428837228;
                                attribute Cy : Real = 28.659749450162053;
                                attribute sigma_Cy : Real = 28.23690002309109;
                                attribute Cz : Real = 73.88611100614071;
                                attribute sigma_Cz : Real = 29.057750463592832;
                                attribute Ixx : Real = 1.0484490431043456;
                                attribute sigma_Ixx : Real = 0.37074144170588635;
                                attribute Iyy : Real = 0.9742583079671037;
                                attribute sigma_Iyy : Real = 0.3723953238821935;
                                attribute Izz : Real = 1.0068877350171561;
                                attribute sigma_Izz : Real = 0.37017423652493897;
                                attribute Ixy : Real = -0.024455286571313004;
                                attribute sigma_Ixy : Real = 0.02351283871158888;
                                attribute Ixz : Real = -0.06737624668913994;
                                attribute sigma_Ixz : Real = 0.022566176940390956;
                                attribute Iyz : Real = -0.0021416849567374055;
                                attribute sigma_Iyz : Real = 0.02209918015384651;
                            }
                            part <'C.1.2.3.1.5.2.3'> 'Part 1066' {
                                attribute POIconv : String = "+";
                                attribute Ipoint : Boolean = false;
                                attribute mass : Real = 0.7310225569473114;
                                attribute sigma_mass : Real = 0.28909372274994966;
                                attribute Cx : Real = 67.07863849587739;
                                attribute sigma_Cx : Real = 28.721044428837228;
                                attribute Cy : Real = -25.98369112238288;
                                attribute sigma_Cy : Real = 28.23690002309109;
                                attribute Cz : Real = -23.45006908290088;
                                attribute sigma_Cz : Real = 29.057750463592832;
                                attribute Ixx : Real = 1.109147505274529;
                                attribute sigma_Ixx : Real = 0.37074144170588635;
                                attribute Iyy : Real = 1.0759648119965606;
                                attribute sigma_Iyy : Real = 0.3723953238821935;
                                attribute Izz : Real = 1.103281754436055;
                                attribute sigma_Izz : Real = 0.37017423652493897;
                                attribute Ixy : Real = 0.01570963527677722;
                                attribute sigma_Ixy : Real = 0.02351283871158888;
                                attribute Ixz : Real = 0.0066060770728070504;
                                attribute sigma_Ixz : Real = 0.022566176940390956;
                                attribute Iyz : Real = 0.025445873328981;
                                attribute sigma_Iyz : Real = 0.02209918015384651;
                            }
                            part <'C.1.2.3.1.5.2.4'> 'Part 1067' {
                                attribute POIconv : String = "-";
                                attribute Ipoint : Boolean = false;
                                attribute mass : Real = 0.9189796810848638;
                                attribute sigma_mass : Real = 0.28909372274994966;
                                attribute Cx : Real = -88.89390137046576;
                                attribute sigma_Cx : Real = 28.721044428837228;
                                attribute Cy : Real = -59.95402755215764;
                                attribute sigma_Cy : Real = 28.23690002309109;
                                attribute Cz : Real = -16.915352595970035;
                                attribute sigma_Cz : Real = 29.057750463592832;
                                attribute Ixx : Real = 1.0891428888523997;
                                attribute sigma_Ixx : Real = 0.37074144170588635;
                                attribute Iyy : Real = 0.9480638612162594;
                                attribute sigma_Iyy : Real = 0.3723953238821935;
                                attribute Izz : Real = 1.0896619427952465;
                                attribute sigma_Izz : Real = 0.37017423652493897;
                                attribute Ixy : Real = -0.016774989020531705;
                                attribute sigma_Ixy : Real = 0.02351283871158888;
                                attribute Ixz : Real = -0.03668470294928386;
                                attribute sigma_Ixz : Real = 0.022566176940390956;
                                attribute Iyz : Real = -0.028651109157971887;
                                attribute sigma_Iyz : Real = 0.02209918015384651;
                            }
                            part <'C.1.2.3.1.5.2.5'> 'Part 1068' {
                                attribute POIconv : String = "+";
                                attribute Ipoint : Boolean = false;
                                attribute mass : Real = 0.7143612390323542;
                                attribute sigma_mass : Real = 0.28909372274994966;
                                attribute Cx : Real = -23.984279250726104;
                                attribute sigma_Cx : Real = 28.721044428837228;
                                attribute Cy : Real = -64.71602632664144;
                                attribute sigma_Cy : Real = 28.23690002309109;
                                attribute Cz : Real = -70.3919951338321;
                                attribute sigma_Cz : Real = 29.057750463592832;
                                attribute Ixx : Real = 0.8930441663136031;
                                attribute sigma_Ixx : Real = 0.37074144170588635;
                                attribute Iyy : Real = 0.8785900304424367;
                                attribute sigma_Iyy : Real = 0.3723953238821935;
                                attribute Izz : Real = 0.8533034238540819;
                                attribute sigma_Izz : Real = 0.37017423652493897;
                                attribute Ixy : Real = -0.00024477902432202734;
                                attribute sigma_Ixy : Real = 0.02351283871158888;
                                attribute Ixz : Real = -0.015456694583625643;
                                attribute sigma_Ixz : Real = 0.022566176940390956;
                                attribute Iyz : Real = -0.0012787325076341707;
                                attribute sigma_Iyz : Real = 0.02209918015384651;
                            }
                        }
                        part <'C.1.2.3.1.5.3'> 'Subassembly 302' {
                            attribute POIconv : String = "-";
                            attribute Ipoint : Boolean = false;
                            attribute mass : Real = 2.9458899530763736;
                            attribute sigma_mass : Real = 0.5781874454998993;
                            attribute Cx : Real = -25.687980129148148;
                            attribute sigma_Cx : Real = 17.450092125673525;
                            attribute Cy : Real = 38.78120252903625;
                            attribute sigma_Cy : Real = 17.736830377204235;
                            attribute Cz : Real = -31.428348049454687;
                            attribute sigma_Cz : Real = 18.740923712490787;
                            attribute Ixx : Real = 15743.103051703674;
                            attribute sigma_Ixx : Real = 7124.458576029563;
                            attribute Iyy : Real = 14567.886264078672;
                            attribute sigma_Iyy : Real = 6855.73070089657;
                            attribute Izz : Real = 12545.951297595931;
                            attribute sigma_Izz : Real = 6283.320079175687;
                            attribute Ixy : Real = 3793.190540975267;
                            attribute sigma_Ixy : Real = 3131.6428903929864;
                            attribute Ixz : Real = 5854.490879895387;
                            attribute sigma_Ixz : Real = 3351.8851862855545;
                            attribute Iyz : Real = -1733.5372867708757;
                            attribute sigma_Iyz : Real = 3525.444732399379;
                            part <'C.1.2.3.1.5.3.1'> 'Part 1069' {
                                attribute POIconv : String = "-";
                                attribute Ipoint : Boolean = false;
                                attribute mass : Real = 0.8673915939605795;
                                attribute sigma_mass : Real = 0.28909372274994966;
                                attribute Cx : Real = -65.39055369794369;
                                attribute sigma_Cx : Real = 28.721044428837228;
                                attribute Cy : Real = 81.82338951155543;
                                attribute sigma_Cy : Real = 28.23690002309109;
                                attribute Cz : Real = 29.988151090219617;
                                attribute sigma_Cz : Real = 29.057750463592832;
                                attribute Ixx : Real = 1.034835911520058;
                                attribute sigma_Ixx : Real = 0.37074144170588635;
                                attribute Iyy : Real = 1.0146309044037214;
                                attribute sigma_Iyy : Real = 0.3723953238821935;
                                attribute Izz : Real = 1.0737685711147267;
                                attribute sigma_Izz : Real = 0.37017423652493897;
                                attribute Ixy : Real = 0.043130757775615654;
                                attribute sigma_Ixy : Real = 0.02351283871158888;
                                attribute Ixz : Real = 0.009992808796341953;
                                attribute sigma_Ixz : Real = 0.022566176940390956;
                                attribute Iyz : Real = -0.0029229533229066956;
                                attribute sigma_Iyz : Real = 0.02209918015384651;
                            }
                            part <'C.1.2.3.1.5.3.2'> 'Part 1070' {
                                attribute POIconv : String = "-";
                                attribute Ipoint : Boolean = false;
                                attribute mass : Real = 0.9694585117974784;
                                attribute sigma_mass : Real = 0.28909372274994966;
                                attribute Cx : Real = -24.787927605211735;
                                attribute sigma_Cx : Real = 28.721044428837228;
                                attribute Cy : Real = 70.91575739905238;
                                attribute sigma_Cy : Real = 28.23690002309109;
                                attribute Cz : Real = -76.74522497691214;
                                attribute sigma_Cz : Real = 29.057750463592832;
                                attribute Ixx : Real = 1.2813553158196134;
                                attribute sigma_Ixx : Real = 0.37074144170588635;
                                attribute Iyy : Real = 1.5410880811154988;
                                attribute sigma_Iyy : Real = 0.3723953238821935;
                                attribute Izz : Real = 1.334614558718345;
                                attribute sigma_Izz : Real = 0.37017423652493897;
                                attribute Ixy : Real = -0.0017469691574664215;
                                attribute sigma_Ixy : Real = 0.02351283871158888;
                                attribute Ixz : Real = -0.007961963272010188;
                                attribute sigma_Ixz : Real = 0.022566176940390956;
                                attribute Iyz : Real = 0.09502671921962388;
                                attribute sigma_Iyz : Real = 0.02209918015384651;
                            }
                            part <'C.1.2.3.1.5.3.3'> 'Part 1071' {
                                attribute POIconv : String = "+";
                                attribute Ipoint : Boolean = false;
                                attribute mass : Real = 0.6972554392570164;
                                attribute sigma_mass : Real = 0.28909372274994966;
                                attribute Cx : Real = 46.49368082173169;
                                attribute sigma_Cx : Real = 28.721044428837228;
                                attribute Cy : Real = -26.354542141780257;
                                attribute sigma_Cy : Real = 28.23690002309109;
                                attribute Cz : Real = -83.26301476918161;
                                attribute sigma_Cz : Real = 29.057750463592832;
                                attribute Ixx : Real = 0.8135661893211564;
                                attribute sigma_Ixx : Real = 0.37074144170588635;
                                attribute Iyy : Real = 0.9014552009155617;
                                attribute sigma_Iyy : Real = 0.3723953238821935;
                                attribute Izz : Real = 0.9240257779140032;
                                attribute sigma_Izz : Real = 0.37017423652493897;
                                attribute Ixy : Real = 0.05302263147365869;
                                attribute sigma_Ixy : Real = 0.02351283871158888;
                                attribute Ixz : Real = 0.03037337300464587;
                                attribute sigma_Ixz : Real = 0.022566176940390956;
                                attribute Iyz : Real = 0.0022654829686027055;
                                attribute sigma_Iyz : Real = 0.02209918015384651;
                            }
                            part <'C.1.2.3.1.5.3.4'> 'Part 1072' {
                                attribute POIconv : String = "-";
                                attribute Ipoint : Boolean = false;
                                attribute mass : Real = 0.41178440806129946;
                                attribute sigma_mass : Real = 0.28909372274994966;
                                attribute Cx : Real = -66.39845967292786;
                                attribute sigma_Cx : Real = 28.721044428837228;
                                attribute Cy : Real = -17.246408527716994;
                                attribute sigma_Cy : Real = 28.23690002309109;
                                attribute Cz : Real = 33.660761127248406;
                                attribute sigma_Cz : Real = 29.057750463592832;
                                attribute Ixx : Real = 0.41581779812420794;
                                attribute sigma_Ixx : Real = 0.37074144170588635;
                                attribute Iyy : Real = 0.41707775514054957;
                                attribute sigma_Iyy : Real = 0.3723953238821935;
                                attribute Izz : Real = 0.36798170276345094;
                                attribute sigma_Izz : Real = 0.37017423652493897;
                                attribute Ixy : Real = -0.008350212227890258;
                                attribute sigma_Ixy : Real = 0.02351283871158888;
                                attribute Ixz : Real = -0.004087352846995563;
                                attribute sigma_Ixz : Real = 0.022566176940390956;
                                attribute Iyz : Real = 0.007085325112769063;
                                attribute sigma_Iyz : Real = 0.02209918015384651;
                            }
                        }
                        part <'C.1.2.3.1.5.4'> 'Subassembly 303' {
                            attribute POIconv : String = "-";
                            attribute Ipoint : Boolean = false;
                            attribute mass : Real = 0.6345425742801745;
                            attribute sigma_mass : Real = 0.40884026350990615;
                            attribute Cx : Real = 53.6254724162189;
                            attribute sigma_Cx : Real = 33.28849558753054;
                            attribute Cy : Real = -40.780781582795065;
                            attribute sigma_Cy : Real = 21.497608042560547;
                            attribute Cz : Real = 51.07503362790288;
                            attribute sigma_Cz : Real = 28.90153427148598;
                            attribute Ixx : Real = 700.3279173502491;
                            attribute sigma_Ixx : Real = 978.5192713370357;
                            attribute Iyy : Real = 1645.7394446130345;
                            attribute sigma_Iyy : Real = 1714.9899083366577;
                            attribute Izz : Real = 1123.1447236559643;
                            attribute sigma_Izz : Real = 1314.723118748869;
                            attribute Ixy : Real = 302.4820588641793;
                            attribute sigma_Ixy : Real = 568.3059281192562;
                            attribute Ixz : Real = 794.8910551820111;
                            attribute sigma_Ixz : Real = 847.1626619348547;
                            attribute Iyz : Real = -232.57297028282315;
                            attribute sigma_Iyz : Real = 448.11576251825727;
                            part <'C.1.2.3.1.5.4.1'> 'Part 1073' {
                                attribute POIconv : String = "+";
                                attribute Ipoint : Boolean = false;
                                attribute mass : Real = 0.2842550932301674;
                                attribute sigma_mass : Real = 0.28909372274994966;
                                attribute Cx : Real = 98.43460656702518;
                                attribute sigma_Cx : Real = 28.721044428837228;
                                attribute Cy : Real = -53.890949906781316;
                                attribute sigma_Cy : Real = 28.23690002309109;
                                attribute Cz : Real = 16.625373950228095;
                                attribute sigma_Cz : Real = 29.057750463592832;
                                attribute Ixx : Real = 0.36011565782792765;
                                attribute sigma_Ixx : Real = 0.37074144170588635;
                                attribute Iyy : Real = 0.3721605664139445;
                                attribute sigma_Iyy : Real = 0.3723953238821935;
                                attribute Izz : Real = 0.36010709330218926;
                                attribute sigma_Izz : Real = 0.37017423652493897;
                                attribute Ixy : Real = 0.010117331774858546;
                                attribute sigma_Ixy : Real = 0.02351283871158888;
                                attribute Ixz : Real = -0.004505712659662552;
                                attribute sigma_Ixz : Real = 0.022566176940390956;
                                attribute Iyz : Real = 0.014886826239469745;
                                attribute sigma_Iyz : Real = 0.02209918015384651;
                            }
                            part <'C.1.2.3.1.5.4.2'> 'Part 1074' {
                                attribute POIconv : String = "-";
                                attribute Ipoint : Boolean = false;
                                attribute mass : Real = 0.35028748105000707;
                                attribute sigma_mass : Real = 0.28909372274994966;
                                attribute Cx : Real = 17.263269098475575;
                                attribute sigma_Cx : Real = 28.721044428837228;
                                attribute Cy : Real = -30.141999665647745;
                                attribute sigma_Cy : Real = 28.23690002309109;
                                attribute Cz : Real = 79.03061797842383;
                                attribute sigma_Cz : Real = 29.057750463592832;
                                attribute Ixx : Real = 0.36139648477900693;
                                attribute sigma_Ixx : Real = 0.37074144170588635;
                                attribute Iyy : Real = 0.3669227309060699;
                                attribute sigma_Iyy : Real = 0.3723953238821935;
                                attribute Izz : Real = 0.3834589229076559;
                                attribute sigma_Izz : Real = 0.37017423652493897;
                                attribute Ixy : Real = -0.0035371725947279534;
                                attribute sigma_Ixy : Real = 0.02351283871158888;
                                attribute Ixz : Real = 0.016939714911895595;
                                attribute sigma_Ixz : Real = 0.022566176940390956;
                                attribute Iyz : Real = 0.0033033452734507317;
                                attribute sigma_Iyz : Real = 0.02209918015384651;
                            }
                        }
                    }
                }
                part <'C.1.2.3.2'> 'Subsystem 24' {
                    attribute POIconv : String = "-";
                    attribute Ipoint : Boolean = false;
                    attribute mass : Real = 21.384639824985292;
                    attribute sigma_mass : Real = 2.0029000638085734;
                    attribute Cx : Real = 16.895433451220494;
                    attribute sigma_Cx : Real = 7.442562676358299;
                    attribute Cy : Real = 4.600236735059287;
                    attribute sigma_Cy : Real = 7.696115902943146;
                    attribute Cz : Real = 11.48282105315963;
                    attribute sigma_Cz : Real = 7.720746033251516;
                    attribute Ixx : Real = 143133.25911007557;
                    attribute sigma_Ixx : Real = 26652.38655432351;
                    attribute Iyy : Real = 136187.50810618675;
                    attribute sigma_Iyy : Real = 24291.580957349957;
                    attribute Izz : Real = 134092.12364780702;
                    attribute sigma_Izz : Real = 24299.118226334616;
                    attribute Ixy : Real = 26428.45432548998;
                    attribute sigma_Ixy : Real = 11353.199621459155;
                    attribute Ixz : Real = 2990.080596037226;
                    attribute sigma_Ixz : Real = 11029.003445046545;
                    attribute Iyz : Real = -1551.1683500525207;
                    attribute sigma_Iyz : Real = 12249.270506656392;
                    part <'C.1.2.3.2.1'> 'Assembly 88' {
                        attribute POIconv : String = "-";
                        attribute Ipoint : Boolean = false;
                        attribute mass : Real = 2.4673902517026294;
                        attribute sigma_mass : Real = 0.7648700959862226;
                        attribute Cx : Real = 49.98848702994774;
                        attribute sigma_Cx : Real = 20.211143185456727;
                        attribute Cy : Real = -12.68254496520438;
                        attribute sigma_Cy : Real = 22.91036533541961;
                        attribute Cz : Real = 43.5204437416958;
                        attribute sigma_Cz : Real = 22.415734211155733;
                        attribute Ixx : Real = 14477.132237385178;
                        attribute sigma_Ixx : Real = 8088.238199979074;
                        attribute Iyy : Real = 11454.89734210526;
                        attribute sigma_Iyy : Real = 6421.828886538976;
                        attribute Izz : Real = 14586.09754496317;
                        attribute sigma_Izz : Real = 7882.297010335752;
                        attribute Ixy : Real = 5950.572329698587;
                        attribute sigma_Ixy : Real = 3750.1672730933387;
                        attribute Ixz : Real = -427.3148480057531;
                        attribute sigma_Ixz : Real = 3009.297375295248;
                        attribute Iyz : Real = 1733.281458687253;
                        attribute sigma_Iyz : Real = 3904.076705018855;
                        part <'C.1.2.3.2.1.1'> 'Subassembly 304' {
                            attribute POIconv : String = "-";
                            attribute Ipoint : Boolean = false;
                            attribute mass : Real = 1.0475805618728047;
                            attribute sigma_mass : Real = 0.5781874454998993;
                            attribute Cx : Real = 65.88000558610939;
                            attribute sigma_Cx : Real = 31.12928051504883;
                            attribute Cy : Real = -2.2490121615232685;
                            attribute sigma_Cy : Real = 35.9661517155797;
                            attribute Cz : Real = -0.07456891737239398;
                            attribute sigma_Cz : Real = 32.30862811702768;
                            attribute Ixx : Real = 2428.9133778866567;
                            attribute sigma_Ixx : Real = 5019.227552054465;
                            attribute Iyy : Real = 2257.665290206323;
                            attribute sigma_Iyy : Real = 3287.39230961031;
                            attribute Izz : Real = 2064.6870005348133;
                            attribute sigma_Izz : Real = 4277.285645408726;
                            attribute Ixy : Real = 555.669165411801;
                            attribute sigma_Ixy : Real = 1813.337731195498;
                            attribute Ixz : Real = -178.66551602957398;
                            attribute sigma_Ixz : Real = 1472.5293923124927;
                            attribute Iyz : Real = -899.7924213818137;
                            attribute sigma_Iyz : Real = 2408.7908295562374;
                            part <'C.1.2.3.2.1.1.1'> 'Part 1075' {
                                attribute POIconv : String = "-";
                                attribute Ipoint : Boolean = false;
                                attribute mass : Real = 0.09316603884263895;
                                attribute sigma_mass : Real = 0.28909372274994966;
                                attribute Cx : Real = 12.60268916375935;
                                attribute sigma_Cx : Real = 28.721044428837228;
                                attribute Cy : Real = 99.58324069157243;
                                attribute sigma_Cy : Real = 28.23690002309109;
                                attribute Cz : Real = 78.88803649693727;
                                attribute sigma_Cz : Real = 29.057750463592832;
                                attribute Ixx : Real = 0.09066852039309423;
                                attribute sigma_Ixx : Real = 0.37074144170588635;
                                attribute Iyy : Real = 0.08644172903608323;
                                attribute sigma_Iyy : Real = 0.3723953238821935;
                                attribute Izz : Real = 0.09541729913191384;
                                attribute sigma_Izz : Real = 0.37017423652493897;
                                attribute Ixy : Real = 0.007200924428477702;
                                attribute sigma_Ixy : Real = 0.02351283871158888;
                                attribute Ixz : Real = 0.0020119762557935204;
                                attribute sigma_Ixz : Real = 0.022566176940390956;
                                attribute Iyz : Real = -0.0038258231022511666;
                                attribute sigma_Iyz : Real = 0.02209918015384651;
                            }
                            part <'C.1.2.3.2.1.1.2'> 'Part 1076' {
                                attribute POIconv : String = "+";
                                attribute Ipoint : Boolean = false;
                                attribute mass : Real = 0.2929952875059098;
                                attribute sigma_mass : Real = 0.28909372274994966;
                                attribute Cx : Real = 35.99120490252972;
                                attribute sigma_Cx : Real = 28.721044428837228;
                                attribute Cy : Real = -17.41807605139911;
                                attribute sigma_Cy : Real = 28.23690002309109;
                                attribute Cz : Real = -47.60262714698911;
                                attribute sigma_Cz : Real = 29.057750463592832;
                                attribute Ixx : Real = 0.3111176327232721;
                                attribute sigma_Ixx : Real = 0.37074144170588635;
                                attribute Iyy : Real = 0.3095046432194984;
                                attribute sigma_Iyy : Real = 0.3723953238821935;
                                attribute Izz : Real = 0.31368155305549866;
                                attribute sigma_Izz : Real = 0.37017423652493897;
                                attribute Ixy : Real = 0.0012294486106757575;
                                attribute sigma_Ixy : Real = 0.02351283871158888;
                                attribute Ixz : Real = -0.0003635390425681407;
                                attribute sigma_Ixz : Real = 0.022566176940390956;
                                attribute Iyz : Real = -0.00316724628804734;
                                attribute sigma_Iyz : Real = 0.02209918015384651;
                            }
                            part <'C.1.2.3.2.1.1.3'> 'Part 1077' {
                                attribute POIconv : String = "+";
                                attribute Ipoint : Boolean = false;
                                attribute mass : Real = 0.020711855444824324;
                                attribute sigma_mass : Real = 0.28909372274994966;
                                attribute Cx : Real = 7.059088023379445;
                                attribute sigma_Cx : Real = 28.721044428837228;
                                attribute Cy : Real = 36.22960192151368;
                                attribute sigma_Cy : Real = 28.23690002309109;
                                attribute Cz : Real = -0.7960488088428974;
                                attribute sigma_Cz : Real = 29.057750463592832;
                                attribute Ixx : Real = 0.03211247631308151;
                                attribute sigma_Ixx : Real = 0.37074144170588635;
                                attribute Iyy : Real = 0.03170252760446786;
                                attribute sigma_Iyy : Real = 0.3723953238821935;
                                attribute Izz : Real = 0.03201935618477567;
                                attribute sigma_Izz : Real = 0.37017423652493897;
                                attribute Ixy : Real = 0.0006483174484189957;
                                attribute sigma_Ixy : Real = 0.02351283871158888;
                                attribute Ixz : Real = -0.00031159791406084274;
                                attribute sigma_Ixz : Real = 0.022566176940390956;
                                attribute Iyz : Real = -0.00014705000092052589;
                                attribute sigma_Iyz : Real = 0.02209918015384651;
                            }
                            part <'C.1.2.3.2.1.1.4'> 'Part 1078' {
                                attribute POIconv : String = "-";
                                attribute Ipoint : Boolean = false;
                                attribute mass : Real = 0.6407073800794315;
                                attribute sigma_mass : Real = 0.28909372274994966;
                                attribute Cx : Real = 89.19674125500023;
                                attribute sigma_Cx : Real = 28.721044428837228;
                                attribute Cy : Real = -11.363636190071702;
                                attribute sigma_Cy : Real = 28.23690002309109;
                                attribute Cz : Real = 10.201271995902061;
                                attribute sigma_Cz : Real = 29.057750463592832;
                                attribute Ixx : Real = 0.6378199053512029;
                                attribute sigma_Ixx : Real = 0.37074144170588635;
                                attribute Iyy : Real = 0.633743329509938;
                                attribute sigma_Iyy : Real = 0.3723953238821935;
                                attribute Izz : Real = 0.6317123394183661;
                                attribute sigma_Izz : Real = 0.37017423652493897;
                                attribute Ixy : Real = 0.001900299222432658;
                                attribute sigma_Ixy : Real = 0.02351283871158888;
                                attribute Ixz : Real = -0.0016071137086057386;
                                attribute sigma_Ixz : Real = 0.022566176940390956;
                                attribute Iyz : Real = 0.003453936252889564;
                                attribute sigma_Iyz : Real = 0.02209918015384651;
                            }
                        }
                        part <'C.1.2.3.2.1.2'> 'Subassembly 305' {
                            attribute POIconv : String = "-";
                            attribute Ipoint : Boolean = false;
                            attribute mass : Real = 1.4198096898298247;
                            attribute sigma_mass : Real = 0.5007250159521434;
                            attribute Cx : Real = 38.26322127262553;
                            attribute sigma_Cx : Real = 25.439111339917062;
                            attribute Cy : Real = -20.380735951708097;
                            attribute sigma_Cy : Real = 29.249772057902153;
                            attribute Cz : Real = 75.68622496108762;
                            attribute sigma_Cz : Real = 22.479982507757285;
                            attribute Ixx : Real = 8390.098228254825;
                            attribute sigma_Ixx : Real = 4962.422809705312;
                            attribute Iyy : Real = 5277.536100847292;
                            attribute sigma_Iyy : Real = 3717.8703054125554;
                            attribute Izz : Real = 11863.476969838128;
                            attribute sigma_Izz : Real = 6400.268595667162;
                            attribute Ixy : Real = 5696.7536821927715;
                            attribute sigma_Ixy : Real = 3158.4233429964543;
                            attribute Ixz : Real = -1509.8882044523311;
                            attribute sigma_Ixz : Real = 1700.3589506806252;
                            attribute Iyz : Real = 1805.0109669653045;
                            attribute sigma_Iyz : Real = 2165.0776390515653;
                            part <'C.1.2.3.2.1.2.1'> 'Part 1079' {
                                attribute POIconv : String = "-";
                                attribute Ipoint : Boolean = false;
                                attribute mass : Real = 0.736369208443677;
                                attribute sigma_mass : Real = 0.28909372274994966;
                                attribute Cx : Real = 89.08713683485985;
                                attribute sigma_Cx : Real = 28.721044428837228;
                                attribute Cy : Real = -84.48967160657048;
                                attribute sigma_Cy : Real = 28.23690002309109;
                                attribute Cz : Real = 98.127674870193;
                                attribute sigma_Cz : Real = 29.057750463592832;
                                attribute Ixx : Real = 0.9074281887474119;
                                attribute sigma_Ixx : Real = 0.37074144170588635;
                                attribute Iyy : Real = 1.1312562714610315;
                                attribute sigma_Iyy : Real = 0.3723953238821935;
                                attribute Izz : Real = 0.8903214997645635;
                                attribute sigma_Izz : Real = 0.37017423652493897;
                                attribute Ixy : Real = -0.013089116061488274;
                                attribute sigma_Ixy : Real = 0.02351283871158888;
                                attribute Ixz : Real = -0.0454508459241012;
                                attribute sigma_Ixz : Real = 0.022566176940390956;
                                attribute Iyz : Real = -0.0175540541806187;
                                attribute sigma_Iyz : Real = 0.02209918015384651;
                            }
                            part <'C.1.2.3.2.1.2.2'> 'Part 1080' {
                                attribute POIconv : String = "-";
                                attribute Ipoint : Boolean = false;
                                attribute mass : Real = 0.136034482173156;
                                attribute sigma_mass : Real = 0.28909372274994966;
                                attribute Cx : Real = 33.401367627084255;
                                attribute sigma_Cx : Real = 28.721044428837228;
                                attribute Cy : Real = -35.36435957066715;
                                attribute sigma_Cy : Real = 28.23690002309109;
                                attribute Cz : Real = 23.781332932412624;
                                attribute sigma_Cz : Real = 29.057750463592832;
                                attribute Ixx : Real = 0.1898722227295391;
                                attribute sigma_Ixx : Real = 0.37074144170588635;
                                attribute Iyy : Real = 0.19031328235873918;
                                attribute sigma_Iyy : Real = 0.3723953238821935;
                                attribute Izz : Real = 0.1937970315547518;
                                attribute sigma_Izz : Real = 0.37017423652493897;
                                attribute Ixy : Real = 5.706782241701358e-05;
                                attribute sigma_Ixy : Real = 0.02351283871158888;
                                attribute Ixz : Real = -0.010390161027714846;
                                attribute sigma_Ixz : Real = 0.022566176940390956;
                                attribute Iyz : Real = 0.004074095579415841;
                                attribute sigma_Iyz : Real = 0.02209918015384651;
                            }
                            part <'C.1.2.3.2.1.2.3'> 'Part 1081' {
                                attribute POIconv : String = "-";
                                attribute Ipoint : Boolean = false;
                                attribute mass : Real = 0.5474059992129915;
                                attribute sigma_mass : Real = 0.28909372274994966;
                                attribute Cx : Real = -28.896778402850032;
                                attribute sigma_Cx : Real = 28.721044428837228;
                                attribute Cy : Real = 69.58198961801827;
                                attribute sigma_Cy : Real = 28.23690002309109;
                                attribute Cz : Real = 58.396795159205794;
                                attribute sigma_Cz : Real = 29.057750463592832;
                                attribute Ixx : Real = 0.7233941636655403;
                                attribute sigma_Ixx : Real = 0.37074144170588635;
                                attribute Iyy : Real = 0.8743873254364747;
                                attribute sigma_Iyy : Real = 0.3723953238821935;
                                attribute Izz : Real = 0.7255875116120409;
                                attribute sigma_Izz : Real = 0.37017423652493897;
                                attribute Ixy : Real = 0.018533668099388154;
                                attribute sigma_Ixy : Real = 0.02351283871158888;
                                attribute Ixz : Real = -0.003610646093416209;
                                attribute sigma_Ixz : Real = 0.022566176940390956;
                                attribute Iyz : Real = -0.028479450887521702;
                                attribute sigma_Iyz : Real = 0.02209918015384651;
                            }
                        }
                    }
                    part <'C.1.2.3.2.2'> 'Assembly 89' {
                        attribute POIconv : String = "-";
                        attribute Ipoint : Boolean = false;
                        attribute mass : Real = 4.591247935624095;
                        attribute sigma_mass : Real = 0.867281168249849;
                        attribute Cx : Real = 33.03139114220371;
                        attribute sigma_Cx : Real = 14.840815312293882;
                        attribute Cy : Real = -13.898533611088407;
                        attribute sigma_Cy : Real = 14.162943884268355;
                        attribute Cz : Real = -2.6727487308772657;
                        attribute sigma_Cz : Real = 15.52613903075126;
                        attribute Ixx : Real = 21193.74998796149;
                        attribute sigma_Ixx : Real = 9668.96228538111;
                        attribute Iyy : Real = 26958.344722059614;
                        attribute sigma_Iyy : Real = 10019.166255101207;
                        attribute Izz : Real = 20172.76135605474;
                        attribute sigma_Izz : Real = 9200.885876398255;
                        attribute Ixy : Real = 7995.980559541057;
                        attribute sigma_Ixy : Real = 4391.992516906764;
                        attribute Ixz : Real = 3511.879833106237;
                        attribute sigma_Ixz : Real = 4534.389136472739;
                        attribute Iyz : Real = -2523.101265152156;
                        attribute sigma_Iyz : Real = 4636.150315873076;
                        part <'C.1.2.3.2.2.1'> 'Subassembly 306' {
                            attribute POIconv : String = "-";
                            attribute Ipoint : Boolean = false;
                            attribute mass : Real = 2.4498070401041767;
                            attribute sigma_mass : Real = 0.5781874454998993;
                            attribute Cx : Real = 28.021593657713687;
                            attribute sigma_Cx : Real = 17.181503470153395;
                            attribute Cy : Real = -1.8604852788244537;
                            attribute sigma_Cy : Real = 15.407377909560838;
                            attribute Cz : Real = -1.1755999001044677;
                            attribute sigma_Cz : Real = 19.441879268330794;
                            attribute Ixx : Real = 8069.005672373602;
                            attribute sigma_Ixx : Real = 5000.078423932589;
                            attribute Iyy : Real = 10426.576805612895;
                            attribute sigma_Iyy : Real = 5742.101011157534;
                            attribute Izz : Real = 3107.912157904121;
                            attribute sigma_Izz : Real = 2813.726410199262;
                            attribute Ixy : Real = 525.8318570961915;
                            attribute sigma_Ixy : Real = 1351.5955015517272;
                            attribute Ixz : Real = 3691.5150718421055;
                            attribute sigma_Ixz : Real = 2772.8751663540584;
                            attribute Iyz : Real = -179.3430067662094;
                            attribute sigma_Iyz : Real = 2283.5669072484716;
                            part <'C.1.2.3.2.2.1.1'> 'Part 1082' {
                                attribute POIconv : String = "+";
                                attribute Ipoint : Boolean = false;
                                attribute mass : Real = 0.2667583300252445;
                                attribute sigma_mass : Real = 0.28909372274994966;
                                attribute Cx : Real = 53.04571748711169;
                                attribute sigma_Cx : Real = 28.721044428837228;
                                attribute Cy : Real = 4.3095247354358435;
                                attribute sigma_Cy : Real = 28.23690002309109;
                                attribute Cz : Real = 10.195624688640237;
                                attribute sigma_Cz : Real = 29.057750463592832;
                                attribute Ixx : Real = 0.35496684195529155;
                                attribute sigma_Ixx : Real = 0.37074144170588635;
                                attribute Iyy : Real = 0.3423101052017469;
                                attribute sigma_Iyy : Real = 0.3723953238821935;
                                attribute Izz : Real = 0.32696397213086575;
                                attribute sigma_Izz : Real = 0.37017423652493897;
                                attribute Ixy : Real = 0.02616009064231773;
                                attribute sigma_Ixy : Real = 0.02351283871158888;
                                attribute Ixz : Real = -0.024513321047162917;
                                attribute sigma_Ixz : Real = 0.022566176940390956;
                                attribute Iyz : Real = 0.006453009990542897;
                                attribute sigma_Iyz : Real = 0.02209918015384651;
                            }
                            part <'C.1.2.3.2.2.1.2'> 'Part 1083' {
                                attribute POIconv : String = "-";
                                attribute Ipoint : Boolean = false;
                                attribute mass : Real = 0.7603096472376492;
                                attribute sigma_mass : Real = 0.28909372274994966;
                                attribute Cx : Real = 36.968472227454185;
                                attribute sigma_Cx : Real = 28.721044428837228;
                                attribute Cy : Real = 8.351876493543386;
                                attribute sigma_Cy : Real = 28.23690002309109;
                                attribute Cz : Real = -60.864388290792704;
                                attribute sigma_Cz : Real = 29.057750463592832;
                                attribute Ixx : Real = 0.9683795560205579;
                                attribute sigma_Ixx : Real = 0.37074144170588635;
                                attribute Iyy : Real = 0.683083289070925;
                                attribute sigma_Iyy : Real = 0.3723953238821935;
                                attribute Izz : Real = 0.9531789613066111;
                                attribute sigma_Izz : Real = 0.37017423652493897;
                                attribute Ixy : Real = 0.03052886075915511;
                                attribute sigma_Ixy : Real = 0.02351283871158888;
                                attribute Ixz : Real = -0.0027199163184193553;
                                attribute sigma_Ixz : Real = 0.022566176940390956;
                                attribute Iyz : Real = 0.0030415095379864097;
                                attribute sigma_Iyz : Real = 0.02209918015384651;
                            }
                            part <'C.1.2.3.2.2.1.3'> 'Part 1084' {
                                attribute POIconv : String = "+";
                                attribute Ipoint : Boolean = false;
                                attribute mass : Real = 0.5433033645558171;
                                attribute sigma_mass : Real = 0.28909372274994966;
                                attribute Cx : Real = 70.5368238966912;
                                attribute sigma_Cx : Real = 28.721044428837228;
                                attribute Cy : Real = -24.354524118825793;
                                attribute sigma_Cy : Real = 28.23690002309109;
                                attribute Cz : Real = -36.1916437279433;
                                attribute sigma_Cz : Real = 29.057750463592832;
                                attribute Ixx : Real = 0.7013746708070755;
                                attribute sigma_Ixx : Real = 0.37074144170588635;
                                attribute Iyy : Real = 0.6678097921525751;
                                attribute sigma_Iyy : Real = 0.3723953238821935;
                                attribute Izz : Real = 0.8236997681605733;
                                attribute sigma_Izz : Real = 0.37017423652493897;
                                attribute Ixy : Real = -0.008369130198001673;
                                attribute sigma_Ixy : Real = 0.02351283871158888;
                                attribute Ixz : Real = 0.008652304561179163;
                                attribute sigma_Ixz : Real = 0.022566176940390956;
                                attribute Iyz : Real = -0.0014998593408943365;
                                attribute sigma_Iyz : Real = 0.02209918015384651;
                            }
                            part <'C.1.2.3.2.2.1.4'> 'Part 1085' {
                                attribute POIconv : String = "-";
                                attribute Ipoint : Boolean = false;
                                attribute mass : Real = 0.8794356982854661;
                                attribute sigma_mass : Real = 0.28909372274994966;
                                attribute Cx : Real = -13.569234730675817;
                                attribute sigma_Cx : Real = 28.721044428837228;
                                attribute Cy : Real = 1.335459854453802;
                                attribute sigma_Cy : Real = 28.23690002309109;
                                attribute Cz : Real = 68.61111368052661;
                                attribute sigma_Cz : Real = 29.057750463592832;
                                attribute Ixx : Real = 1.1877927503193577;
                                attribute sigma_Ixx : Real = 0.37074144170588635;
                                attribute Iyy : Real = 1.2278454811245667;
                                attribute sigma_Iyy : Real = 0.3723953238821935;
                                attribute Izz : Real = 1.2778868521919615;
                                attribute sigma_Izz : Real = 0.37017423652493897;
                                attribute Ixy : Real = -0.0037696542450097363;
                                attribute sigma_Ixy : Real = 0.02351283871158888;
                                attribute Ixz : Real = 0.007588528370933295;
                                attribute sigma_Ixz : Real = 0.022566176940390956;
                                attribute Iyz : Real = -0.0035635831397830965;
                                attribute sigma_Iyz : Real = 0.02209918015384651;
                            }
                        }
                        part <'C.1.2.3.2.2.2'> 'Subassembly 307' {
                            attribute POIconv : String = "-";
                            attribute Ipoint : Boolean = false;
                            attribute mass : Real = 2.141440895519918;
                            attribute sigma_mass : Real = 0.6464332159373649;
                            attribute Cx : Real = 38.76259631937023;
                            attribute sigma_Cx : Real = 24.925148941015625;
                            attribute Cy : Real = -27.670053345857703;
                            attribute sigma_Cy : Real = 24.156379606762226;
                            attribute Cz : Real = -4.385486053389477;
                            attribute sigma_Cz : Real = 24.758395863670128;
                            attribute Ixx : Real = 12351.824057357;
                            attribute sigma_Ixx : Real = 8096.674288368533;
                            attribute Iyy : Real = 16388.170209698976;
                            attribute sigma_Iyy : Real = 8173.474201305398;
                            attribute Izz : Real = 16171.877197342399;
                            attribute sigma_Izz : Real = 8561.592251610635;
                            attribute Ixy : Real = 7153.386914810145;
                            attribute sigma_Ixy : Real = 4066.72506542786;
                            attribute Ixz : Real = -219.03029073277574;
                            attribute sigma_Ixz : Real = 3565.1359125381327;
                            attribute Iyz : Real = -2249.09584110081;
                            attribute sigma_Iyz : Real = 3925.044302509224;
                            part <'C.1.2.3.2.2.2.1'> 'Part 1086' {
                                attribute POIconv : String = "+";
                                attribute Ipoint : Boolean = false;
                                attribute mass : Real = 0.5561327123520896;
                                attribute sigma_mass : Real = 0.28909372274994966;
                                attribute Cx : Real = -67.25634438917041;
                                attribute sigma_Cx : Real = 28.721044428837228;
                                attribute Cy : Real = 44.11402442492545;
                                attribute sigma_Cy : Real = 28.23690002309109;
                                attribute Cz : Real = -9.386031981557608;
                                attribute sigma_Cz : Real = 29.057750463592832;
                                attribute Ixx : Real = 0.6644465897368035;
                                attribute sigma_Ixx : Real = 0.37074144170588635;
                                attribute Iyy : Real = 0.6683513639241091;
                                attribute sigma_Iyy : Real = 0.3723953238821935;
                                attribute Izz : Real = 0.6803736349721548;
                                attribute sigma_Izz : Real = 0.37017423652493897;
                                attribute Ixy : Real = 0.015266620905208394;
                                attribute sigma_Ixy : Real = 0.02351283871158888;
                                attribute Ixz : Real = 0.057243504428252656;
                                attribute sigma_Ixz : Real = 0.022566176940390956;
                                attribute Iyz : Real = -0.0030015997111666392;
                                attribute sigma_Iyz : Real = 0.02209918015384651;
                            }
                            part <'C.1.2.3.2.2.2.2'> 'Part 1087' {
                                attribute POIconv : String = "+";
                                attribute Ipoint : Boolean = false;
                                attribute mass : Real = 0.8172284247637727;
                                attribute sigma_mass : Real = 0.28909372274994966;
                                attribute Cx : Real = 96.7974812258035;
                                attribute sigma_Cx : Real = 28.721044428837228;
                                attribute Cy : Real = -53.83351510390639;
                                attribute sigma_Cy : Real = 28.23690002309109;
                                attribute Cz : Real = 34.36636570841074;
                                attribute sigma_Cz : Real = 29.057750463592832;
                                attribute Ixx : Real = 1.0378063120688916;
                                attribute sigma_Ixx : Real = 0.37074144170588635;
                                attribute Iyy : Real = 0.8648887463909;
                                attribute sigma_Iyy : Real = 0.3723953238821935;
                                attribute Izz : Real = 0.9453361135450055;
                                attribute sigma_Izz : Real = 0.37017423652493897;
                                attribute Ixy : Real = -0.08299612091319185;
                                attribute sigma_Ixy : Real = 0.02351283871158888;
                                attribute Ixz : Real = -0.02758577712053387;
                                attribute sigma_Ixz : Real = 0.022566176940390956;
                                attribute Iyz : Real = 0.06066584038479146;
                                attribute sigma_Iyz : Real = 0.02209918015384651;
                            }
                            part <'C.1.2.3.2.2.2.3'> 'Part 1088' {
                                attribute POIconv : String = "+";
                                attribute Ipoint : Boolean = false;
                                attribute mass : Real = 0.5543945668123197;
                                attribute sigma_mass : Real = 0.28909372274994966;
                                attribute Cx : Real = 67.49224541708827;
                                attribute sigma_Cx : Real = 28.721044428837228;
                                attribute Cy : Real = -77.22733500413597;
                                attribute sigma_Cy : Real = 28.23690002309109;
                                attribute Cz : Real = -85.7072887942195;
                                attribute sigma_Cz : Real = 29.057750463592832;
                                attribute Ixx : Real = 0.6646762377603901;
                                attribute sigma_Ixx : Real = 0.37074144170588635;
                                attribute Iyy : Real = 0.7584581113637139;
                                attribute sigma_Iyy : Real = 0.3723953238821935;
                                attribute Izz : Real = 0.6745716401529638;
                                attribute sigma_Izz : Real = 0.37017423652493897;
                                attribute Ixy : Real = -0.0012254954982177484;
                                attribute sigma_Ixy : Real = 0.02351283871158888;
                                attribute Ixz : Real = -0.005532532777050148;
                                attribute sigma_Ixz : Real = 0.022566176940390956;
                                attribute Iyz : Real = -0.0446952174073174;
                                attribute sigma_Iyz : Real = 0.02209918015384651;
                            }
                            part <'C.1.2.3.2.2.2.4'> 'Part 1089' {
                                attribute POIconv : String = "+";
                                attribute Ipoint : Boolean = false;
                                attribute mass : Real = 0.1149001410761848;
                                attribute sigma_mass : Real = 0.28909372274994966;
                                attribute Cx : Real = -28.907833760604262;
                                attribute sigma_Cx : Real = 28.721044428837228;
                                attribute Cy : Real = 74.52406007796526;
                                attribute sigma_Cy : Real = 28.23690002309109;
                                attribute Cz : Real = 95.78590663149953;
                                attribute sigma_Cz : Real = 29.057750463592832;
                                attribute Ixx : Real = 0.1152588949388443;
                                attribute sigma_Ixx : Real = 0.37074144170588635;
                                attribute Iyy : Real = 0.13523930274537949;
                                attribute sigma_Iyy : Real = 0.3723953238821935;
                                attribute Izz : Real = 0.12827683824647135;
                                attribute sigma_Izz : Real = 0.37017423652493897;
                                attribute Ixy : Real = 0.005759024629091454;
                                attribute sigma_Ixy : Real = 0.02351283871158888;
                                attribute Ixz : Real = 0.0005342428656350633;
                                attribute sigma_Ixz : Real = 0.022566176940390956;
                                attribute Iyz : Real = 0.008073754644159973;
                                attribute sigma_Iyz : Real = 0.02209918015384651;
                            }
                            part <'C.1.2.3.2.2.2.5'> 'Part 1090' {
                                attribute POIconv : String = "-";
                                attribute Ipoint : Boolean = false;
                                attribute mass : Real = 0.09878505051555111;
                                attribute sigma_mass : Real = 0.28909372274994966;
                                attribute Cx : Real = 72.98461738973856;
                                attribute sigma_Cx : Real = 28.721044428837228;
                                attribute Cy : Real = -56.09317580237985;
                                attribute sigma_Cy : Real = 28.23690002309109;
                                attribute Cz : Real = 43.05601269006729;
                                attribute sigma_Cz : Real = 29.057750463592832;
                                attribute Ixx : Real = 0.10518643948193843;
                                attribute sigma_Ixx : Real = 0.37074144170588635;
                                attribute Iyy : Real = 0.12900552991247027;
                                attribute sigma_Iyy : Real = 0.3723953238821935;
                                attribute Izz : Real = 0.12483903234966033;
                                attribute sigma_Izz : Real = 0.37017423652493897;
                                attribute Ixy : Real = 0.008310185808837344;
                                attribute sigma_Ixy : Real = 0.02351283871158888;
                                attribute Ixz : Real = 2.958743020453706e-05;
                                attribute sigma_Ixz : Real = 0.022566176940390956;
                                attribute Iyz : Real = 1.568144424204719e-05;
                                attribute sigma_Iyz : Real = 0.02209918015384651;
                            }
                        }
                    }
                    part <'C.1.2.3.2.3'> 'Assembly 90' {
                        attribute POIconv : String = "-";
                        attribute Ipoint : Boolean = false;
                        attribute mass : Real = 3.170173673385056;
                        attribute sigma_mass : Real = 0.8176805270198123;
                        attribute Cx : Real = -14.983174639410956;
                        attribute sigma_Cx : Real = 20.511651165290704;
                        attribute Cy : Real = 30.615214836555985;
                        attribute sigma_Cy : Real = 19.002450905655866;
                        attribute Cz : Real = 21.01101588777433;
                        attribute sigma_Cz : Real = 21.096972246754436;
                        attribute Ixx : Real = 15291.569786703476;
                        attribute sigma_Ixx : Real = 11975.68739298385;
                        attribute Iyy : Real = 22601.71803447108;
                        attribute sigma_Iyy : Real = 10941.10525074905;
                        attribute Izz : Real = 21719.368614288527;
                        attribute sigma_Izz : Real = 8968.824011990295;
                        attribute Ixy : Real = 2375.7500263583174;
                        attribute sigma_Ixy : Real = 3724.5271639078564;
                        attribute Ixz : Real = 1643.549944489887;
                        attribute sigma_Ixz : Real = 4299.648107971971;
                        attribute Iyz : Real = -1120.9088288341034;
                        attribute sigma_Iyz : Real = 5647.12430303184;
                        part <'C.1.2.3.2.3.1'> 'Subassembly 308' {
                            attribute POIconv : String = "-";
                            attribute Ipoint : Boolean = false;
                            attribute mass : Real = 1.2463051272300072;
                            attribute sigma_mass : Real = 0.5781874454998993;
                            attribute Cx : Real = -55.30581042597365;
                            attribute sigma_Cx : Real = 24.696147015577296;
                            attribute Cy : Real = 18.971153796916497;
                            attribute sigma_Cy : Real = 40.134948594542685;
                            attribute Cz : Real = 54.00870532118359;
                            attribute sigma_Cz : Real = 39.28193442452917;
                            attribute Ixx : Real = 6592.410175461087;
                            attribute sigma_Ixx : Real = 10680.19106177128;
                            attribute Iyy : Real = 2626.763377811705;
                            attribute sigma_Iyy : Real = 6736.498317535996;
                            attribute Izz : Real = 6602.156835655479;
                            attribute sigma_Izz : Real = 5605.800403365498;
                            attribute Ixy : Real = 1628.098073186423;
                            attribute sigma_Ixy : Real = 1857.4635203688433;
                            attribute Ixz : Real = 297.9256124088986;
                            attribute sigma_Ixz : Real = 1063.1903063491945;
                            attribute Iyz : Real = -917.1826478861585;
                            attribute sigma_Iyz : Real = 5017.6422666021945;
                            part <'C.1.2.3.2.3.1.1'> 'Part 1091' {
                                attribute POIconv : String = "-";
                                attribute Ipoint : Boolean = false;
                                attribute mass : Real = 0.05497397221671418;
                                attribute sigma_mass : Real = 0.28909372274994966;
                                attribute Cx : Real = -37.98266397789121;
                                attribute sigma_Cx : Real = 28.721044428837228;
                                attribute Cy : Real = -92.95306913554668;
                                attribute sigma_Cy : Real = 28.23690002309109;
                                attribute Cz : Real = -94.83069661073387;
                                attribute sigma_Cz : Real = 29.057750463592832;
                                attribute Ixx : Real = 0.06966739586818131;
                                attribute sigma_Ixx : Real = 0.37074144170588635;
                                attribute Iyy : Real = 0.07700279554782437;
                                attribute sigma_Iyy : Real = 0.3723953238821935;
                                attribute Izz : Real = 0.08054261771822534;
                                attribute sigma_Izz : Real = 0.37017423652493897;
                                attribute Ixy : Real = -0.0014231119013099409;
                                attribute sigma_Ixy : Real = 0.02351283871158888;
                                attribute Ixz : Real = 0.0006900242581363717;
                                attribute sigma_Ixz : Real = 0.022566176940390956;
                                attribute Iyz : Real = 0.0032138513078286053;
                                attribute sigma_Iyz : Real = 0.02209918015384651;
                            }
                            part <'C.1.2.3.2.3.1.2'> 'Part 1092' {
                                attribute POIconv : String = "+";
                                attribute Ipoint : Boolean = false;
                                attribute mass : Real = 0.34918252723268234;
                                attribute sigma_mass : Real = 0.28909372274994966;
                                attribute Cx : Real = -27.887688716873527;
                                attribute sigma_Cx : Real = 28.721044428837228;
                                attribute Cy : Real = -71.5850982349366;
                                attribute sigma_Cy : Real = 28.23690002309109;
                                attribute Cz : Real = 62.47166618704796;
                                attribute sigma_Cz : Real = 29.057750463592832;
                                attribute Ixx : Real = 0.372801418281261;
                                attribute sigma_Ixx : Real = 0.37074144170588635;
                                attribute Iyy : Real = 0.3798433680811546;
                                attribute sigma_Iyy : Real = 0.3723953238821935;
                                attribute Izz : Real = 0.36972095559979956;
                                attribute sigma_Izz : Real = 0.37017423652493897;
                                attribute Ixy : Real = 0.008647293681186243;
                                attribute sigma_Ixy : Real = 0.02351283871158888;
                                attribute Ixz : Real = -0.01976745999837262;
                                attribute sigma_Ixz : Real = 0.022566176940390956;
                                attribute Iyz : Real = -0.010441217251067579;
                                attribute sigma_Iyz : Real = 0.02209918015384651;
                            }
                            part <'C.1.2.3.2.3.1.3'> 'Part 1093' {
                                attribute POIconv : String = "+";
                                attribute Ipoint : Boolean = false;
                                attribute mass : Real = 0.15086264159809798;
                                attribute sigma_mass : Real = 0.28909372274994966;
                                attribute Cx : Real = 2.4376981891691685;
                                attribute sigma_Cx : Real = 28.721044428837228;
                                attribute Cy : Real = 49.69403180293739;
                                attribute sigma_Cy : Real = 28.23690002309109;
                                attribute Cz : Real = 46.903557144105434;
                                attribute sigma_Cz : Real = 29.057750463592832;
                                attribute Ixx : Real = 0.19931265931396447;
                                attribute sigma_Ixx : Real = 0.37074144170588635;
                                attribute Iyy : Real = 0.23335506539353873;
                                attribute sigma_Iyy : Real = 0.3723953238821935;
                                attribute Izz : Real = 0.20698063272790948;
                                attribute sigma_Izz : Real = 0.37017423652493897;
                                attribute Ixy : Real = 0.003925626952911989;
                                attribute sigma_Ixy : Real = 0.02351283871158888;
                                attribute Ixz : Real = 0.004855835772829;
                                attribute sigma_Ixz : Real = 0.022566176940390956;
                                attribute Iyz : Real = 0.0003237336856689135;
                                attribute sigma_Iyz : Real = 0.02209918015384651;
                            }
                            part <'C.1.2.3.2.3.1.4'> 'Part 1094' {
                                attribute POIconv : String = "-";
                                attribute Ipoint : Boolean = false;
                                attribute mass : Real = 0.6912859861825127;
                                attribute sigma_mass : Real = 0.28909372274994966;
                                attribute Cx : Real = -83.1345091573894;
                                attribute sigma_Cx : Real = 28.721044428837228;
                                attribute Cy : Real = 66.90883254632354;
                                attribute sigma_Cy : Real = 28.23690002309109;
                                attribute Cz : Real = 63.120819022879004;
                                attribute sigma_Cz : Real = 29.057750463592832;
                                attribute Ixx : Real = 0.8003024047957623;
                                attribute sigma_Ixx : Real = 0.37074144170588635;
                                attribute Iyy : Real = 0.8259060592874118;
                                attribute sigma_Iyy : Real = 0.3723953238821935;
                                attribute Izz : Real = 1.025402684249924;
                                attribute sigma_Izz : Real = 0.37017423652493897;
                                attribute Ixy : Real = -0.02298066551182457;
                                attribute sigma_Ixy : Real = 0.02351283871158888;
                                attribute Ixz : Real = 0.0002835827405062617;
                                attribute sigma_Ixz : Real = 0.022566176940390956;
                                attribute Iyz : Real = 0.02761624917420914;
                                attribute sigma_Iyz : Real = 0.02209918015384651;
                            }
                        }
                        part <'C.1.2.3.2.3.2'> 'Subassembly 309' {
                            attribute POIconv : String = "-";
                            attribute Ipoint : Boolean = false;
                            attribute mass : Real = 1.9238685461550487;
                            attribute sigma_mass : Real = 0.5781874454998993;
                            attribute Cx : Real = 11.138312623664842;
                            attribute sigma_Cx : Real = 26.037719967646368;
                            attribute Cy : Real = 38.1583772862384;
                            attribute sigma_Cy : Real = 16.94374485542141;
                            attribute Cz : Real = -0.3652832412863454;
                            attribute sigma_Cz : Real = 20.526627177924848;
                            attribute Ixx : Real = 6184.573022509732;
                            attribute sigma_Ixx : Real = 3724.6281327838715;
                            attribute Iyy : Real = 14399.710665453611;
                            attribute sigma_Iyy : Real = 6717.903753989436;
                            attribute Izz : Real = 11499.662368701041;
                            attribute sigma_Izz : Real = 5760.7353663224985;
                            attribute Ixy : Real = 1711.8925867776836;
                            attribute sigma_Ixy : Real = 2295.840595192356;
                            attribute Ixz : Real = -1386.9028213306633;
                            attribute sigma_Ixz : Real = 3085.6569023816614;
                            attribute Iyz : Real = -992.8043834547534;
                            attribute sigma_Iyz : Real = 1741.1602824058982;
                            part <'C.1.2.3.2.3.2.1'> 'Part 1095' {
                                attribute POIconv : String = "+";
                                attribute Ipoint : Boolean = false;
                                attribute mass : Real = 0.5428474221359938;
                                attribute sigma_mass : Real = 0.28909372274994966;
                                attribute Cx : Real = 79.09870496951044;
                                attribute sigma_Cx : Real = 28.721044428837228;
                                attribute Cy : Real = 18.296489398926497;
                                attribute sigma_Cy : Real = 28.23690002309109;
                                attribute Cz : Real = 52.67065283842385;
                                attribute sigma_Cz : Real = 29.057750463592832;
                                attribute Ixx : Real = 0.6313717312322196;
                                attribute sigma_Ixx : Real = 0.37074144170588635;
                                attribute Iyy : Real = 0.6806577498054742;
                                attribute sigma_Iyy : Real = 0.3723953238821935;
                                attribute Izz : Real = 0.6605338827974486;
                                attribute sigma_Izz : Real = 0.37017423652493897;
                                attribute Ixy : Real = 0.038212751645309295;
                                attribute sigma_Ixy : Real = 0.02351283871158888;
                                attribute Ixz : Real = 0.010085192110511138;
                                attribute sigma_Ixz : Real = 0.022566176940390956;
                                attribute Iyz : Real = 0.05159292832745426;
                                attribute sigma_Iyz : Real = 0.02209918015384651;
                            }
                            part <'C.1.2.3.2.3.2.2'> 'Part 1096' {
                                attribute POIconv : String = "-";
                                attribute Ipoint : Boolean = false;
                                attribute mass : Real = 0.41461438029562125;
                                attribute sigma_mass : Real = 0.28909372274994966;
                                attribute Cx : Real = -37.03171834349632;
                                attribute sigma_Cx : Real = 28.721044428837228;
                                attribute Cy : Real = 93.54875925928354;
                                attribute sigma_Cy : Real = 28.23690002309109;
                                attribute Cz : Real = 41.99002832174301;
                                attribute sigma_Cz : Real = 29.057750463592832;
                                attribute Ixx : Real = 0.5766702800897564;
                                attribute sigma_Ixx : Real = 0.37074144170588635;
                                attribute Iyy : Real = 0.5602879990760286;
                                attribute sigma_Iyy : Real = 0.3723953238821935;
                                attribute Izz : Real = 0.54340643768561;
                                attribute sigma_Izz : Real = 0.37017423652493897;
                                attribute Ixy : Real = 0.0053229441757046405;
                                attribute sigma_Ixy : Real = 0.02351283871158888;
                                attribute Ixz : Real = -0.008756018723474852;
                                attribute sigma_Ixz : Real = 0.022566176940390956;
                                attribute Iyz : Real = 0.024595523787997054;
                                attribute sigma_Iyz : Real = 0.02209918015384651;
                            }
                            part <'C.1.2.3.2.3.2.3'> 'Part 1097' {
                                attribute POIconv : String = "+";
                                attribute Ipoint : Boolean = false;
                                attribute mass : Real = 0.4438376878462732;
                                attribute sigma_mass : Real = 0.28909372274994966;
                                attribute Cx : Real = -92.51174703240395;
                                attribute sigma_Cx : Real = 28.721044428837228;
                                attribute Cy : Real = 26.771060144528747;
                                attribute sigma_Cy : Real = 28.23690002309109;
                                attribute Cz : Real = -40.756921749562025;
                                attribute sigma_Cz : Real = 29.057750463592832;
                                attribute Ixx : Real = 0.6657342942508085;
                                attribute sigma_Ixx : Real = 0.37074144170588635;
                                attribute Iyy : Real = 0.5605041396293176;
                                attribute sigma_Iyy : Real = 0.3723953238821935;
                                attribute Izz : Real = 0.5571096079454422;
                                attribute sigma_Izz : Real = 0.37017423652493897;
                                attribute Ixy : Real = 0.033843872786422924;
                                attribute sigma_Ixy : Real = 0.02351283871158888;
                                attribute Ixz : Real = 0.0007748775845943994;
                                attribute sigma_Ixz : Real = 0.022566176940390956;
                                attribute Iyz : Real = -0.011373311147057924;
                                attribute sigma_Iyz : Real = 0.02209918015384651;
                            }
                            part <'C.1.2.3.2.3.2.4'> 'Part 1098' {
                                attribute POIconv : String = "+";
                                attribute Ipoint : Boolean = false;
                                attribute mass : Real = 0.5225690558771603;
                                attribute sigma_mass : Real = 0.28909372274994966;
                                attribute Cx : Real = 66.79347674362361;
                                attribute sigma_Cx : Real = 28.721044428837228;
                                attribute Cy : Real = 24.51510149985552;
                                attribute sigma_Cy : Real = 28.23690002309109;
                                attribute Cz : Real = -54.75849821232259;
                                attribute sigma_Cz : Real = 29.057750463592832;
                                attribute Ixx : Real = 0.7172592588858192;
                                attribute sigma_Ixx : Real = 0.37074144170588635;
                                attribute Iyy : Real = 0.7693971489784205;
                                attribute sigma_Iyy : Real = 0.3723953238821935;
                                attribute Izz : Real = 0.6439328692741644;
                                attribute sigma_Izz : Real = 0.37017423652493897;
                                attribute Ixy : Real = -0.01948385557972983;
                                attribute sigma_Ixy : Real = 0.02351283871158888;
                                attribute Ixz : Real = -0.020205136169337494;
                                attribute sigma_Ixz : Real = 0.022566176940390956;
                                attribute Iyz : Real = -0.039895396171442526;
                                attribute sigma_Iyz : Real = 0.02209918015384651;
                            }
                        }
                    }
                    part <'C.1.2.3.2.4'> 'Assembly 91' {
                        attribute POIconv : String = "-";
                        attribute Ipoint : Boolean = false;
                        attribute mass : Real = 9.117797173004597;
                        attribute sigma_mass : Real = 1.2265207905297186;
                        attribute Cx : Real = 16.197633295621365;
                        attribute sigma_Cx : Real = 10.942630186678864;
                        attribute Cy : Real = 17.399596462388843;
                        attribute sigma_Cy : Real = 11.494636143964838;
                        attribute Cz : Real = 13.82211611785766;
                        attribute sigma_Cz : Real = 11.761950636862153;
                        attribute Ixx : Real = 69320.51931230337;
                        attribute sigma_Ixx : Real = 16903.00482684163;
                        attribute Iyy : Real = 56438.56779709521;
                        attribute sigma_Iyy : Real = 15308.77551848337;
                        attribute Izz : Real = 50113.628105677824;
                        attribute sigma_Izz : Real = 15018.431474129306;
                        attribute Ixy : Real = 3090.729656176314;
                        attribute sigma_Ixy : Real = 6990.448847701705;
                        attribute Ixz : Real = 1189.8528562181305;
                        attribute sigma_Ixz : Real = 7098.998518797774;
                        attribute Iyz : Real = 2555.5820405100276;
                        attribute sigma_Iyz : Real = 7233.335750679927;
                        part <'C.1.2.3.2.4.1'> 'Subassembly 310' {
                            attribute POIconv : String = "-";
                            attribute Ipoint : Boolean = false;
                            attribute mass : Real = 2.677598734643543;
                            attribute sigma_mass : Real = 0.6464332159373649;
                            attribute Cx : Real = 12.785591690096394;
                            attribute sigma_Cx : Real = 20.2747261234296;
                            attribute Cy : Real = 36.37833146300435;
                            attribute sigma_Cy : Real = 21.498243632856617;
                            attribute Cz : Real = -11.232122753673;
                            attribute sigma_Cz : Real = 23.298635849763713;
                            attribute Ixx : Real = 22156.8927995023;
                            attribute sigma_Ixx : Real = 9827.386173236546;
                            attribute Iyy : Real = 21682.417601030997;
                            attribute sigma_Iyy : Real = 9516.173828537374;
                            attribute Izz : Real = 11278.140416343116;
                            attribute sigma_Izz : Real = 8911.196694028811;
                            attribute Ixy : Real = -1268.4218223806047;
                            attribute sigma_Ixy : Real = 4182.653960576875;
                            attribute Ixz : Real = -2402.477227494015;
                            attribute sigma_Ixz : Real = 4255.744740889892;
                            attribute Iyz : Real = 5716.832035545336;
                            attribute sigma_Iyz : Real = 3661.5128458610448;
                            part <'C.1.2.3.2.4.1.1'> 'Part 1099' {
                                attribute POIconv : String = "-";
                                attribute Ipoint : Boolean = false;
                                attribute mass : Real = 0.9355795071159955;
                                attribute sigma_mass : Real = 0.28909372274994966;
                                attribute Cx : Real = 5.548589210957289;
                                attribute sigma_Cx : Real = 28.721044428837228;
                                attribute Cy : Real = 56.769949151203036;
                                attribute sigma_Cy : Real = 28.23690002309109;
                                attribute Cz : Real = -86.13865557126701;
                                attribute sigma_Cz : Real = 29.057750463592832;
                                attribute Ixx : Real = 1.2637948732072388;
                                attribute sigma_Ixx : Real = 0.37074144170588635;
                                attribute Iyy : Real = 1.3494083538412773;
                                attribute sigma_Iyy : Real = 0.3723953238821935;
                                attribute Izz : Real = 1.3830498531416495;
                                attribute sigma_Izz : Real = 0.37017423652493897;
                                attribute Ixy : Real = 0.012519699709962303;
                                attribute sigma_Ixy : Real = 0.02351283871158888;
                                attribute Ixz : Real = -0.05939141884256449;
                                attribute sigma_Ixz : Real = 0.022566176940390956;
                                attribute Iyz : Real = -0.02278298144222341;
                                attribute sigma_Iyz : Real = 0.02209918015384651;
                            }
                            part <'C.1.2.3.2.4.1.2'> 'Part 1100' {
                                attribute POIconv : String = "-";
                                attribute Ipoint : Boolean = false;
                                attribute mass : Real = 0.15088262663478963;
                                attribute sigma_mass : Real = 0.28909372274994966;
                                attribute Cx : Real = -81.87416386790574;
                                attribute sigma_Cx : Real = 28.721044428837228;
                                attribute Cy : Real = -95.14246680773795;
                                attribute sigma_Cy : Real = 28.23690002309109;
                                attribute Cz : Real = -29.56867925822735;
                                attribute sigma_Cz : Real = 29.057750463592832;
                                attribute Ixx : Real = 0.1585559014803746;
                                attribute sigma_Ixx : Real = 0.37074144170588635;
                                attribute Iyy : Real = 0.14138737886412606;
                                attribute sigma_Iyy : Real = 0.3723953238821935;
                                attribute Izz : Real = 0.1652953054496566;
                                attribute sigma_Izz : Real = 0.37017423652493897;
                                attribute Ixy : Real = -0.00014282638455323797;
                                attribute sigma_Ixy : Real = 0.02351283871158888;
                                attribute Ixz : Real = -5.806910750280517e-06;
                                attribute sigma_Ixz : Real = 0.022566176940390956;
                                attribute Iyz : Real = 0.0034817968054934446;
                                attribute sigma_Iyz : Real = 0.02209918015384651;
                            }
                            part <'C.1.2.3.2.4.1.3'> 'Part 1101' {
                                attribute POIconv : String = "-";
                                attribute Ipoint : Boolean = false;
                                attribute mass : Real = 0.4954275927224662;
                                attribute sigma_mass : Real = 0.28909372274994966;
                                attribute Cx : Real = -26.655212603509426;
                                attribute sigma_Cx : Real = 28.721044428837228;
                                attribute Cy : Real = 1.1172140017151833;
                                attribute sigma_Cy : Real = 28.23690002309109;
                                attribute Cz : Real = 94.6926117874682;
                                attribute sigma_Cz : Real = 29.057750463592832;
                                attribute Ixx : Real = 0.6604474722485992;
                                attribute sigma_Ixx : Real = 0.37074144170588635;
                                attribute Iyy : Real = 0.6350152847021314;
                                attribute sigma_Iyy : Real = 0.3723953238821935;
                                attribute Izz : Real = 0.6833549157572724;
                                attribute sigma_Izz : Real = 0.37017423652493897;
                                attribute Ixy : Real = -0.005172712107083852;
                                attribute sigma_Ixy : Real = 0.02351283871158888;
                                attribute Ixz : Real = 0.006025208356714807;
                                attribute sigma_Ixz : Real = 0.022566176940390956;
                                attribute Iyz : Real = 0.011726085303259687;
                                attribute sigma_Iyz : Real = 0.02209918015384651;
                            }
                            part <'C.1.2.3.2.4.1.4'> 'Part 1102' {
                                attribute POIconv : String = "-";
                                attribute Ipoint : Boolean = false;
                                attribute mass : Real = 0.6521077641418669;
                                attribute sigma_mass : Real = 0.28909372274994966;
                                attribute Cx : Real = 17.113251471892;
                                attribute sigma_Cx : Real = 28.721044428837228;
                                attribute Cy : Real = 87.86846911534667;
                                attribute sigma_Cy : Real = 28.23690002309109;
                                attribute Cz : Real = -48.58629060909152;
                                attribute sigma_Cz : Real = 29.057750463592832;
                                attribute Ixx : Real = 0.9054042630024207;
                                attribute sigma_Ixx : Real = 0.37074144170588635;
                                attribute Iyy : Real = 0.9241841079190529;
                                attribute sigma_Iyy : Real = 0.3723953238821935;
                                attribute Izz : Real = 0.9496548367234031;
                                attribute sigma_Izz : Real = 0.37017423652493897;
                                attribute Ixy : Real = -0.0362169035073473;
                                attribute sigma_Ixy : Real = 0.02351283871158888;
                                attribute Ixz : Real = -0.03909162655610002;
                                attribute sigma_Ixz : Real = 0.022566176940390956;
                                attribute Iyz : Real = 0.034281708841578246;
                                attribute sigma_Iyz : Real = 0.02209918015384651;
                            }
                            part <'C.1.2.3.2.4.1.5'> 'Part 1103' {
                                attribute POIconv : String = "-";
                                attribute Ipoint : Boolean = false;
                                attribute mass : Real = 0.4436012440284248;
                                attribute sigma_mass : Real = 0.28909372274994966;
                                attribute Cx : Real = 97.9324808344245;
                                attribute sigma_Cx : Real = 28.721044428837228;
                                attribute Cy : Real = 1.7941991332918406;
                                attribute sigma_Cy : Real = 28.23690002309109;
                                attribute Cz : Real = 89.59850408136845;
                                attribute sigma_Cz : Real = 29.057750463592832;
                                attribute Ixx : Real = 0.5958068911074978;
                                attribute sigma_Ixx : Real = 0.37074144170588635;
                                attribute Iyy : Real = 0.4943680226960312;
                                attribute sigma_Iyy : Real = 0.3723953238821935;
                                attribute Izz : Real = 0.575398086083283;
                                attribute sigma_Izz : Real = 0.37017423652493897;
                                attribute Ixy : Real = 0.015589705510161738;
                                attribute sigma_Ixy : Real = 0.02351283871158888;
                                attribute Ixz : Real = -0.008923778699198723;
                                attribute sigma_Ixz : Real = 0.022566176940390956;
                                attribute Iyz : Real = 0.03533123349596242;
                                attribute sigma_Iyz : Real = 0.02209918015384651;
                            }
                        }
                        part <'C.1.2.3.2.4.2'> 'Subassembly 311' {
                            attribute POIconv : String = "-";
                            attribute Ipoint : Boolean = false;
                            attribute mass : Real = 1.6744082260008435;
                            attribute sigma_mass : Real = 0.40884026350990615;
                            attribute Cx : Real = -1.5885127391495482;
                            attribute sigma_Cx : Real = 20.668734287067767;
                            attribute Cy : Real = -16.781777217134888;
                            attribute sigma_Cy : Real = 28.671443517377337;
                            attribute Cz : Real = 17.914778974152416;
                            attribute sigma_Cz : Real = 20.750101912583535;
                            attribute Ixx : Real = 11269.28322595359;
                            attribute sigma_Ixx : Real = 6186.09790180394;
                            attribute Iyy : Real = 206.27686280002575;
                            attribute sigma_Iyy : Real = 746.713130780082;
                            attribute Izz : Real = 11446.044721159129;
                            attribute sigma_Izz : Real = 6246.855519703429;
                            attribute Ixy : Real = 1464.6898189152794;
                            attribute sigma_Ixy : Real = 2810.5613120876405;
                            attribute Ixz : Real = 51.172533116691;
                            attribute sigma_Ixz : Real = 376.40906186958375;
                            attribute Iyz : Real = -392.4517247743363;
                            attribute sigma_Iyz : Real = 2797.522485470106;
                            part <'C.1.2.3.2.4.2.1'> 'Part 1104' {
                                attribute POIconv : String = "-";
                                attribute Ipoint : Boolean = false;
                                attribute mass : Real = 0.7227953992483672;
                                attribute sigma_mass : Real = 0.28909372274994966;
                                attribute Cx : Real = -13.830693904310465;
                                attribute sigma_Cx : Real = 28.721044428837228;
                                attribute Cy : Real = 77.28517251089215;
                                attribute sigma_Cy : Real = 28.23690002309109;
                                attribute Cz : Real = 21.19648582302034;
                                attribute sigma_Cz : Real = 29.057750463592832;
                                attribute Ixx : Real = 0.74744148432908;
                                attribute sigma_Ixx : Real = 0.37074144170588635;
                                attribute Iyy : Real = 0.7233700979355331;
                                attribute sigma_Iyy : Real = 0.3723953238821935;
                                attribute Izz : Real = 0.6408198576755768;
                                attribute sigma_Izz : Real = 0.37017423652493897;
                                attribute Ixy : Real = 0.0023911687933561966;
                                attribute sigma_Ixy : Real = 0.02351283871158888;
                                attribute Ixz : Real = -0.005298585512449525;
                                attribute sigma_Ixz : Real = 0.022566176940390956;
                                attribute Iyz : Real = 0.05094650401846454;
                                attribute sigma_Iyz : Real = 0.02209918015384651;
                            }
                            part <'C.1.2.3.2.4.2.2'> 'Part 1105' {
                                attribute POIconv : String = "+";
                                attribute Ipoint : Boolean = false;
                                attribute mass : Real = 0.9516128267524764;
                                attribute sigma_mass : Real = 0.28909372274994966;
                                attribute Cx : Real = 7.7100086491554976;
                                attribute sigma_Cx : Real = 28.721044428837228;
                                attribute Cy : Real = -88.23011899366975;
                                attribute sigma_Cy : Real = 28.23690002309109;
                                attribute Cz : Real = 15.422165859490633;
                                attribute sigma_Cz : Real = 29.057750463592832;
                                attribute Ixx : Real = 1.262666097491278;
                                attribute sigma_Ixx : Real = 0.37074144170588635;
                                attribute Iyy : Real = 1.2518975744882963;
                                attribute sigma_Iyy : Real = 0.3723953238821935;
                                attribute Izz : Real = 1.222591874616785;
                                attribute sigma_Izz : Real = 0.37017423652493897;
                                attribute Ixy : Real = -0.11010656102204461;
                                attribute sigma_Ixy : Real = 0.02351283871158888;
                                attribute Ixz : Real = -0.08322898012810283;
                                attribute sigma_Ixz : Real = 0.022566176940390956;
                                attribute Iyz : Real = -0.10003250362266354;
                                attribute sigma_Iyz : Real = 0.02209918015384651;
                            }
                        }
                        part <'C.1.2.3.2.4.3'> 'Subassembly 312' {
                            attribute POIconv : String = "-";
                            attribute Ipoint : Boolean = false;
                            attribute mass : Real = 0.4826864812700078;
                            attribute sigma_mass : Real = 0.40884026350990615;
                            attribute Cx : Real = 81.73150736848805;
                            attribute sigma_Cx : Real = 21.644185327471405;
                            attribute Cy : Real = 11.338234068993499;
                            attribute sigma_Cy : Real = 62.718435472197605;
                            attribute Cz : Real = 33.11194889967157;
                            attribute sigma_Cz : Real = 24.130104902409474;
                            attribute Ixx : Real = 1835.8072248931217;
                            attribute sigma_Ixx : Real = 2673.6531587840127;
                            attribute Iyy : Real = 53.39101856690456;
                            attribute sigma_Iyy : Real = 204.93914792504063;
                            attribute Izz : Real = 1783.1559984065655;
                            attribute sigma_Izz : Real = 2603.1624921787525;
                            attribute Ixy : Real = 7.945659798027567;
                            attribute sigma_Ixy : Real = 553.9215888249378;
                            attribute Ixz : Real = 1.356887830195501;
                            attribute sigma_Ixz : Real = 95.23013671183391;
                            attribute Iyz : Real = -306.3459466138996;
                            attribute sigma_Iyz : Real = 698.444008454034;
                            part <'C.1.2.3.2.4.3.1'> 'Part 1106' {
                                attribute POIconv : String = "-";
                                attribute Ipoint : Boolean = false;
                                attribute mass : Real = 0.15245172869018278;
                                attribute sigma_mass : Real = 0.28909372274994966;
                                attribute Cx : Real = 82.1294114459306;
                                attribute sigma_Cx : Real = 28.721044428837228;
                                attribute Cy : Real = -78.09897377155721;
                                attribute sigma_Cy : Real = 28.23690002309109;
                                attribute Cz : Real = 17.741036973893642;
                                attribute sigma_Cz : Real = 29.057750463592832;
                                attribute Ixx : Real = 0.21717095508092787;
                                attribute sigma_Ixx : Real = 0.37074144170588635;
                                attribute Iyy : Real = 0.1971670500317219;
                                attribute sigma_Iyy : Real = 0.3723953238821935;
                                attribute Izz : Real = 0.1836865595422051;
                                attribute sigma_Izz : Real = 0.37017423652493897;
                                attribute Ixy : Real = 0.004674645632627362;
                                attribute sigma_Ixy : Real = 0.02351283871158888;
                                attribute Ixz : Real = 0.006608017622239318;
                                attribute sigma_Ixz : Real = 0.022566176940390956;
                                attribute Iyz : Real = -0.013550468386228223;
                                attribute sigma_Iyz : Real = 0.02209918015384651;
                            }
                            part <'C.1.2.3.2.4.3.2'> 'Part 1107' {
                                attribute POIconv : String = "+";
                                attribute Ipoint : Boolean = false;
                                attribute mass : Real = 0.330234752579825;
                                attribute sigma_mass : Real = 0.28909372274994966;
                                attribute Cx : Real = 81.547816330567;
                                attribute sigma_Cx : Real = 28.721044428837228;
                                attribute Cy : Real = 52.62661101296544;
                                attribute sigma_Cy : Real = 28.23690002309109;
                                attribute Cz : Real = 40.2078771032393;
                                attribute sigma_Cz : Real = 29.057750463592832;
                                attribute Ixx : Real = 0.5183635413897415;
                                attribute sigma_Ixx : Real = 0.37074144170588635;
                                attribute Iyy : Real = 0.5115284083294579;
                                attribute sigma_Iyy : Real = 0.3723953238821935;
                                attribute Izz : Real = 0.5123840850324586;
                                attribute sigma_Izz : Real = 0.37017423652493897;
                                attribute Ixy : Real = -0.011018954783511593;
                                attribute sigma_Ixy : Real = 0.02351283871158888;
                                attribute Ixz : Real = 0.012584871386786916;
                                attribute sigma_Ixz : Real = 0.022566176940390956;
                                attribute Iyz : Real = 0.0002449865937105925;
                                attribute sigma_Iyz : Real = 0.02209918015384651;
                            }
                        }
                        part <'C.1.2.3.2.4.4'> 'Subassembly 313' {
                            attribute POIconv : String = "-";
                            attribute Ipoint : Boolean = false;
                            attribute mass : Real = 2.4872491308003664;
                            attribute sigma_mass : Real = 0.6464332159373649;
                            attribute Cx : Real = -12.960126553655325;
                            attribute sigma_Cx : Real = 19.758997234897304;
                            attribute Cy : Real = 22.279967031038968;
                            attribute sigma_Cy : Real = 19.690791409386684;
                            attribute Cz : Real = 40.84644534734005;
                            attribute sigma_Cz : Real = 17.391097923757993;
                            attribute Ixx : Real = 9286.229587542923;
                            attribute sigma_Ixx : Real = 5268.43446665227;
                            attribute Iyy : Real = 4304.694117915929;
                            attribute sigma_Iyy : Real = 4886.574086057088;
                            attribute Izz : Real = 8145.820927856876;
                            attribute sigma_Izz : Real = 6050.649452674786;
                            attribute Ixy : Real = 1866.3854296928898;
                            attribute sigma_Ixy : Real = 2623.7366715526896;
                            attribute Ixz : Real = -1549.1254581381531;
                            attribute sigma_Ixz : Real = 2066.302882176907;
                            attribute Iyz : Real = 1091.8508964367243;
                            attribute sigma_Iyz : Real = 2488.747369105306;
                            part <'C.1.2.3.2.4.4.1'> 'Part 1108' {
                                attribute POIconv : String = "+";
                                attribute Ipoint : Boolean = false;
                                attribute mass : Real = 0.016121685769874602;
                                attribute sigma_mass : Real = 0.28909372274994966;
                                attribute Cx : Real = 90.47938068397343;
                                attribute sigma_Cx : Real = 28.721044428837228;
                                attribute Cy : Real = -27.619647048413754;
                                attribute sigma_Cy : Real = 28.23690002309109;
                                attribute Cz : Real = -1.5015270560979843;
                                attribute sigma_Cz : Real = 29.057750463592832;
                                attribute Ixx : Real = 0.01946039445245955;
                                attribute sigma_Ixx : Real = 0.37074144170588635;
                                attribute Iyy : Real = 0.018841092155858132;
                                attribute sigma_Iyy : Real = 0.3723953238821935;
                                attribute Izz : Real = 0.020817150149981548;
                                attribute sigma_Izz : Real = 0.37017423652493897;
                                attribute Ixy : Real = 0.0002673951490214987;
                                attribute sigma_Ixy : Real = 0.02351283871158888;
                                attribute Ixz : Real = -0.0012171115318801724;
                                attribute sigma_Ixz : Real = 0.022566176940390956;
                                attribute Iyz : Real = 0.0012571686809779033;
                                attribute sigma_Iyz : Real = 0.02209918015384651;
                            }
                            part <'C.1.2.3.2.4.4.2'> 'Part 1109' {
                                attribute POIconv : String = "-";
                                attribute Ipoint : Boolean = false;
                                attribute mass : Real = 0.6192007512964774;
                                attribute sigma_mass : Real = 0.28909372274994966;
                                attribute Cx : Real = -50.13936059549451;
                                attribute sigma_Cx : Real = 28.721044428837228;
                                attribute Cy : Real = 90.9339573699981;
                                attribute sigma_Cy : Real = 28.23690002309109;
                                attribute Cz : Real = -5.758166639134288;
                                attribute sigma_Cz : Real = 29.057750463592832;
                                attribute Ixx : Real = 0.7544162856581335;
                                attribute sigma_Ixx : Real = 0.37074144170588635;
                                attribute Iyy : Real = 0.7844172004587067;
                                attribute sigma_Iyy : Real = 0.3723953238821935;
                                attribute Izz : Real = 0.8893412959485172;
                                attribute sigma_Izz : Real = 0.37017423652493897;
                                attribute Ixy : Real = -0.001520068948336354;
                                attribute sigma_Ixy : Real = 0.02351283871158888;
                                attribute Ixz : Real = -0.013119333252952375;
                                attribute sigma_Ixz : Real = 0.022566176940390956;
                                attribute Iyz : Real = 0.00919834567052532;
                                attribute sigma_Iyz : Real = 0.02209918015384651;
                            }
                            part <'C.1.2.3.2.4.4.3'> 'Part 1110' {
                                attribute POIconv : String = "-";
                                attribute Ipoint : Boolean = false;
                                attribute mass : Real = 0.8519235519045033;
                                attribute sigma_mass : Real = 0.28909372274994966;
                                attribute Cx : Real = 10.888919606804848;
                                attribute sigma_Cx : Real = 28.721044428837228;
                                attribute Cy : Real = 29.18862784281373;
                                attribute sigma_Cy : Real = 28.23690002309109;
                                attribute Cz : Real = 75.17644455656409;
                                attribute sigma_Cz : Real = 29.057750463592832;
                                attribute Ixx : Real = 1.1747274995723958;
                                attribute sigma_Ixx : Real = 0.37074144170588635;
                                attribute Iyy : Real = 1.177720886597631;
                                attribute sigma_Iyy : Real = 0.3723953238821935;
                                attribute Izz : Real = 1.193344147244268;
                                attribute sigma_Izz : Real = 0.37017423652493897;
                                attribute Ixy : Real = -0.012833828777611748;
                                attribute sigma_Ixy : Real = 0.02351283871158888;
                                attribute Ixz : Real = -0.013564274028886339;
                                attribute sigma_Ixz : Real = 0.022566176940390956;
                                attribute Iyz : Real = -0.0007884820807096713;
                                attribute sigma_Iyz : Real = 0.02209918015384651;
                            }
                            part <'C.1.2.3.2.4.4.4'> 'Part 1111' {
                                attribute POIconv : String = "-";
                                attribute Ipoint : Boolean = false;
                                attribute mass : Real = 0.6062849436367397;
                                attribute sigma_mass : Real = 0.28909372274994966;
                                attribute Cx : Real = -5.354289570823312;
                                attribute sigma_Cx : Real = 28.721044428837228;
                                attribute Cy : Real = -54.34263232164085;
                                attribute sigma_Cy : Real = 28.23690002309109;
                                attribute Cz : Real = 26.216398319229484;
                                attribute sigma_Cz : Real = 29.057750463592832;
                                attribute Ixx : Real = 0.8110678129408333;
                                attribute sigma_Ixx : Real = 0.37074144170588635;
                                attribute Iyy : Real = 0.8159399987915779;
                                attribute sigma_Iyy : Real = 0.3723953238821935;
                                attribute Izz : Real = 0.658226395386454;
                                attribute sigma_Izz : Real = 0.37017423652493897;
                                attribute Ixy : Real = 0.005608632892637671;
                                attribute sigma_Ixy : Real = 0.02351283871158888;
                                attribute Ixz : Real = -0.0013624788414457003;
                                attribute sigma_Ixz : Real = 0.022566176940390956;
                                attribute Iyz : Real = -0.027304984492302252;
                                attribute sigma_Iyz : Real = 0.02209918015384651;
                            }
                            part <'C.1.2.3.2.4.4.5'> 'Part 1112' {
                                attribute POIconv : String = "+";
                                attribute Ipoint : Boolean = false;
                                attribute mass : Real = 0.39371819819277154;
                                attribute sigma_mass : Real = 0.28909372274994966;
                                attribute Cx : Real = -22.040423471480608;
                                attribute sigma_Cx : Real = 28.721044428837228;
                                attribute Cy : Real = 19.392980774864554;
                                attribute sigma_Cy : Real = 28.23690002309109;
                                attribute Cz : Real = 64.12140158936381;
                                attribute sigma_Cz : Real = 29.057750463592832;
                                attribute Ixx : Real = 0.4509935414856381;
                                attribute sigma_Ixx : Real = 0.37074144170588635;
                                attribute Iyy : Real = 0.49325683095698586;
                                attribute sigma_Iyy : Real = 0.3723953238821935;
                                attribute Izz : Real = 0.4317900286245668;
                                attribute sigma_Izz : Real = 0.37017423652493897;
                                attribute Ixy : Real = -0.027477813882965565;
                                attribute sigma_Ixy : Real = 0.02351283871158888;
                                attribute Ixz : Real = -0.013513574981236835;
                                attribute sigma_Ixz : Real = 0.022566176940390956;
                                attribute Iyz : Real = 0.012169320648142341;
                                attribute sigma_Iyz : Real = 0.02209918015384651;
                            }
                        }
                        part <'C.1.2.3.2.4.5'> 'Subassembly 314' {
                            attribute POIconv : String = "-";
                            attribute Ipoint : Boolean = false;
                            attribute mass : Real = 1.7958546002898366;
                            attribute sigma_mass : Real = 0.5781874454998993;
                            attribute Cx : Real = 60.63755914656309;
                            attribute sigma_Cx : Real = 21.524694958828086;
                            attribute Cy : Real = 15.842219085168598;
                            attribute sigma_Cy : Real = 22.8785482484388;
                            attribute Cz : Real = 4.7485692134678255;
                            attribute sigma_Cz : Real = 34.032610098790805;
                            attribute Ixx : Real = 17917.45625387959;
                            attribute sigma_Ixx : Real = 9076.090311991056;
                            attribute Iyy : Real = 18043.944202256862;
                            attribute sigma_Iyy : Real = 8528.689774687327;
                            attribute Izz : Real = 6163.264609493381;
                            attribute sigma_Izz : Real = 4367.524328529092;
                            attribute Ixy : Real = 1194.7412820112722;
                            attribute sigma_Ixy : Real = 1891.801224611495;
                            attribute Ixz : Real = 3122.107603884723;
                            attribute sigma_Ixz : Real = 3674.788828548101;
                            attribute Iyz : Real = -4764.752867149231;
                            attribute sigma_Iyz : Real = 4132.568516662501;
                            part <'C.1.2.3.2.4.5.1'> 'Part 1113' {
                                attribute POIconv : String = "+";
                                attribute Ipoint : Boolean = false;
                                attribute mass : Real = 0.7066141671736259;
                                attribute sigma_mass : Real = 0.28909372274994966;
                                attribute Cx : Real = 89.06655050814152;
                                attribute sigma_Cx : Real = 28.721044428837228;
                                attribute Cy : Real = -31.84382147155702;
                                attribute sigma_Cy : Real = 28.23690002309109;
                                attribute Cz : Real = -96.88437008298934;
                                attribute sigma_Cz : Real = 29.057750463592832;
                                attribute Ixx : Real = 0.74219272866924;
                                attribute sigma_Ixx : Real = 0.37074144170588635;
                                attribute Iyy : Real = 0.7310644097280373;
                                attribute sigma_Iyy : Real = 0.3723953238821935;
                                attribute Izz : Real = 0.7316206503994653;
                                attribute sigma_Izz : Real = 0.37017423652493897;
                                attribute Ixy : Real = 0.0025341132894404006;
                                attribute sigma_Ixy : Real = 0.02351283871158888;
                                attribute Ixz : Real = 0.001922566306612992;
                                attribute sigma_Ixz : Real = 0.022566176940390956;
                                attribute Iyz : Real = 2.4552321915932155e-05;
                                attribute sigma_Iyz : Real = 0.02209918015384651;
                            }
                            part <'C.1.2.3.2.4.5.2'> 'Part 1114' {
                                attribute POIconv : String = "+";
                                attribute Ipoint : Boolean = false;
                                attribute mass : Real = 0.41636258010845634;
                                attribute sigma_mass : Real = 0.28909372274994966;
                                attribute Cx : Real = -11.276261461898685;
                                attribute sigma_Cx : Real = 28.721044428837228;
                                attribute Cy : Real = 29.970974940806627;
                                attribute sigma_Cy : Real = 28.23690002309109;
                                attribute Cz : Real = 87.68960488960147;
                                attribute sigma_Cz : Real = 29.057750463592832;
                                attribute Ixx : Real = 0.5636588883307363;
                                attribute sigma_Ixx : Real = 0.37074144170588635;
                                attribute Iyy : Real = 0.5590741487674599;
                                attribute sigma_Iyy : Real = 0.3723953238821935;
                                attribute Izz : Real = 0.6030087155458527;
                                attribute sigma_Izz : Real = 0.37017423652493897;
                                attribute Ixy : Real = 0.010506020988205859;
                                attribute sigma_Ixy : Real = 0.02351283871158888;
                                attribute Ixz : Real = -0.038231433474013754;
                                attribute sigma_Ixz : Real = 0.022566176940390956;
                                attribute Iyz : Real = -0.029167939537512066;
                                attribute sigma_Iyz : Real = 0.02209918015384651;
                            }
                            part <'C.1.2.3.2.4.5.3'> 'Part 1115' {
                                attribute POIconv : String = "+";
                                attribute Ipoint : Boolean = false;
                                attribute mass : Real = 0.5816145352178719;
                                attribute sigma_mass : Real = 0.28909372274994966;
                                attribute Cx : Real = 83.29264703206718;
                                attribute sigma_Cx : Real = 28.721044428837228;
                                attribute Cy : Real = 50.73892958462238;
                                attribute sigma_Cy : Real = 28.23690002309109;
                                attribute Cz : Real = 85.10421188548207;
                                attribute sigma_Cz : Real = 29.057750463592832;
                                attribute Ixx : Real = 0.8211560207005684;
                                attribute sigma_Ixx : Real = 0.37074144170588635;
                                attribute Iyy : Real = 0.7493723798815796;
                                attribute sigma_Iyy : Real = 0.3723953238821935;
                                attribute Izz : Real = 0.7222445548861581;
                                attribute sigma_Izz : Real = 0.37017423652493897;
                                attribute Ixy : Real = 0.05420213167923642;
                                attribute sigma_Ixy : Real = 0.02351283871158888;
                                attribute Ixz : Real = -0.008305300103981457;
                                attribute sigma_Ixz : Real = 0.022566176940390956;
                                attribute Iyz : Real = 0.002751495075160395;
                                attribute sigma_Iyz : Real = 0.02209918015384651;
                            }
                            part <'C.1.2.3.2.4.5.4'> 'Part 1116' {
                                attribute POIconv : String = "+";
                                attribute Ipoint : Boolean = false;
                                attribute mass : Real = 0.09126331778988242;
                                attribute sigma_mass : Real = 0.28909372274994966;
                                attribute Cx : Real = 24.23046096228063;
                                attribute sigma_Cx : Real = 28.721044428837228;
                                attribute Cy : Real = 98.20293877273798;
                                attribute sigma_Cy : Real = 28.23690002309109;
                                attribute Cz : Real = -98.84484428912401;
                                attribute sigma_Cz : Real = 29.057750463592832;
                                attribute Ixx : Real = 0.11036362834762625;
                                attribute sigma_Ixx : Real = 0.37074144170588635;
                                attribute Iyy : Real = 0.12282192603579145;
                                attribute sigma_Iyy : Real = 0.3723953238821935;
                                attribute Izz : Real = 0.10383856477144217;
                                attribute sigma_Izz : Real = 0.37017423652493897;
                                attribute Ixy : Real = 0.0075857185307616065;
                                attribute sigma_Ixy : Real = 0.02351283871158888;
                                attribute Ixz : Real = 0.0006377065400574866;
                                attribute sigma_Ixz : Real = 0.022566176940390956;
                                attribute Iyz : Real = 0.005336207085140968;
                                attribute sigma_Iyz : Real = 0.02209918015384651;
                            }
                        }
                    }
                    part <'C.1.2.3.2.5'> 'Assembly 92' {
                        attribute POIconv : String = "-";
                        attribute Ipoint : Boolean = false;
                        attribute mass : Real = 2.038030791268917;
                        attribute sigma_mass : Real = 0.7081321085790055;
                        attribute Cx : Real = -6.811046374858961;
                        attribute sigma_Cx : Real = 23.117193210790276;
                        attribute Cy : Real = -30.530810687300576;
                        attribute sigma_Cy : Real = 28.182974411859043;
                        attribute Cz : Real = -20.701598333039097;
                        attribute sigma_Cz : Real = 20.84972983173966;
                        attribute Ixx : Real = 8486.29125548789;
                        attribute sigma_Ixx : Real = 7009.91075429886;
                        attribute Iyy : Real = 4563.596698974657;
                        attribute sigma_Iyy : Real = 5057.886617162179;
                        attribute Izz : Real = 10768.52576904994;
                        attribute sigma_Izz : Real = 7200.090493184339;
                        attribute Ixy : Real = 3220.5693196465727;
                        attribute sigma_Ixy : Real = 3467.8144612764086;
                        attribute Ixz : Real = -783.4422084290615;
                        attribute sigma_Ixz : Real = 2372.6464854418846;
                        attribute Iyz : Real = 1003.2079345508293;
                        attribute sigma_Iyz : Real = 3233.6919401572563;
                        part <'C.1.2.3.2.5.1'> 'Subassembly 315' {
                            attribute POIconv : String = "-";
                            attribute Ipoint : Boolean = false;
                            attribute mass : Real = 1.0252855565259233;
                            attribute sigma_mass : Real = 0.5781874454998993;
                            attribute Cx : Real = -29.087985268229396;
                            attribute sigma_Cx : Real = 36.18244838076031;
                            attribute Cy : Real = 16.002162343007893;
                            attribute sigma_Cy : Real = 38.6327047742183;
                            attribute Cz : Real = -16.469016039825807;
                            attribute sigma_Cz : Real = 33.841184768195916;
                            attribute Ixx : Real = 3767.392558944765;
                            attribute sigma_Ixx : Real = 5202.907493395259;
                            attribute Iyy : Real = 3462.451677942367;
                            attribute sigma_Iyy : Real = 4619.1694245748995;
                            attribute Izz : Real = 5024.882010092389;
                            attribute sigma_Izz : Real = 4971.868435729782;
                            attribute Ixy : Real = 991.2902620770383;
                            attribute sigma_Ixy : Real = 2450.31231959352;
                            attribute Ixz : Real = -983.068409261185;
                            attribute sigma_Ixz : Real = 2163.303295443193;
                            attribute Iyz : Real = 1421.3925672962232;
                            attribute sigma_Iyz : Real = 2533.2585699694514;
                            part <'C.1.2.3.2.5.1.1'> 'Part 1117' {
                                attribute POIconv : String = "+";
                                attribute Ipoint : Boolean = false;
                                attribute mass : Real = 0.47044576397631316;
                                attribute sigma_mass : Real = 0.28909372274994966;
                                attribute Cx : Real = 2.569628646597266;
                                attribute sigma_Cx : Real = 28.721044428837228;
                                attribute Cy : Real = -32.78453899547458;
                                attribute sigma_Cy : Real = 28.23690002309109;
                                attribute Cz : Real = 6.346535868942738;
                                attribute sigma_Cz : Real = 29.057750463592832;
                                attribute Ixx : Real = 0.6435109223521447;
                                attribute sigma_Ixx : Real = 0.37074144170588635;
                                attribute Iyy : Real = 0.6319281439582822;
                                attribute sigma_Iyy : Real = 0.3723953238821935;
                                attribute Izz : Real = 0.635749727032682;
                                attribute sigma_Izz : Real = 0.37017423652493897;
                                attribute Ixy : Real = -0.009649223272934833;
                                attribute sigma_Ixy : Real = 0.02351283871158888;
                                attribute Ixz : Real = -0.004767302061863253;
                                attribute sigma_Ixz : Real = 0.022566176940390956;
                                attribute Iyz : Real = 0.006933716334258468;
                                attribute sigma_Iyz : Real = 0.02209918015384651;
                            }
                            part <'C.1.2.3.2.5.1.2'> 'Part 1118' {
                                attribute POIconv : String = "-";
                                attribute Ipoint : Boolean = false;
                                attribute mass : Real = 0.37974785833922214;
                                attribute sigma_mass : Real = 0.28909372274994966;
                                attribute Cx : Real = -85.01557409763336;
                                attribute sigma_Cx : Real = 28.721044428837228;
                                attribute Cy : Real = 62.093520956113935;
                                attribute sigma_Cy : Real = 28.23690002309109;
                                attribute Cz : Real = -54.929202469065785;
                                attribute sigma_Cz : Real = 29.057750463592832;
                                attribute Ixx : Real = 0.5849535482464808;
                                attribute sigma_Ixx : Real = 0.37074144170588635;
                                attribute Iyy : Real = 0.5346327766143826;
                                attribute sigma_Iyy : Real = 0.3723953238821935;
                                attribute Izz : Real = 0.5736480168125648;
                                attribute sigma_Izz : Real = 0.37017423652493897;
                                attribute Ixy : Real = 0.00890710336288442;
                                attribute sigma_Ixy : Real = 0.02351283871158888;
                                attribute Ixz : Real = 0.004345863693145809;
                                attribute sigma_Ixz : Real = 0.022566176940390956;
                                attribute Iyz : Real = -0.004018970593441017;
                                attribute sigma_Iyz : Real = 0.02209918015384651;
                            }
                            part <'C.1.2.3.2.5.1.3'> 'Part 1119' {
                                attribute POIconv : String = "-";
                                attribute Ipoint : Boolean = false;
                                attribute mass : Real = 0.14067737479438075;
                                attribute sigma_mass : Real = 0.28909372274994966;
                                attribute Cx : Real = 32.7779624145478;
                                attribute sigma_Cx : Real = 28.721044428837228;
                                attribute Cy : Real = 75.29446827247739;
                                attribute sigma_Cy : Real = 28.23690002309109;
                                attribute Cz : Real = -11.46841049194336;
                                attribute sigma_Cz : Real = 29.057750463592832;
                                attribute Ixx : Real = 0.15892723039233403;
                                attribute sigma_Ixx : Real = 0.37074144170588635;
                                attribute Iyy : Real = 0.1678808983553926;
                                attribute sigma_Iyy : Real = 0.3723953238821935;
                                attribute Izz : Real = 0.17775567616954238;
                                attribute sigma_Izz : Real = 0.37017423652493897;
                                attribute Ixy : Real = 0.0018071040092204952;
                                attribute sigma_Ixy : Real = 0.02351283871158888;
                                attribute Ixz : Real = -0.001680649506816778;
                                attribute sigma_Ixz : Real = 0.022566176940390956;
                                attribute Iyz : Real = -0.014830472293822429;
                                attribute sigma_Iyz : Real = 0.02209918015384651;
                            }
                            part <'C.1.2.3.2.5.1.4'> 'Part 1120' {
                                attribute POIconv : String = "+";
                                attribute Ipoint : Boolean = false;
                                attribute mass : Real = 0.034414559416007254;
                                attribute sigma_mass : Real = 0.28909372274994966;
                                attribute Cx : Real = -97.60396899655461;
                                attribute sigma_Cx : Real = 28.721044428837228;
                                attribute Cy : Real = -68.05190462619066;
                                attribute sigma_Cy : Real = 28.23690002309109;
                                attribute Cz : Real = 75.59148604050279;
                                attribute sigma_Cz : Real = 29.057750463592832;
                                attribute Ixx : Real = 0.038059115816056935;
                                attribute sigma_Ixx : Real = 0.37074144170588635;
                                attribute Iyy : Real = 0.044014803362034095;
                                attribute sigma_Iyy : Real = 0.3723953238821935;
                                attribute Izz : Real = 0.042160093414771393;
                                attribute sigma_Izz : Real = 0.37017423652493897;
                                attribute Ixy : Real = 0.0013617379503700182;
                                attribute sigma_Ixy : Real = 0.02351283871158888;
                                attribute Ixz : Real = 0.000204852444372326;
                                attribute sigma_Ixz : Real = 0.022566176940390956;
                                attribute Iyz : Real = -0.0035621184285471457;
                                attribute sigma_Iyz : Real = 0.02209918015384651;
                            }
                        }
                        part <'C.1.2.3.2.5.2'> 'Subassembly 316' {
                            attribute POIconv : String = "-";
                            attribute Ipoint : Boolean = false;
                            attribute mass : Real = 1.0127452347429935;
                            attribute sigma_mass : Real = 0.40884026350990615;
                            attribute Cx : Real = 15.741736800447221;
                            attribute sigma_Cx : Real = 24.03612450786456;
                            attribute Cy : Real = -77.63997843598217;
                            attribute sigma_Cy : Real = 24.889149554774882;
                            attribute Cz : Real = -24.98659059285479;
                            attribute sigma_Cz : Real = 24.03847958382428;
                            attribute Ixx : Real = 214.30809409305573;
                            attribute sigma_Ixx : Real = 528.6440630270032;
                            attribute Iyy : Real = 40.261227669929454;
                            attribute sigma_Iyy : Real = 208.52124438057635;
                            attribute Izz : Real = 252.09518976347206;
                            attribute sigma_Izz : Real = 586.0170497766333;
                            attribute Ixy : Real = 90.47161527485252;
                            attribute sigma_Ixy : Real = 277.60502572846815;
                            attribute Ixz : Real = 5.082892736314571;
                            attribute sigma_Ixz : Real = 103.03589697563935;
                            attribute Iyz : Real = -11.814684334603543;
                            attribute sigma_Iyz : Real = 240.29850295681808;
                            part <'C.1.2.3.2.5.2.1'> 'Part 1121' {
                                attribute POIconv : String = "+";
                                attribute Ipoint : Boolean = false;
                                attribute mass : Real = 0.8136336002105381;
                                attribute sigma_mass : Real = 0.28909372274994966;
                                attribute Cx : Real = 18.792902631685138;
                                attribute sigma_Cx : Real = 28.721044428837228;
                                attribute Cy : Real = -84.80450455099344;
                                attribute sigma_Cy : Real = 28.23690002309109;
                                attribute Cz : Real = -25.386005640029907;
                                attribute sigma_Cz : Real = 29.057750463592832;
                                attribute Ixx : Real = 0.9875334638584475;
                                attribute sigma_Ixx : Real = 0.37074144170588635;
                                attribute Iyy : Real = 0.8492803765609918;
                                attribute sigma_Iyy : Real = 0.3723953238821935;
                                attribute Izz : Real = 0.9176661921602746;
                                attribute sigma_Izz : Real = 0.37017423652493897;
                                attribute Ixy : Real = -0.02184093446547435;
                                attribute sigma_Ixy : Real = 0.02351283871158888;
                                attribute Ixz : Real = -0.011531735642302495;
                                attribute sigma_Ixz : Real = 0.022566176940390956;
                                attribute Iyz : Real = -0.006885765518491183;
                                attribute sigma_Iyz : Real = 0.02209918015384651;
                            }
                            part <'C.1.2.3.2.5.2.2'> 'Part 1122' {
                                attribute POIconv : String = "+";
                                attribute Ipoint : Boolean = false;
                                attribute mass : Real = 0.19911163453245537;
                                attribute sigma_mass : Real = 0.28909372274994966;
                                attribute Cx : Real = 3.27370073646307;
                                attribute sigma_Cx : Real = 28.721044428837228;
                                attribute Cy : Real = -48.36344122886658;
                                attribute sigma_Cy : Real = 28.23690002309109;
                                attribute Cz : Real = -23.354453407227993;
                                attribute sigma_Cz : Real = 29.057750463592832;
                                attribute Ixx : Real = 0.23449143385256138;
                                attribute sigma_Ixx : Real = 0.37074144170588635;
                                attribute Iyy : Real = 0.22483809930691548;
                                attribute sigma_Iyy : Real = 0.3723953238821935;
                                attribute Izz : Real = 0.2247627247990798;
                                attribute sigma_Izz : Real = 0.37017423652493897;
                                attribute Ixy : Real = 0.016296491388182663;
                                attribute sigma_Ixy : Real = 0.02351283871158888;
                                attribute Ixz : Real = -0.027969523137785075;
                                attribute sigma_Ixz : Real = 0.022566176940390956;
                                attribute Iyz : Real = -0.020955658093139956;
                                attribute sigma_Iyz : Real = 0.02209918015384651;
                            }
                        }
                    }
                }
                part <'C.1.2.3.3'> 'Subsystem 25' {
                    attribute POIconv : String = "-";
                    attribute Ipoint : Boolean = false;
                    attribute mass : Real = 36.71120201082737;
                    attribute sigma_mass : Real = 2.4868782357553076;
                    attribute Cx : Real = 5.363728418872687;
                    attribute sigma_Cx : Real = 5.9286890949803395;
                    attribute Cy : Real = 8.340790241562955;
                    attribute sigma_Cy : Real = 5.470763709568985;
                    attribute Cz : Real = 3.2593801364735255;
                    attribute sigma_Cz : Real = 5.858677665152858;
                    attribute Ixx : Real = 222586.51951170596;
                    attribute sigma_Ixx : Real = 31368.932743108522;
                    attribute Iyy : Real = 264638.90687225317;
                    attribute sigma_Iyy : Real = 33671.1285995715;
                    attribute Izz : Real = 243881.2293606433;
                    attribute sigma_Izz : Real = 31434.476085810278;
                    attribute Ixy : Real = -37367.19490494017;
                    attribute sigma_Ixy : Real = 14795.997954843384;
                    attribute Ixz : Real = -8402.452322677242;
                    attribute sigma_Ixz : Real = 15945.269834784256;
                    attribute Iyz : Real = -8708.654722302814;
                    attribute sigma_Iyz : Real = 14693.642428488249;
                    part <'C.1.2.3.3.1'> 'Assembly 93' {
                        attribute POIconv : String = "-";
                        attribute Ipoint : Boolean = false;
                        attribute mass : Real = 3.013570448651211;
                        attribute sigma_mass : Real = 0.6464332159373648;
                        attribute Cx : Real = 1.0950454682931368;
                        attribute sigma_Cx : Real = 18.334983849706994;
                        attribute Cy : Real = 33.62235263370719;
                        attribute sigma_Cy : Real = 19.668592313592633;
                        attribute Cz : Real = -9.591390795381377;
                        attribute sigma_Cz : Real = 16.817121386371614;
                        attribute Ixx : Real = 16220.609296735973;
                        attribute sigma_Ixx : Real = 7274.866193599415;
                        attribute Iyy : Real = 15535.496354446926;
                        attribute sigma_Iyy : Real = 6910.581212964983;
                        attribute Izz : Real = 19990.066609202942;
                        attribute sigma_Izz : Real = 8221.607278910702;
                        attribute Ixy : Real = 4037.4030346709274;
                        attribute sigma_Ixy : Real = 3810.3682174428354;
                        attribute Ixz : Real = 6632.402311887588;
                        attribute sigma_Ixz : Real = 3413.471295883863;
                        attribute Iyz : Real = -3318.1486214833103;
                        attribute sigma_Iyz : Real = 3334.5518242901117;
                        part <'C.1.2.3.3.1.1'> 'Subassembly 317' {
                            attribute POIconv : String = "-";
                            attribute Ipoint : Boolean = false;
                            attribute mass : Real = 1.3032310264068656;
                            attribute sigma_mass : Real = 0.40884026350990615;
                            attribute Cx : Real = -52.29360948806616;
                            attribute sigma_Cx : Real = 24.845297135566412;
                            attribute Cy : Real = 46.509223732724344;
                            attribute sigma_Cy : Real = 25.988168444808615;
                            attribute Cz : Real = 38.23815728054734;
                            attribute sigma_Cz : Real = 21.57111749684718;
                            attribute Ixx : Real = 3889.8008346278857;
                            attribute sigma_Ixx : Real = 3114.6767437357253;
                            attribute Iyy : Real = 2969.0627499678876;
                            attribute sigma_Iyy : Real = 2698.9795409491708;
                            attribute Izz : Real = 5955.534345020958;
                            attribute sigma_Izz : Real = 4043.085660108773;
                            attribute Ixy : Real = 2941.0783665443373;
                            attribute sigma_Ixy : Real = 2019.6083245783104;
                            attribute Ixz : Real = 1065.2008261269525;
                            attribute sigma_Ixz : Real = 1313.6591230224224;
                            attribute Iyz : Real = -1244.8284825437406;
                            attribute sigma_Iyz : Real = 1503.9938230162595;
                            part <'C.1.2.3.3.1.1.1'> 'Part 1123' {
                                attribute POIconv : String = "-";
                                attribute Ipoint : Boolean = false;
                                attribute mass : Real = 0.7402315276924055;
                                attribute sigma_mass : Real = 0.28909372274994966;
                                attribute Cx : Real = -90.6176423188299;
                                attribute sigma_Cx : Real = 28.721044428837228;
                                attribute Cy : Real = 91.29746346734464;
                                attribute sigma_Cy : Real = 28.23690002309109;
                                attribute Cz : Real = 54.458841728046536;
                                attribute sigma_Cz : Real = 29.057750463592832;
                                attribute Ixx : Real = 1.0179245101354817;
                                attribute sigma_Ixx : Real = 0.37074144170588635;
                                attribute Iyy : Real = 0.9064378212625557;
                                attribute sigma_Iyy : Real = 0.3723953238821935;
                                attribute Izz : Real = 0.9961967172515375;
                                attribute sigma_Izz : Real = 0.37017423652493897;
                                attribute Ixy : Real = -0.04097862941807292;
                                attribute sigma_Ixy : Real = 0.02351283871158888;
                                attribute Ixz : Real = 0.011574126188077617;
                                attribute sigma_Ixz : Real = 0.022566176940390956;
                                attribute Iyz : Real = -0.05094899777544264;
                                attribute sigma_Iyz : Real = 0.02209918015384651;
                            }
                            part <'C.1.2.3.3.1.1.2'> 'Part 1124' {
                                attribute POIconv : String = "-";
                                attribute Ipoint : Boolean = false;
                                attribute mass : Real = 0.5629994987144601;
                                attribute sigma_mass : Real = 0.28909372274994966;
                                attribute Cx : Real = -1.9051856361329556;
                                attribute sigma_Cx : Real = 28.721044428837228;
                                attribute Cy : Real = -12.37833690829575;
                                attribute sigma_Cy : Real = 28.23690002309109;
                                attribute Cz : Real = 16.911207512021065;
                                attribute sigma_Cz : Real = 29.057750463592832;
                                attribute Ixx : Real = 0.7131628517514028;
                                attribute sigma_Ixx : Real = 0.37074144170588635;
                                attribute Iyy : Real = 0.666251029176459;
                                attribute sigma_Iyy : Real = 0.3723953238821935;
                                attribute Izz : Real = 0.6518860524368141;
                                attribute sigma_Izz : Real = 0.37017423652493897;
                                attribute Ixy : Real = -0.02391320703225242;
                                attribute sigma_Ixy : Real = 0.02351283871158888;
                                attribute Ixz : Real = 0.013281885385761378;
                                attribute sigma_Ixz : Real = 0.022566176940390956;
                                attribute Iyz : Real = 0.06423244867076075;
                                attribute sigma_Iyz : Real = 0.02209918015384651;
                            }
                        }
                        part <'C.1.2.3.3.1.2'> 'Subassembly 318' {
                            attribute POIconv : String = "-";
                            attribute Ipoint : Boolean = false;
                            attribute mass : Real = 1.7103394222443455;
                            attribute sigma_mass : Real = 0.5007250159521434;
                            attribute Cx : Real = 41.775714283116244;
                            attribute sigma_Cx : Real = 19.50763578882284;
                            attribute Cy : Real = 23.802915607864158;
                            attribute sigma_Cy : Real = 28.12687837010379;
                            attribute Cz : Real = -46.03617492470608;
                            attribute sigma_Cz : Real = 19.06021663764367;
                            attribute Ixx : Real = 6696.397952629056;
                            attribute sigma_Ixx : Real = 5212.946925567446;
                            attribute Iyy : Real = 768.2337396374126;
                            attribute sigma_Iyy : Real = 1275.7637251050558;
                            attribute Izz : Real = 7108.057534997828;
                            attribute sigma_Izz : Real = 5289.75215872323;
                            attribute Ixy : Real = -483.52919827573606;
                            attribute sigma_Ixy : Real = 1714.660470599104;
                            attribute Ixz : Real = -296.41706644129664;
                            attribute sigma_Ixz : Real = 629.8557025614542;
                            attribute Iyz : Real = -657.9689464849398;
                            attribute sigma_Iyz : Real = 1682.2462537405884;
                            part <'C.1.2.3.3.1.2.1'> 'Part 1125' {
                                attribute POIconv : String = "+";
                                attribute Ipoint : Boolean = false;
                                attribute mass : Real = 0.9771186153339222;
                                attribute sigma_mass : Real = 0.28909372274994966;
                                attribute Cx : Real = 56.416200241073966;
                                attribute sigma_Cx : Real = 28.721044428837228;
                                attribute Cy : Real = 57.22544393502176;
                                attribute sigma_Cy : Real = 28.23690002309109;
                                attribute Cz : Real = -37.21758299507201;
                                attribute sigma_Cz : Real = 29.057750463592832;
                                attribute Ixx : Real = 1.2044085430831106;
                                attribute sigma_Ixx : Real = 0.37074144170588635;
                                attribute Iyy : Real = 0.9881488738740569;
                                attribute sigma_Iyy : Real = 0.3723953238821935;
                                attribute Izz : Real = 1.1867021157945699;
                                attribute sigma_Izz : Real = 0.37017423652493897;
                                attribute Ixy : Real = -0.06383660530983334;
                                attribute sigma_Ixy : Real = 0.02351283871158888;
                                attribute Ixz : Real = -0.02092339044913391;
                                attribute sigma_Ixz : Real = 0.022566176940390956;
                                attribute Iyz : Real = 0.04866868527405713;
                                attribute sigma_Iyz : Real = 0.02209918015384651;
                            }
                            part <'C.1.2.3.3.1.2.2'> 'Part 1126' {
                                attribute POIconv : String = "-";
                                attribute Ipoint : Boolean = false;
                                attribute mass : Real = 0.3694087115677539;
                                attribute sigma_mass : Real = 0.28909372274994966;
                                attribute Cx : Real = 10.647061048075557;
                                attribute sigma_Cx : Real = 28.721044428837228;
                                attribute Cy : Real = 52.2939610760659;
                                attribute sigma_Cy : Real = 28.23690002309109;
                                attribute Cz : Real = -58.04320606403053;
                                attribute sigma_Cz : Real = 29.057750463592832;
                                attribute Ixx : Real = 0.5275253429735705;
                                attribute sigma_Ixx : Real = 0.37074144170588635;
                                attribute Iyy : Real = 0.5194531474684527;
                                attribute sigma_Iyy : Real = 0.3723953238821935;
                                attribute Izz : Real = 0.4912565970207912;
                                attribute sigma_Izz : Real = 0.37017423652493897;
                                attribute Ixy : Real = -0.015045108692227315;
                                attribute sigma_Ixy : Real = 0.02351283871158888;
                                attribute Ixz : Real = 0.007796659230711382;
                                attribute sigma_Ixz : Real = 0.022566176940390956;
                                attribute Iyz : Real = 0.004199626118750391;
                                attribute sigma_Iyz : Real = 0.02209918015384651;
                            }
                            part <'C.1.2.3.3.1.2.3'> 'Part 1127' {
                                attribute POIconv : String = "+";
                                attribute Ipoint : Boolean = false;
                                attribute mass : Real = 0.3638120953426696;
                                attribute sigma_mass : Real = 0.28909372274994966;
                                attribute Cx : Real = 34.06212884001434;
                                attribute sigma_Cx : Real = 28.721044428837228;
                                attribute Cy : Real = -94.89191491156816;
                                attribute sigma_Cy : Real = 28.23690002309109;
                                attribute Cz : Real = -57.52921896055341;
                                attribute sigma_Cz : Real = 29.057750463592832;
                                attribute Ixx : Real = 0.4424417369904654;
                                attribute sigma_Ixx : Real = 0.37074144170588635;
                                attribute Iyy : Real = 0.3844101733738442;
                                attribute sigma_Iyy : Real = 0.3723953238821935;
                                attribute Izz : Real = 0.41688282310939734;
                                attribute sigma_Izz : Real = 0.37017423652493897;
                                attribute Ixy : Real = -0.016384025792099875;
                                attribute sigma_Ixy : Real = 0.02351283871158888;
                                attribute Ixz : Real = -0.032584746128578854;
                                attribute sigma_Ixz : Real = 0.022566176940390956;
                                attribute Iyz : Real = 0.0012805385570121056;
                                attribute sigma_Iyz : Real = 0.02209918015384651;
                            }
                        }
                    }
                    part <'C.1.2.3.3.2'> 'Assembly 94' {
                        attribute POIconv : String = "-";
                        attribute Ipoint : Boolean = false;
                        attribute mass : Real = 6.994009743188276;
                        attribute sigma_mass : Real = 1.2265207905297184;
                        attribute Cx : Real = 22.818601001153926;
                        attribute sigma_Cx : Real = 13.674928078784607;
                        attribute Cy : Real = -2.1058372334447513;
                        attribute sigma_Cy : Real = 14.742746401746118;
                        attribute Cz : Real = 27.85713770331337;
                        attribute sigma_Cz : Real = 16.432191955294783;
                        attribute Ixx : Real = 69924.37677360977;
                        attribute sigma_Ixx : Real = 19163.02591508451;
                        attribute Iyy : Real = 66443.03138452004;
                        attribute sigma_Iyy : Real = 16910.945364592084;
                        attribute Izz : Real = 58960.31430692395;
                        attribute sigma_Izz : Real = 15362.345793726496;
                        attribute Ixy : Real = -919.4439196968191;
                        attribute sigma_Ixy : Real = 7389.219258620669;
                        attribute Ixz : Real = -8758.994893247298;
                        attribute sigma_Ixz : Real = 8017.046408673966;
                        attribute Iyz : Real = 2892.0944393068676;
                        attribute sigma_Iyz : Real = 9141.87054467528;
                        part <'C.1.2.3.3.2.1'> 'Subassembly 319' {
                            attribute POIconv : String = "-";
                            attribute Ipoint : Boolean = false;
                            attribute mass : Real = 1.7521341340888759;
                            attribute sigma_mass : Real = 0.6464332159373649;
                            attribute Cx : Real = 0.39095172459322103;
                            attribute sigma_Cx : Real = 27.167413503430062;
                            attribute Cy : Real = 22.659978155739566;
                            attribute sigma_Cy : Real = 28.96162247019863;
                            attribute Cz : Real = -50.28570616374343;
                            attribute sigma_Cz : Real = 22.78783168919484;
                            attribute Ixx : Real = 12139.830695881159;
                            attribute sigma_Ixx : Real = 7298.314831625293;
                            attribute Iyy : Real = 11456.11022875456;
                            attribute sigma_Iyy : Real = 5915.598588212442;
                            attribute Izz : Real = 16003.754872240099;
                            attribute sigma_Izz : Real = 7649.848442762005;
                            attribute Ixy : Real = 5997.172188430665;
                            attribute sigma_Ixy : Real = 3427.739556447071;
                            attribute Ixz : Real = -1210.4871429384668;
                            attribute sigma_Ixz : Real = 2227.195528317549;
                            attribute Iyz : Real = 4086.1600699315386;
                            attribute sigma_Iyz : Real = 3537.7640240732453;
                            part <'C.1.2.3.3.2.1.1'> 'Part 1128' {
                                attribute POIconv : String = "+";
                                attribute Ipoint : Boolean = false;
                                attribute mass : Real = 0.300287495268276;
                                attribute sigma_mass : Real = 0.28909372274994966;
                                attribute Cx : Real = 68.32964611239731;
                                attribute sigma_Cx : Real = 28.721044428837228;
                                attribute Cy : Real = 3.152820374816656;
                                attribute sigma_Cy : Real = 28.23690002309109;
                                attribute Cz : Real = -66.47687186487019;
                                attribute sigma_Cz : Real = 29.057750463592832;
                                attribute Ixx : Real = 0.36934015848696866;
                                attribute sigma_Ixx : Real = 0.37074144170588635;
                                attribute Iyy : Real = 0.33326036779988943;
                                attribute sigma_Iyy : Real = 0.3723953238821935;
                                attribute Izz : Real = 0.4384724295112993;
                                attribute sigma_Izz : Real = 0.37017423652493897;
                                attribute Ixy : Real = -0.005957327785694725;
                                attribute sigma_Ixy : Real = 0.02351283871158888;
                                attribute Ixz : Real = -0.005763712398440347;
                                attribute sigma_Ixz : Real = 0.022566176940390956;
                                attribute Iyz : Real = 0.02152417654744623;
                                attribute sigma_Iyz : Real = 0.02209918015384651;
                            }
                            part <'C.1.2.3.3.2.1.2'> 'Part 1129' {
                                attribute POIconv : String = "+";
                                attribute Ipoint : Boolean = false;
                                attribute mass : Real = 0.6313118730988353;
                                attribute sigma_mass : Real = 0.28909372274994966;
                                attribute Cx : Real = -65.77382539398968;
                                attribute sigma_Cx : Real = 28.721044428837228;
                                attribute Cy : Real = 92.49089434742928;
                                attribute sigma_Cy : Real = 28.23690002309109;
                                attribute Cz : Real = -93.92624609172344;
                                attribute sigma_Cz : Real = 29.057750463592832;
                                attribute Ixx : Real = 0.9052151271990161;
                                attribute sigma_Ixx : Real = 0.37074144170588635;
                                attribute Iyy : Real = 0.9188131205196788;
                                attribute sigma_Iyy : Real = 0.3723953238821935;
                                attribute Izz : Real = 0.8429030930681655;
                                attribute sigma_Izz : Real = 0.37017423652493897;
                                attribute Ixy : Real = 0.0577147169741431;
                                attribute sigma_Ixy : Real = 0.02351283871158888;
                                attribute Ixz : Real = -0.0010377715377740677;
                                attribute sigma_Ixz : Real = 0.022566176940390956;
                                attribute Iyz : Real = 0.0005588881213690777;
                                attribute sigma_Iyz : Real = 0.02209918015384651;
                            }
                            part <'C.1.2.3.3.2.1.3'> 'Part 1130' {
                                attribute POIconv : String = "+";
                                attribute Ipoint : Boolean = false;
                                attribute mass : Real = 0.3436191369073931;
                                attribute sigma_mass : Real = 0.28909372274994966;
                                attribute Cx : Real = 95.01519436016679;
                                attribute sigma_Cx : Real = 28.721044428837228;
                                attribute Cy : Real = -47.71872563287616;
                                attribute sigma_Cy : Real = 28.23690002309109;
                                attribute Cz : Real = -45.841980539262295;
                                attribute sigma_Cz : Real = 29.057750463592832;
                                attribute Ixx : Real = 0.42306059961619746;
                                attribute sigma_Ixx : Real = 0.37074144170588635;
                                attribute Iyy : Real = 0.43898016803194384;
                                attribute sigma_Iyy : Real = 0.3723953238821935;
                                attribute Izz : Real = 0.45376610250614074;
                                attribute sigma_Izz : Real = 0.37017423652493897;
                                attribute Ixy : Real = 0.050977190340680364;
                                attribute sigma_Ixy : Real = 0.02351283871158888;
                                attribute Ixz : Real = 0.01048526169886384;
                                attribute sigma_Ixz : Real = 0.022566176940390956;
                                attribute Iyz : Real = -0.01761748347598234;
                                attribute sigma_Iyz : Real = 0.02209918015384651;
                            }
                            part <'C.1.2.3.3.2.1.4'> 'Part 1131' {
                                attribute POIconv : String = "-";
                                attribute Ipoint : Boolean = false;
                                attribute mass : Real = 0.26585083035216667;
                                attribute sigma_mass : Real = 0.28909372274994966;
                                attribute Cx : Real = -6.060240929946303;
                                attribute sigma_Cx : Real = 28.721044428837228;
                                attribute Cy : Real = -77.85823168233037;
                                attribute sigma_Cy : Real = 28.23690002309109;
                                attribute Cz : Real = 43.523722840473056;
                                attribute sigma_Cz : Real = 29.057750463592832;
                                attribute Ixx : Real = 0.4129818329488012;
                                attribute sigma_Ixx : Real = 0.37074144170588635;
                                attribute Iyy : Real = 0.36396376179780493;
                                attribute sigma_Iyy : Real = 0.3723953238821935;
                                attribute Izz : Real = 0.35550458844387295;
                                attribute sigma_Izz : Real = 0.37017423652493897;
                                attribute Ixy : Real = -0.0211706853257008;
                                attribute sigma_Ixy : Real = 0.02351283871158888;
                                attribute Ixz : Real = -0.007904168998703706;
                                attribute sigma_Ixz : Real = 0.022566176940390956;
                                attribute Iyz : Real = -0.00010739461788334439;
                                attribute sigma_Iyz : Real = 0.02209918015384651;
                            }
                            part <'C.1.2.3.3.2.1.5'> 'Part 1132' {
                                attribute POIconv : String = "-";
                                attribute Ipoint : Boolean = false;
                                attribute mass : Real = 0.21106479846220463;
                                attribute sigma_mass : Real = 0.28909372274994966;
                                attribute Cx : Real = -44.2881076131016;
                                attribute sigma_Cx : Real = 28.721044428837228;
                                attribute Cy : Real = 82.73152085021138;
                                attribute sigma_Cy : Real = 28.23690002309109;
                                attribute Cz : Real = -22.1117430832237;
                                attribute sigma_Cz : Real = 29.057750463592832;
                                attribute Ixx : Real = 0.25086121241928727;
                                attribute sigma_Ixx : Real = 0.37074144170588635;
                                attribute Iyy : Real = 0.2923312086306453;
                                attribute sigma_Iyy : Real = 0.3723953238821935;
                                attribute Izz : Real = 0.2690899894141246;
                                attribute sigma_Izz : Real = 0.37017423652493897;
                                attribute Ixy : Real = 0.014416957482808924;
                                attribute sigma_Ixy : Real = 0.02351283871158888;
                                attribute Ixz : Real = 0.010783202443186918;
                                attribute sigma_Ixz : Real = 0.022566176940390956;
                                attribute Iyz : Real = 0.008936610454802823;
                                attribute sigma_Iyz : Real = 0.02209918015384651;
                            }
                        }
                        part <'C.1.2.3.3.2.2'> 'Subassembly 320' {
                            attribute POIconv : String = "-";
                            attribute Ipoint : Boolean = false;
                            attribute mass : Real = 0.5376748833898455;
                            attribute sigma_mass : Real = 0.5007250159521434;
                            attribute Cx : Real = -43.02588042548773;
                            attribute sigma_Cx : Real = 41.789910176381746;
                            attribute Cy : Real = -34.23106609672078;
                            attribute sigma_Cy : Real = 32.484518969591335;
                            attribute Cz : Real = -19.781540597229384;
                            attribute sigma_Cz : Real = 74.61862777245072;
                            attribute Ixx : Real = 3562.7050264516874;
                            attribute sigma_Ixx : Real = 4899.5555839028575;
                            attribute Iyy : Real = 3940.4355183276466;
                            attribute sigma_Iyy : Real = 4815.837670461734;
                            attribute Izz : Real = 1324.9163524454525;
                            attribute sigma_Izz : Real = 1621.86985239059;
                            attribute Ixy : Real = -55.81308366002236;
                            attribute sigma_Ixy : Real = 616.7141069132239;
                            attribute Ixz : Real = 424.2983445902372;
                            attribute sigma_Ixz : Real = 1421.5841678999986;
                            attribute Iyz : Real = 1190.2060657666862;
                            attribute sigma_Iyz : Real = 1694.2247565589003;
                            part <'C.1.2.3.3.2.2.1'> 'Part 1133' {
                                attribute POIconv : String = "+";
                                attribute Ipoint : Boolean = false;
                                attribute mass : Real = 0.16530295626493172;
                                attribute sigma_mass : Real = 0.28909372274994966;
                                attribute Cx : Real = 16.369473561644554;
                                attribute sigma_Cx : Real = 28.721044428837228;
                                attribute Cy : Real = -34.88249834626913;
                                attribute sigma_Cy : Real = 28.23690002309109;
                                attribute Cz : Real = -38.14453766681254;
                                attribute sigma_Cz : Real = 29.057750463592832;
                                attribute Ixx : Real = 0.25503409827761864;
                                attribute sigma_Ixx : Real = 0.37074144170588635;
                                attribute Iyy : Real = 0.2508321338514727;
                                attribute sigma_Iyy : Real = 0.3723953238821935;
                                attribute Izz : Real = 0.2349600814221059;
                                attribute sigma_Izz : Real = 0.37017423652493897;
                                attribute Ixy : Real = -0.001871789487561103;
                                attribute sigma_Ixy : Real = 0.02351283871158888;
                                attribute Ixz : Real = 4.500984796894639e-05;
                                attribute sigma_Ixz : Real = 0.022566176940390956;
                                attribute Iyz : Real = -0.003602639942466051;
                                attribute sigma_Iyz : Real = 0.02209918015384651;
                            }
                            part <'C.1.2.3.3.2.2.2'> 'Part 1134' {
                                attribute POIconv : String = "+";
                                attribute Ipoint : Boolean = false;
                                attribute mass : Real = 0.21987718947092072;
                                attribute sigma_mass : Real = 0.28909372274994966;
                                attribute Cx : Real = -65.31264008954167;
                                attribute sigma_Cx : Real = 28.721044428837228;
                                attribute Cy : Real = -4.255700530484319;
                                attribute sigma_Cy : Real = 28.23690002309109;
                                attribute Cz : Real = -86.48242908529937;
                                attribute sigma_Cz : Real = 29.057750463592832;
                                attribute Ixx : Real = 0.29381339334264334;
                                attribute sigma_Ixx : Real = 0.37074144170588635;
                                attribute Iyy : Real = 0.31808276140654207;
                                attribute sigma_Iyy : Real = 0.3723953238821935;
                                attribute Izz : Real = 0.28945871052345834;
                                attribute sigma_Izz : Real = 0.37017423652493897;
                                attribute Ixy : Real = 0.017812997157717874;
                                attribute sigma_Ixy : Real = 0.02351283871158888;
                                attribute Ixz : Real = 0.00020626148078625102;
                                attribute sigma_Ixz : Real = 0.022566176940390956;
                                attribute Iyz : Real = -8.951390882603949e-05;
                                attribute sigma_Iyz : Real = 0.02209918015384651;
                            }
                            part <'C.1.2.3.3.2.2.3'> 'Part 1135' {
                                attribute POIconv : String = "-";
                                attribute Ipoint : Boolean = false;
                                attribute mass : Real = 0.15249473765399307;
                                attribute sigma_mass : Real = 0.28909372274994966;
                                attribute Cx : Real = -75.27537047863007;
                                attribute sigma_Cx : Real = 28.721044428837228;
                                attribute Cy : Real = -76.74542139284313;
                                attribute sigma_Cy : Real = 28.23690002309109;
                                attribute Cz : Real = 96.29762298427522;
                                attribute sigma_Cz : Real = 29.057750463592832;
                                attribute Ixx : Real = 0.1452462579879769;
                                attribute sigma_Ixx : Real = 0.37074144170588635;
                                attribute Iyy : Real = 0.15108497357480608;
                                attribute sigma_Iyy : Real = 0.3723953238821935;
                                attribute Izz : Real = 0.15837791424322542;
                                attribute sigma_Izz : Real = 0.37017423652493897;
                                attribute Ixy : Real = -0.0024451108444513954;
                                attribute sigma_Ixy : Real = 0.02351283871158888;
                                attribute Ixz : Real = 0.0011055171266655043;
                                attribute sigma_Ixz : Real = 0.022566176940390956;
                                attribute Iyz : Real = -0.0052871407602917775;
                                attribute sigma_Iyz : Real = 0.02209918015384651;
                            }
                        }
                        part <'C.1.2.3.3.2.3'> 'Subassembly 321' {
                            attribute POIconv : String = "-";
                            attribute Ipoint : Boolean = false;
                            attribute mass : Real = 1.4447445686056746;
                            attribute sigma_mass : Real = 0.5781874454998993;
                            attribute Cx : Real = 80.25753314173838;
                            attribute sigma_Cx : Real = 21.17512796193685;
                            attribute Cy : Real = 25.329636869082982;
                            attribute sigma_Cy : Real = 42.307916590894756;
                            attribute Cz : Real = 27.938013600756147;
                            attribute sigma_Cz : Real = 34.97121169391278;
                            attribute Ixx : Real = 19611.910289819985;
                            attribute sigma_Ixx : Real = 10736.321491810866;
                            attribute Iyy : Real = 9489.88227209013;
                            attribute sigma_Iyy : Real = 5790.532411639738;
                            attribute Izz : Real = 11354.974737439554;
                            attribute sigma_Izz : Real = 7402.482204805054;
                            attribute Ixy : Real = -2393.6474860970766;
                            attribute sigma_Ixy : Real = 2571.8307895931716;
                            attribute Ixz : Real = -2212.815501764661;
                            attribute sigma_Ixz : Real = 2399.4822796336302;
                            attribute Iyz : Real = -9472.701104158046;
                            attribute sigma_Iyz : Real = 5147.708544950849;
                            part <'C.1.2.3.3.2.3.1'> 'Part 1136' {
                                attribute POIconv : String = "-";
                                attribute Ipoint : Boolean = false;
                                attribute mass : Real = 0.4949692073278129;
                                attribute sigma_mass : Real = 0.28909372274994966;
                                attribute Cx : Real = 51.751705491915345;
                                attribute sigma_Cx : Real = 28.721044428837228;
                                attribute Cy : Real = -82.3002414777875;
                                attribute sigma_Cy : Real = 28.23690002309109;
                                attribute Cz : Real = -73.04290840402246;
                                attribute sigma_Cz : Real = 29.057750463592832;
                                attribute Ixx : Real = 0.5468992172889806;
                                attribute sigma_Ixx : Real = 0.37074144170588635;
                                attribute Iyy : Real = 0.6270105274079575;
                                attribute sigma_Iyy : Real = 0.3723953238821935;
                                attribute Izz : Real = 0.6243832705769022;
                                attribute sigma_Izz : Real = 0.37017423652493897;
                                attribute Ixy : Real = 0.07254116357168534;
                                attribute sigma_Ixy : Real = 0.02351283871158888;
                                attribute Ixz : Real = -0.017785245093049407;
                                attribute sigma_Ixz : Real = 0.022566176940390956;
                                attribute Iyz : Real = 0.013614617102668588;
                                attribute sigma_Iyz : Real = 0.02209918015384651;
                            }
                            part <'C.1.2.3.3.2.3.2'> 'Part 1137' {
                                attribute POIconv : String = "-";
                                attribute Ipoint : Boolean = false;
                                attribute mass : Real = 0.026876852105138824;
                                attribute sigma_mass : Real = 0.28909372274994966;
                                attribute Cx : Real = 98.31936792470515;
                                attribute sigma_Cx : Real = 28.721044428837228;
                                attribute Cy : Real = 98.197972914204;
                                attribute sigma_Cy : Real = 28.23690002309109;
                                attribute Cz : Real = -24.136184295639396;
                                attribute sigma_Cz : Real = 29.057750463592832;
                                attribute Ixx : Real = 0.033284602015161126;
                                attribute sigma_Ixx : Real = 0.37074144170588635;
                                attribute Iyy : Real = 0.03463491734367418;
                                attribute sigma_Iyy : Real = 0.3723953238821935;
                                attribute Izz : Real = 0.03223346391066476;
                                attribute sigma_Izz : Real = 0.37017423652493897;
                                attribute Ixy : Real = -0.0019857378748306224;
                                attribute sigma_Ixy : Real = 0.02351283871158888;
                                attribute Ixz : Real = -0.0006402604989273093;
                                attribute sigma_Ixz : Real = 0.022566176940390956;
                                attribute Iyz : Real = 0.0017428941593680498;
                                attribute sigma_Iyz : Real = 0.02209918015384651;
                            }
                            part <'C.1.2.3.3.2.3.3'> 'Part 1138' {
                                attribute POIconv : String = "-";
                                attribute Ipoint : Boolean = false;
                                attribute mass : Real = 0.8601742880437523;
                                attribute sigma_mass : Real = 0.28909372274994966;
                                attribute Cx : Real = 95.5351846292615;
                                attribute sigma_Cx : Real = 28.721044428837228;
                                attribute Cy : Real = 93.52711904793978;
                                attribute sigma_Cy : Real = 28.23690002309109;
                                attribute Cz : Real = 92.00677648186684;
                                attribute sigma_Cz : Real = 29.057750463592832;
                                attribute Ixx : Real = 1.0219546514477373;
                                attribute sigma_Ixx : Real = 0.37074144170588635;
                                attribute Iyy : Real = 1.077712092840212;
                                attribute sigma_Iyy : Real = 0.3723953238821935;
                                attribute Izz : Real = 1.1627805137826237;
                                attribute sigma_Izz : Real = 0.37017423652493897;
                                attribute Ixy : Real = -0.053868656566637044;
                                attribute sigma_Ixy : Real = 0.02351283871158888;
                                attribute Ixz : Real = -0.015212325251310648;
                                attribute sigma_Ixz : Real = 0.022566176940390956;
                                attribute Iyz : Real = -0.03678154830821617;
                                attribute sigma_Iyz : Real = 0.02209918015384651;
                            }
                            part <'C.1.2.3.3.2.3.4'> 'Part 1139' {
                                attribute POIconv : String = "-";
                                attribute Ipoint : Boolean = false;
                                attribute mass : Real = 0.06272422112897039;
                                attribute sigma_mass : Real = 0.28909372274994966;
                                attribute Cx : Real = 87.95182816684246;
                                attribute sigma_Cx : Real = 28.721044428837228;
                                attribute Cy : Real = -91.79763020947576;
                                attribute sigma_Cy : Real = 28.23690002309109;
                                attribute Cz : Real = -31.500987708568573;
                                attribute sigma_Cz : Real = 29.057750463592832;
                                attribute Ixx : Real = 0.08802745265021128;
                                attribute sigma_Ixx : Real = 0.37074144170588635;
                                attribute Iyy : Real = 0.07853123469248825;
                                attribute sigma_Iyy : Real = 0.3723953238821935;
                                attribute Izz : Real = 0.08959774559323586;
                                attribute sigma_Izz : Real = 0.37017423652493897;
                                attribute Ixy : Real = -0.0005522474371692713;
                                attribute sigma_Ixy : Real = 0.02351283871158888;
                                attribute Ixz : Real = -0.0003955644618723155;
                                attribute sigma_Ixz : Real = 0.022566176940390956;
                                attribute Iyz : Real = 0.004539404301995009;
                                attribute sigma_Iyz : Real = 0.02209918015384651;
                            }
                        }
                        part <'C.1.2.3.3.2.4'> 'Subassembly 322' {
                            attribute POIconv : String = "-";
                            attribute Ipoint : Boolean = false;
                            attribute mass : Real = 1.9196786039171276;
                            attribute sigma_mass : Real = 0.5007250159521434;
                            attribute Cx : Real = 19.095686727999738;
                            attribute sigma_Cx : Real = 24.763614564668984;
                            attribute Cy : Real = -58.438617022838294;
                            attribute sigma_Cy : Real = 19.032242310762758;
                            attribute Cz : Real = 77.95476113367579;
                            attribute sigma_Cz : Real = 24.302369968415363;
                            attribute Ixx : Real = 2433.846706694776;
                            attribute sigma_Ixx : Real = 3450.8582104915668;
                            attribute Iyy : Real = 11511.862477846877;
                            attribute sigma_Iyy : Real = 6603.9909583810195;
                            attribute Izz : Real = 10178.007035877046;
                            attribute sigma_Izz : Real = 5885.314480316909;
                            attribute Ixy : Real = -2043.8411620858396;
                            attribute sigma_Ixy : Real = 2701.218494932421;
                            attribute Ixz : Real = -1141.1954665449143;
                            attribute sigma_Ixz : Real = 2825.3479673614966;
                            attribute Iyz : Real = 205.81865935244755;
                            attribute sigma_Iyz : Real = 1037.056914812711;
                            part <'C.1.2.3.3.2.4.1'> 'Part 1140' {
                                attribute POIconv : String = "-";
                                attribute Ipoint : Boolean = false;
                                attribute mass : Real = 0.8029978942512535;
                                attribute sigma_mass : Real = 0.28909372274994966;
                                attribute Cx : Real = -58.86550433933735;
                                attribute sigma_Cx : Real = 28.721044428837228;
                                attribute Cy : Real = -78.26017765328288;
                                attribute sigma_Cy : Real = 28.23690002309109;
                                attribute Cz : Real = 81.46493663080037;
                                attribute sigma_Cz : Real = 29.057750463592832;
                                attribute Ixx : Real = 0.8267211510723803;
                                attribute sigma_Ixx : Real = 0.37074144170588635;
                                attribute Iyy : Real = 0.9706107330115894;
                                attribute sigma_Iyy : Real = 0.3723953238821935;
                                attribute Izz : Real = 0.9742928874226946;
                                attribute sigma_Izz : Real = 0.37017423652493897;
                                attribute Ixy : Real = -0.01726447560138701;
                                attribute sigma_Ixy : Real = 0.02351283871158888;
                                attribute Ixz : Real = -0.07927684323198714;
                                attribute sigma_Ixz : Real = 0.022566176940390956;
                                attribute Iyz : Real = -0.022719756170377147;
                                attribute sigma_Iyz : Real = 0.02209918015384651;
                            }
                            part <'C.1.2.3.3.2.4.2'> 'Part 1141' {
                                attribute POIconv : String = "+";
                                attribute Ipoint : Boolean = false;
                                attribute mass : Real = 0.1681197369468864;
                                attribute sigma_mass : Real = 0.28909372274994966;
                                attribute Cx : Real = -3.885092632845044;
                                attribute sigma_Cx : Real = 28.721044428837228;
                                attribute Cy : Real = -38.47290319390595;
                                attribute sigma_Cy : Real = 28.23690002309109;
                                attribute Cz : Real = -21.66428449563682;
                                attribute sigma_Cz : Real = 29.057750463592832;
                                attribute Ixx : Real = 0.15253122724865734;
                                attribute sigma_Ixx : Real = 0.37074144170588635;
                                attribute Iyy : Real = 0.21085548556488662;
                                attribute sigma_Iyy : Real = 0.3723953238821935;
                                attribute Izz : Real = 0.20495983175999954;
                                attribute sigma_Izz : Real = 0.37017423652493897;
                                attribute Ixy : Real = 0.002656356006204293;
                                attribute sigma_Ixy : Real = 0.02351283871158888;
                                attribute Ixz : Real = -0.016617772613760014;
                                attribute sigma_Ixz : Real = 0.022566176940390956;
                                attribute Iyz : Real = -0.000672715475454482;
                                attribute sigma_Iyz : Real = 0.02209918015384651;
                            }
                            part <'C.1.2.3.3.2.4.3'> 'Part 1142' {
                                attribute POIconv : String = "-";
                                attribute Ipoint : Boolean = false;
                                attribute mass : Real = 0.9485609727189876;
                                attribute sigma_mass : Real = 0.28909372274994966;
                                attribute Cx : Real = 89.16624281555414;
                                attribute sigma_Cx : Real = 28.721044428837228;
                                attribute Cy : Real = -45.19746410660446;
                                attribute sigma_Cy : Real = 28.23690002309109;
                                attribute Cz : Real = 92.63938828371465;
                                attribute sigma_Cz : Real = 29.057750463592832;
                                attribute Ixx : Real = 1.1946055548062644;
                                attribute sigma_Ixx : Real = 0.37074144170588635;
                                attribute Iyy : Real = 1.1394912112408166;
                                attribute sigma_Iyy : Real = 0.3723953238821935;
                                attribute Izz : Real = 1.3186808812918016;
                                attribute sigma_Izz : Real = 0.37017423652493897;
                                attribute Ixy : Real = 0.012486014293346243;
                                attribute sigma_Ixy : Real = 0.02351283871158888;
                                attribute Ixz : Real = 0.032547914619737287;
                                attribute sigma_Ixz : Real = 0.022566176940390956;
                                attribute Iyz : Real = 0.025581138763356902;
                                attribute sigma_Iyz : Real = 0.02209918015384651;
                            }
                        }
                        part <'C.1.2.3.3.2.5'> 'Subassembly 323' {
                            attribute POIconv : String = "-";
                            attribute Ipoint : Boolean = false;
                            attribute mass : Real = 1.339777553186752;
                            attribute sigma_mass : Real = 0.5007250159521434;
                            attribute Cx : Real = 21.968748992699876;
                            attribute sigma_Cx : Real = 20.80799942367231;
                            attribute Cy : Real = 29.528875517424996;
                            attribute sigma_Cy : Real = 21.983777496085878;
                            attribute Cz : Real = 77.30018434702681;
                            attribute sigma_Cz : Real = 22.543831954330994;
                            attribute Ixx : Real = 2013.902297688037;
                            attribute sigma_Ixx : Real = 2518.88102223095;
                            attribute Iyy : Real = 2025.71913359514;
                            attribute sigma_Iyy : Real = 2146.9682506226645;
                            attribute Izz : Real = 1942.4408963441356;
                            attribute sigma_Izz : Real = 2085.7724685099442;
                            attribute Ixy : Real = 384.1097888347001;
                            attribute sigma_Ixy : Real = 969.4668872071111;
                            attribute Ixz : Real = -269.1485731482344;
                            attribute sigma_Ixz : Real = 1002.5828244160839;
                            attribute Iyz : Real = 995.790732037557;
                            attribute sigma_Iyz : Real = 1258.3072978332034;
                            part <'C.1.2.3.3.2.5.1'> 'Part 1143' {
                                attribute POIconv : String = "-";
                                attribute Ipoint : Boolean = false;
                                attribute mass : Real = 0.5021571628896054;
                                attribute sigma_mass : Real = 0.28909372274994966;
                                attribute Cx : Real = 55.76005382463336;
                                attribute sigma_Cx : Real = 28.721044428837228;
                                attribute Cy : Real = 24.068352906033397;
                                attribute sigma_Cy : Real = 28.23690002309109;
                                attribute Cz : Real = 78.04477061145008;
                                attribute sigma_Cz : Real = 29.057750463592832;
                                attribute Ixx : Real = 0.6887006593860255;
                                attribute sigma_Ixx : Real = 0.37074144170588635;
                                attribute Iyy : Real = 0.6239165450929819;
                                attribute sigma_Iyy : Real = 0.3723953238821935;
                                attribute Izz : Real = 0.6141958518624007;
                                attribute sigma_Izz : Real = 0.37017423652493897;
                                attribute Ixy : Real = -0.0017188169770789915;
                                attribute sigma_Ixy : Real = 0.02351283871158888;
                                attribute Ixz : Real = -0.01357297004062851;
                                attribute sigma_Ixz : Real = 0.022566176940390956;
                                attribute Iyz : Real = 0.01199002590248726;
                                attribute sigma_Iyz : Real = 0.02209918015384651;
                            }
                            part <'C.1.2.3.3.2.5.2'> 'Part 1144' {
                                attribute POIconv : String = "+";
                                attribute Ipoint : Boolean = false;
                                attribute mass : Real = 0.21873833777871915;
                                attribute sigma_mass : Real = 0.28909372274994966;
                                attribute Cx : Real = -12.425463367253542;
                                attribute sigma_Cx : Real = 28.721044428837228;
                                attribute Cy : Real = 89.16734554804862;
                                attribute sigma_Cy : Real = 28.23690002309109;
                                attribute Cz : Real = 17.37482170574367;
                                attribute sigma_Cz : Real = 29.057750463592832;
                                attribute Ixx : Real = 0.24191406270711754;
                                attribute sigma_Ixx : Real = 0.37074144170588635;
                                attribute Iyy : Real = 0.26038520895876244;
                                attribute sigma_Iyy : Real = 0.3723953238821935;
                                attribute Izz : Real = 0.27093524158392573;
                                attribute sigma_Izz : Real = 0.37017423652493897;
                                attribute Ixy : Real = -0.016800119541176384;
                                attribute sigma_Ixy : Real = 0.02351283871158888;
                                attribute Ixz : Real = 0.003935348243412233;
                                attribute sigma_Ixz : Real = 0.022566176940390956;
                                attribute Iyz : Real = -6.682418489651988e-05;
                                attribute sigma_Iyz : Real = 0.02209918015384651;
                            }
                            part <'C.1.2.3.3.2.5.3'> 'Part 1145' {
                                attribute POIconv : String = "+";
                                attribute Ipoint : Boolean = false;
                                attribute mass : Real = 0.6188820525184273;
                                attribute sigma_mass : Real = 0.28909372274994966;
                                attribute Cx : Real = 6.707015540450811;
                                attribute sigma_Cx : Real = 28.721044428837228;
                                attribute Cy : Real = 12.880825670436025;
                                attribute sigma_Cy : Real = 28.23690002309109;
                                attribute Cz : Real = 97.8761161211878;
                                attribute sigma_Cz : Real = 29.057750463592832;
                                attribute Ixx : Real = 0.67995172395457;
                                attribute sigma_Ixx : Real = 0.37074144170588635;
                                attribute Iyy : Real = 0.7421351777093977;
                                attribute sigma_Iyy : Real = 0.3723953238821935;
                                attribute Izz : Real = 0.7592668371108575;
                                attribute sigma_Izz : Real = 0.37017423652493897;
                                attribute Ixy : Real = -0.0018951162093840594;
                                attribute sigma_Ixy : Real = 0.02351283871158888;
                                attribute Ixz : Real = 0.0021266837447037317;
                                attribute sigma_Ixz : Real = 0.022566176940390956;
                                attribute Iyz : Real = 5.1422105507893095e-05;
                                attribute sigma_Iyz : Real = 0.02209918015384651;
                            }
                        }
                    }
                    part <'C.1.2.3.3.3'> 'Assembly 95' {
                        attribute POIconv : String = "-";
                        attribute Ipoint : Boolean = false;
                        attribute mass : Real = 5.300787290967535;
                        attribute sigma_mass : Real = 1.0423422407897138;
                        attribute Cx : Real = 24.01765479735251;
                        attribute sigma_Cx : Real = 17.358398719885958;
                        attribute Cy : Real = 22.038181173284066;
                        attribute sigma_Cy : Real = 13.324914609395842;
                        attribute Cz : Real = -12.846049743660746;
                        attribute sigma_Cz : Real = 14.32638661396723;
                        attribute Ixx : Real = 25077.03798417547;
                        attribute sigma_Ixx : Real = 9035.524619272432;
                        attribute Iyy : Real = 43666.10797928134;
                        attribute sigma_Iyy : Real = 13198.65987512028;
                        attribute Izz : Real = 38056.65362918195;
                        attribute sigma_Izz : Real = 12567.084696467284;
                        attribute Ixy : Real = -1054.5728282833597;
                        attribute sigma_Ixy : Real = 5546.419972827075;
                        attribute Ixz : Real = -2138.7607594290475;
                        attribute sigma_Ixz : Real = 5993.689551294697;
                        attribute Iyz : Real = -3696.3856952270316;
                        attribute sigma_Iyz : Real = 4170.683113377797;
                        part <'C.1.2.3.3.3.1'> 'Subassembly 324' {
                            attribute POIconv : String = "-";
                            attribute Ipoint : Boolean = false;
                            attribute mass : Real = 1.229013462133007;
                            attribute sigma_mass : Real = 0.5007250159521434;
                            attribute Cx : Real = 65.91356862972141;
                            attribute sigma_Cx : Real = 34.05122245443475;
                            attribute Cy : Real = -18.174007709493264;
                            attribute sigma_Cy : Real = 31.989140619087976;
                            attribute Cz : Real = -20.95149088554968;
                            attribute sigma_Cz : Real = 29.289098549964056;
                            attribute Ixx : Real = 3278.02137131455;
                            attribute sigma_Ixx : Real = 3978.9127888297594;
                            attribute Iyy : Real = 4377.4511710436345;
                            attribute sigma_Iyy : Real = 4473.408040738144;
                            attribute Izz : Real = 5260.33720074281;
                            attribute sigma_Izz : Real = 5391.408236952069;
                            attribute Ixy : Real = 1410.6451015476955;
                            attribute sigma_Ixy : Real = 2678.0466960981535;
                            attribute Ixz : Real = 1309.8692725058356;
                            attribute sigma_Ixz : Real = 1826.5020401231054;
                            attribute Iyz : Real = 396.15970672553794;
                            attribute sigma_Iyz : Real = 1684.839363542697;
                            part <'C.1.2.3.3.3.1.1'> 'Part 1146' {
                                attribute POIconv : String = "+";
                                attribute Ipoint : Boolean = false;
                                attribute mass : Real = 0.2156393684996292;
                                attribute sigma_mass : Real = 0.28909372274994966;
                                attribute Cx : Real = -25.546913500875235;
                                attribute sigma_Cx : Real = 28.721044428837228;
                                attribute Cy : Real = 64.04562308453023;
                                attribute sigma_Cy : Real = 28.23690002309109;
                                attribute Cz : Real = -11.25999167561531;
                                attribute sigma_Cz : Real = 29.057750463592832;
                                attribute Ixx : Real = 0.3504775645228141;
                                attribute sigma_Ixx : Real = 0.37074144170588635;
                                attribute Iyy : Real = 0.3529738240126634;
                                attribute sigma_Iyy : Real = 0.3723953238821935;
                                attribute Izz : Real = 0.353111997049998;
                                attribute sigma_Izz : Real = 0.37017423652493897;
                                attribute Ixy : Real = -0.001986159206998698;
                                attribute sigma_Ixy : Real = 0.02351283871158888;
                                attribute Ixz : Real = 0.002316887143696578;
                                attribute sigma_Ixz : Real = 0.022566176940390956;
                                attribute Iyz : Real = 0.0035287232705087644;
                                attribute sigma_Iyz : Real = 0.02209918015384651;
                            }
                            part <'C.1.2.3.3.3.1.2'> 'Part 1147' {
                                attribute POIconv : String = "-";
                                attribute Ipoint : Boolean = false;
                                attribute mass : Real = 0.1411246996978298;
                                attribute sigma_mass : Real = 0.28909372274994966;
                                attribute Cx : Real = 7.613337878137827;
                                attribute sigma_Cx : Real = 28.721044428837228;
                                attribute Cy : Real = -79.27542165853083;
                                attribute sigma_Cy : Real = 28.23690002309109;
                                attribute Cz : Real = 61.54035753570497;
                                attribute sigma_Cz : Real = 29.057750463592832;
                                attribute Ixx : Real = 0.15280759801090632;
                                attribute sigma_Ixx : Real = 0.37074144170588635;
                                attribute Iyy : Real = 0.16187744197611764;
                                attribute sigma_Iyy : Real = 0.3723953238821935;
                                attribute Izz : Real = 0.16767715003623793;
                                attribute sigma_Izz : Real = 0.37017423652493897;
                                attribute Ixy : Real = -0.007258785712568836;
                                attribute sigma_Ixy : Real = 0.02351283871158888;
                                attribute Ixz : Real = 0.005728057405915468;
                                attribute sigma_Ixz : Real = 0.022566176940390956;
                                attribute Iyz : Real = 0.00791151460835075;
                                attribute sigma_Iyz : Real = 0.02209918015384651;
                            }
                            part <'C.1.2.3.3.3.1.3'> 'Part 1148' {
                                attribute POIconv : String = "-";
                                attribute Ipoint : Boolean = false;
                                attribute mass : Real = 0.8722493939355481;
                                attribute sigma_mass : Real = 0.28909372274994966;
                                attribute Cx : Real = 97.95725173316896;
                                attribute sigma_Cx : Real = 28.721044428837228;
                                attribute Cy : Real = -28.61468056216836;
                                attribute sigma_Cy : Real = 28.23690002309109;
                                attribute Cz : Real = -36.694128485396504;
                                attribute sigma_Cz : Real = 29.057750463592832;
                                attribute Ixx : Real = 1.0627096534643206;
                                attribute sigma_Ixx : Real = 0.37074144170588635;
                                attribute Iyy : Real = 1.049730785370024;
                                attribute sigma_Iyy : Real = 0.3723953238821935;
                                attribute Izz : Real = 1.0029827838491847;
                                attribute sigma_Izz : Real = 0.37017423652493897;
                                attribute Ixy : Real = -0.024224760306871644;
                                attribute sigma_Ixy : Real = 0.02351283871158888;
                                attribute Ixz : Real = 0.007282904332993631;
                                attribute sigma_Ixz : Real = 0.022566176940390956;
                                attribute Iyz : Real = 0.029223677472345867;
                                attribute sigma_Iyz : Real = 0.02209918015384651;
                            }
                        }
                        part <'C.1.2.3.3.3.2'> 'Subassembly 325' {
                            attribute POIconv : String = "-";
                            attribute Ipoint : Boolean = false;
                            attribute mass : Real = 1.3023908205665649;
                            attribute sigma_mass : Real = 0.5781874454998993;
                            attribute Cx : Real = 59.35926627918262;
                            attribute sigma_Cx : Real = 23.69914069529091;
                            attribute Cy : Real = 60.9606001777681;
                            attribute sigma_Cy : Real = 23.940086589383906;
                            attribute Cz : Real = 26.237081315606467;
                            attribute sigma_Cz : Real = 24.162247886972025;
                            attribute Ixx : Real = 3966.755130374192;
                            attribute sigma_Ixx : Real = 3122.2273765598493;
                            attribute Iyy : Real = 3525.518913703323;
                            attribute sigma_Iyy : Real = 2778.210861894128;
                            attribute Izz : Real = 3441.069420126985;
                            attribute sigma_Izz : Real = 2926.7225845582984;
                            attribute Ixy : Real = -1289.7093352185357;
                            attribute sigma_Ixy : Real = 1407.7400997137854;
                            attribute Ixz : Real = -1023.0188932606704;
                            attribute sigma_Ixz : Real = 1312.5645147025123;
                            attribute Iyz : Real = -1856.1992479765872;
                            attribute sigma_Iyz : Real = 1500.163495053645;
                            part <'C.1.2.3.3.3.2.1'> 'Part 1149' {
                                attribute POIconv : String = "+";
                                attribute Ipoint : Boolean = false;
                                attribute mass : Real = 0.2208638272935059;
                                attribute sigma_mass : Real = 0.28909372274994966;
                                attribute Cx : Real = 10.632020700722933;
                                attribute sigma_Cx : Real = 28.721044428837228;
                                attribute Cy : Real = -2.555057918652892;
                                attribute sigma_Cy : Real = 28.23690002309109;
                                attribute Cz : Real = -15.34853633493185;
                                attribute sigma_Cz : Real = 29.057750463592832;
                                attribute Ixx : Real = 0.25623472940078057;
                                attribute sigma_Ixx : Real = 0.37074144170588635;
                                attribute Iyy : Real = 0.2543089934267736;
                                attribute sigma_Iyy : Real = 0.3723953238821935;
                                attribute Izz : Real = 0.24507464835246398;
                                attribute sigma_Izz : Real = 0.37017423652493897;
                                attribute Ixy : Real = -0.027254775978169252;
                                attribute sigma_Ixy : Real = 0.02351283871158888;
                                attribute Ixz : Real = -0.006873905333996289;
                                attribute sigma_Ixz : Real = 0.022566176940390956;
                                attribute Iyz : Real = -0.006240300320748112;
                                attribute sigma_Iyz : Real = 0.02209918015384651;
                            }
                            part <'C.1.2.3.3.3.2.2'> 'Part 1150' {
                                attribute POIconv : String = "+";
                                attribute Ipoint : Boolean = false;
                                attribute mass : Real = 0.6474646133370697;
                                attribute sigma_mass : Real = 0.28909372274994966;
                                attribute Cx : Real = 83.74939523637295;
                                attribute sigma_Cx : Real = 28.721044428837228;
                                attribute Cy : Real = 96.9920726493001;
                                attribute sigma_Cy : Real = 28.23690002309109;
                                attribute Cz : Real = 64.95299804955721;
                                attribute sigma_Cz : Real = 29.057750463592832;
                                attribute Ixx : Real = 0.8254922846231016;
                                attribute sigma_Ixx : Real = 0.37074144170588635;
                                attribute Iyy : Real = 0.844809395980925;
                                attribute sigma_Iyy : Real = 0.3723953238821935;
                                attribute Izz : Real = 0.8651825925619495;
                                attribute sigma_Izz : Real = 0.37017423652493897;
                                attribute Ixy : Real = 0.041356265963219965;
                                attribute sigma_Ixy : Real = 0.02351283871158888;
                                attribute Ixz : Real = 0.06679462070738779;
                                attribute sigma_Ixz : Real = 0.022566176940390956;
                                attribute Iyz : Real = 0.052902791199776526;
                                attribute sigma_Iyz : Real = 0.02209918015384651;
                            }
                            part <'C.1.2.3.3.3.2.3'> 'Part 1151' {
                                attribute POIconv : String = "-";
                                attribute Ipoint : Boolean = false;
                                attribute mass : Real = 0.1998935781386681;
                                attribute sigma_mass : Real = 0.28909372274994966;
                                attribute Cx : Real = 9.909604350104928;
                                attribute sigma_Cx : Real = 28.721044428837228;
                                attribute Cy : Real = 44.56796427257359;
                                attribute sigma_Cy : Real = 28.23690002309109;
                                attribute Cz : Real = 5.330644641071558;
                                attribute sigma_Cz : Real = 29.057750463592832;
                                attribute Ixx : Real = 0.2784193769521985;
                                attribute sigma_Ixx : Real = 0.37074144170588635;
                                attribute Iyy : Real = 0.2864733155826442;
                                attribute sigma_Iyy : Real = 0.3723953238821935;
                                attribute Izz : Real = 0.27962031369374757;
                                attribute sigma_Izz : Real = 0.37017423652493897;
                                attribute Ixy : Real = 0.00672002298558945;
                                attribute sigma_Ixy : Real = 0.02351283871158888;
                                attribute Ixz : Real = -0.011263582239797319;
                                attribute sigma_Ixz : Real = 0.022566176940390956;
                                attribute Iyz : Real = 0.006480353309416801;
                                attribute sigma_Iyz : Real = 0.02209918015384651;
                            }
                            part <'C.1.2.3.3.3.2.4'> 'Part 1152' {
                                attribute POIconv : String = "+";
                                attribute Ipoint : Boolean = false;
                                attribute mass : Real = 0.23416880179732108;
                                attribute sigma_mass : Real = 0.28909372274994966;
                                attribute Cx : Real = 80.09221772663295;
                                attribute sigma_Cx : Real = 28.721044428837228;
                                attribute Cy : Real = 35.235527670010924;
                                attribute sigma_Cy : Real = 28.23690002309109;
                                attribute Cz : Real = -23.74124568887055;
                                attribute sigma_Cz : Real = 29.057750463592832;
                                attribute Ixx : Real = 0.37557168249293454;
                                attribute sigma_Ixx : Real = 0.37074144170588635;
                                attribute Iyy : Real = 0.37467670613590154;
                                attribute sigma_Iyy : Real = 0.3723953238821935;
                                attribute Izz : Real = 0.37519557994687097;
                                attribute sigma_Izz : Real = 0.37017423652493897;
                                attribute Ixy : Real = 0.0008422927412459983;
                                attribute sigma_Ixy : Real = 0.02351283871158888;
                                attribute Ixz : Real = -0.00011031047906846924;
                                attribute sigma_Ixz : Real = 0.022566176940390956;
                                attribute Iyz : Real = -0.00031105646999059666;
                                attribute sigma_Iyz : Real = 0.02209918015384651;
                            }
                        }
                        part <'C.1.2.3.3.3.3'> 'Subassembly 326' {
                            attribute POIconv : String = "-";
                            attribute Ipoint : Boolean = false;
                            attribute mass : Real = 1.4972130186813883;
                            attribute sigma_mass : Real = 0.5781874454998993;
                            attribute Cx : Real = -6.659812697031491;
                            attribute sigma_Cx : Real = 30.960399098915122;
                            attribute Cy : Real = 1.8541765983726313;
                            attribute sigma_Cy : Real = 17.283249640468313;
                            attribute Cz : Real = -20.61528580958731;
                            attribute sigma_Cz : Real = 27.569787990814923;
                            attribute Ixx : Real = 6510.662001958879;
                            attribute sigma_Ixx : Real = 4034.839601295719;
                            attribute Iyy : Real = 11663.15225838318;
                            attribute sigma_Iyy : Real = 6352.441713712363;
                            attribute Izz : Real = 6022.411447957731;
                            attribute sigma_Izz : Real = 4371.44602362319;
                            attribute Ixy : Real = -988.0220999979348;
                            attribute sigma_Ixy : Real = 1626.9977039676162;
                            attribute Ixz : Real = -5376.530704048791;
                            attribute sigma_Ixz : Real = 2937.3442184437545;
                            attribute Iyz : Real = -675.9693342192573;
                            attribute sigma_Iyz : Real = 1719.7407117920604;
                            part <'C.1.2.3.3.3.3.1'> 'Part 1153' {
                                attribute POIconv : String = "+";
                                attribute Ipoint : Boolean = false;
                                attribute mass : Real = 0.4025493644969538;
                                attribute sigma_mass : Real = 0.28909372274994966;
                                attribute Cx : Real = 30.95246935263276;
                                attribute sigma_Cx : Real = 28.721044428837228;
                                attribute Cy : Real = -10.21992419846356;
                                attribute sigma_Cy : Real = 28.23690002309109;
                                attribute Cz : Real = 46.769953705370426;
                                attribute sigma_Cz : Real = 29.057750463592832;
                                attribute Ixx : Real = 0.4129329869864466;
                                attribute sigma_Ixx : Real = 0.37074144170588635;
                                attribute Iyy : Real = 0.40887155054383484;
                                attribute sigma_Iyy : Real = 0.3723953238821935;
                                attribute Izz : Real = 0.39672464860963186;
                                attribute sigma_Izz : Real = 0.37017423652493897;
                                attribute Ixy : Real = 0.008848099438941714;
                                attribute sigma_Ixy : Real = 0.02351283871158888;
                                attribute Ixz : Real = 0.023886103246154596;
                                attribute sigma_Ixz : Real = 0.022566176940390956;
                                attribute Iyz : Real = -0.019296782793598533;
                                attribute sigma_Iyz : Real = 0.02209918015384651;
                            }
                            part <'C.1.2.3.3.3.3.2'> 'Part 1154' {
                                attribute POIconv : String = "+";
                                attribute Ipoint : Boolean = false;
                                attribute mass : Real = 0.6444155635028146;
                                attribute sigma_mass : Real = 0.28909372274994966;
                                attribute Cx : Real = -65.22628706879914;
                                attribute sigma_Cx : Real = 28.721044428837228;
                                attribute Cy : Real = -8.016453357413411;
                                attribute sigma_Cy : Real = 28.23690002309109;
                                attribute Cz : Real = -90.29602380469441;
                                attribute sigma_Cz : Real = 29.057750463592832;
                                attribute Ixx : Real = 0.8251840899371466;
                                attribute sigma_Ixx : Real = 0.37074144170588635;
                                attribute Iyy : Real = 0.9534690390312993;
                                attribute sigma_Iyy : Real = 0.3723953238821935;
                                attribute Izz : Real = 0.7699277230808921;
                                attribute sigma_Izz : Real = 0.37017423652493897;
                                attribute Ixy : Real = 0.02730906174678948;
                                attribute sigma_Ixy : Real = 0.02351283871158888;
                                attribute Ixz : Real = -0.005660801200392538;
                                attribute sigma_Ixz : Real = 0.022566176940390956;
                                attribute Iyz : Real = 0.004511270369298027;
                                attribute sigma_Iyz : Real = 0.02209918015384651;
                            }
                            part <'C.1.2.3.3.3.3.3'> 'Part 1155' {
                                attribute POIconv : String = "+";
                                attribute Ipoint : Boolean = false;
                                attribute mass : Real = 0.0731430235800799;
                                attribute sigma_mass : Real = 0.28909372274994966;
                                attribute Cx : Real = -94.84316180460155;
                                attribute sigma_Cx : Real = 28.721044428837228;
                                attribute Cy : Real = 7.328130584210157;
                                attribute sigma_Cy : Real = 28.23690002309109;
                                attribute Cz : Real = -50.15052342787385;
                                attribute sigma_Cz : Real = 29.057750463592832;
                                attribute Ixx : Real = 0.08578797256175501;
                                attribute sigma_Ixx : Real = 0.37074144170588635;
                                attribute Iyy : Real = 0.09915849316591722;
                                attribute sigma_Iyy : Real = 0.3723953238821935;
                                attribute Izz : Real = 0.09915812951115507;
                                attribute sigma_Izz : Real = 0.37017423652493897;
                                attribute Ixy : Real = -0.0029198146100436594;
                                attribute sigma_Ixy : Real = 0.02351283871158888;
                                attribute Ixz : Real = -0.0036633529689337526;
                                attribute sigma_Ixz : Real = 0.022566176940390956;
                                attribute Iyz : Real = 0.001764986456764725;
                                attribute sigma_Iyz : Real = 0.02209918015384651;
                            }
                            part <'C.1.2.3.3.3.3.4'> 'Part 1156' {
                                attribute POIconv : String = "+";
                                attribute Ipoint : Boolean = false;
                                attribute mass : Real = 0.37710506710154007;
                                attribute sigma_mass : Real = 0.28909372274994966;
                                attribute Cx : Real = 70.37533391267061;
                                attribute sigma_Cx : Real = 28.721044428837228;
                                attribute Cy : Real = 30.54864020086825;
                                attribute sigma_Cy : Real = 28.23690002309109;
                                attribute Cz : Real = 32.25529328919947;
                                attribute sigma_Cz : Real = 29.057750463592832;
                                attribute Ixx : Real = 0.4694288870777152;
                                attribute sigma_Ixx : Real = 0.37074144170588635;
                                attribute Iyy : Real = 0.45596739470019015;
                                attribute sigma_Iyy : Real = 0.3723953238821935;
                                attribute Izz : Real = 0.46008329267883685;
                                attribute sigma_Izz : Real = 0.37017423652493897;
                                attribute Ixy : Real = -0.005547784278024838;
                                attribute sigma_Ixy : Real = 0.02351283871158888;
                                attribute Ixz : Real = 0.007970367492713386;
                                attribute sigma_Ixz : Real = 0.022566176940390956;
                                attribute Iyz : Real = 0.0005981835115231405;
                                attribute sigma_Iyz : Real = 0.02209918015384651;
                            }
                        }
                        part <'C.1.2.3.3.3.4'> 'Subassembly 327' {
                            attribute POIconv : String = "-";
                            attribute Ipoint : Boolean = false;
                            attribute mass : Real = 1.272169989586575;
                            attribute sigma_mass : Real = 0.40884026350990615;
                            attribute Cx : Real = -16.533945378587433;
                            attribute sigma_Cx : Real = 36.58784160574;
                            attribute Cy : Real = 44.793689406246514;
                            attribute sigma_Cy : Real = 20.2994992431082;
                            attribute Cz : Real = -35.88354764682339;
                            attribute sigma_Cz : Real = 26.553776393077825;
                            attribute Ixx : Real = 3256.8130768343217;
                            attribute sigma_Ixx : Real = 2851.892247732332;
                            attribute Iyy : Real = 13979.296734560558;
                            attribute sigma_Iyy : Real = 7277.763151870612;
                            attribute Izz : Real = 10818.723806708946;
                            attribute sigma_Izz : Real = 6052.898138769874;
                            attribute Ixy : Real = -713.3514972593659;
                            attribute sigma_Ixy : Real = 2328.2200528235066;
                            attribute Ixz : Real = 5877.823729889054;
                            attribute sigma_Ixz : Real = 3400.681813217917;
                            attribute Iyz : Real = 389.2895032133853;
                            attribute sigma_Iyz : Real = 1277.5436276796975;
                            part <'C.1.2.3.3.3.4.1'> 'Part 1157' {
                                attribute POIconv : String = "+";
                                attribute Ipoint : Boolean = false;
                                attribute mass : Real = 0.7336926386537962;
                                attribute sigma_mass : Real = 0.28909372274994966;
                                attribute Cx : Real = -95.35790062509477;
                                attribute sigma_Cx : Real = 28.721044428837228;
                                attribute Cy : Real = 39.57259049639106;
                                attribute sigma_Cy : Real = 28.23690002309109;
                                attribute Cz : Real = 7.135393423959613;
                                attribute sigma_Cz : Real = 29.057750463592832;
                                attribute Ixx : Real = 1.0673947738414644;
                                attribute sigma_Ixx : Real = 0.37074144170588635;
                                attribute Iyy : Real = 1.0609109595985258;
                                attribute sigma_Iyy : Real = 0.3723953238821935;
                                attribute Izz : Real = 0.9952948768670735;
                                attribute sigma_Izz : Real = 0.37017423652493897;
                                attribute Ixy : Real = -0.021407425297408487;
                                attribute sigma_Ixy : Real = 0.02351283871158888;
                                attribute Ixz : Real = -0.029490043312835112;
                                attribute sigma_Ixz : Real = 0.022566176940390956;
                                attribute Iyz : Real = 0.05181015072487731;
                                attribute sigma_Iyz : Real = 0.02209918015384651;
                            }
                            part <'C.1.2.3.3.3.4.2'> 'Part 1158' {
                                attribute POIconv : String = "+";
                                attribute Ipoint : Boolean = false;
                                attribute mass : Real = 0.5384773509327788;
                                attribute sigma_mass : Real = 0.28909372274994966;
                                attribute Cx : Real = 90.86621846072376;
                                attribute sigma_Cx : Real = 28.721044428837228;
                                attribute Cy : Real = 51.9076039083302;
                                attribute sigma_Cy : Real = 28.23690002309109;
                                attribute Cz : Real = -94.49823279865086;
                                attribute sigma_Cz : Real = 29.057750463592832;
                                attribute Ixx : Real = 0.6645092720163112;
                                attribute sigma_Ixx : Real = 0.37074144170588635;
                                attribute Iyy : Real = 0.5894203247511687;
                                attribute sigma_Iyy : Real = 0.3723953238821935;
                                attribute Izz : Real = 0.6602577003094309;
                                attribute sigma_Izz : Real = 0.37017423652493897;
                                attribute Ixy : Real = 0.007554306511462643;
                                attribute sigma_Ixy : Real = 0.02351283871158888;
                                attribute Ixz : Real = -0.061888916998248805;
                                attribute sigma_Ixz : Real = 0.022566176940390956;
                                attribute Iyz : Real = -0.01522748216680998;
                                attribute sigma_Iyz : Real = 0.02209918015384651;
                            }
                        }
                    }
                    part <'C.1.2.3.3.4'> 'Assembly 96' {
                        attribute POIconv : String = "-";
                        attribute Ipoint : Boolean = false;
                        attribute mass : Real = 9.820558709093602;
                        attribute sigma_mass : Real = 1.260130322678996;
                        attribute Cx : Real = -12.011115980427503;
                        attribute sigma_Cx : Real = 11.326266397646275;
                        attribute Cy : Real = -8.213839868247272;
                        attribute sigma_Cy : Real = 10.123779493411467;
                        attribute Cz : Real = -0.561774462313089;
                        attribute sigma_Cz : Real = 10.580671992951675;
                        attribute Ixx : Real = 35134.24169076567;
                        attribute sigma_Ixx : Real = 13604.312867239609;
                        attribute Iyy : Real = 47037.10315545438;
                        attribute sigma_Iyy : Real = 15416.663071475294;
                        attribute Izz : Real = 49335.62087239117;
                        attribute sigma_Izz : Real = 15390.093272630766;
                        attribute Ixy : Real = -16836.661466780242;
                        attribute sigma_Ixy : Real = 7317.402161426723;
                        attribute Ixz : Real = -1134.4270759623619;
                        attribute sigma_Ixz : Real = 7304.3797521958495;
                        attribute Iyz : Real = -921.7657862263823;
                        attribute sigma_Iyz : Real = 6161.033285854391;
                        part <'C.1.2.3.3.4.1'> 'Subassembly 328' {
                            attribute POIconv : String = "-";
                            attribute Ipoint : Boolean = false;
                            attribute mass : Real = 2.3593012570042626;
                            attribute sigma_mass : Real = 0.5781874454998993;
                            attribute Cx : Real = 10.770357150904688;
                            attribute sigma_Cx : Real = 19.473065599770305;
                            attribute Cy : Real = -11.672173913518773;
                            attribute sigma_Cy : Real = 18.67122060101735;
                            attribute Cz : Real = 8.387783470167063;
                            attribute sigma_Cz : Real = 21.54175037350045;
                            attribute Ixx : Real = 3823.6868004285143;
                            attribute sigma_Ixx : Real = 5293.874290776702;
                            attribute Iyy : Real = 7247.794462663714;
                            attribute sigma_Iyy : Real = 5544.142391149449;
                            attribute Izz : Real = 4862.068653549159;
                            attribute sigma_Izz : Real = 4114.2603645843765;
                            attribute Ixy : Real = -614.0207214217685;
                            attribute sigma_Ixy : Real = 1867.3966535858806;
                            attribute Ixz : Real = 3138.493363490702;
                            attribute sigma_Ixz : Real = 2501.2481538435513;
                            attribute Iyz : Real = -134.94600774062542;
                            attribute sigma_Iyz : Real = 2552.449412874805;
                            part <'C.1.2.3.3.4.1.1'> 'Part 1159' {
                                attribute POIconv : String = "+";
                                attribute Ipoint : Boolean = false;
                                attribute mass : Real = 0.7400061334336642;
                                attribute sigma_mass : Real = 0.28909372274994966;
                                attribute Cx : Real = -12.040049163624644;
                                attribute sigma_Cx : Real = 28.721044428837228;
                                attribute Cy : Real = -20.87032371200621;
                                attribute sigma_Cy : Real = 28.23690002309109;
                                attribute Cz : Real = 9.516456397250295;
                                attribute sigma_Cz : Real = 29.057750463592832;
                                attribute Ixx : Real = 0.8736980676978113;
                                attribute sigma_Ixx : Real = 0.37074144170588635;
                                attribute Iyy : Real = 0.8984059541864781;
                                attribute sigma_Iyy : Real = 0.3723953238821935;
                                attribute Izz : Real = 0.8272458262687516;
                                attribute sigma_Izz : Real = 0.37017423652493897;
                                attribute Ixy : Real = 0.05261144903563116;
                                attribute sigma_Ixy : Real = 0.02351283871158888;
                                attribute Ixz : Real = -0.042462779152416655;
                                attribute sigma_Ixz : Real = 0.022566176940390956;
                                attribute Iyz : Real = 0.03292772291785614;
                                attribute sigma_Iyz : Real = 0.02209918015384651;
                            }
                            part <'C.1.2.3.3.4.1.2'> 'Part 1160' {
                                attribute POIconv : String = "-";
                                attribute Ipoint : Boolean = false;
                                attribute mass : Real = 0.6371451087531168;
                                attribute sigma_mass : Real = 0.28909372274994966;
                                attribute Cx : Real = 76.25436382368207;
                                attribute sigma_Cx : Real = 28.721044428837228;
                                attribute Cy : Real = 6.33819280192256;
                                attribute sigma_Cy : Real = 28.23690002309109;
                                attribute Cz : Real = -33.47769808024168;
                                attribute sigma_Cz : Real = 29.057750463592832;
                                attribute Ixx : Real = 0.9194108974451034;
                                attribute sigma_Ixx : Real = 0.37074144170588635;
                                attribute Iyy : Real = 0.8882589578714308;
                                attribute sigma_Iyy : Real = 0.3723953238821935;
                                attribute Izz : Real = 0.8272522240211637;
                                attribute sigma_Izz : Real = 0.37017423652493897;
                                attribute Ixy : Real = 0.014605514666435369;
                                attribute sigma_Ixy : Real = 0.02351283871158888;
                                attribute Ixz : Real = 0.004397523652002532;
                                attribute sigma_Ixz : Real = 0.022566176940390956;
                                attribute Iyz : Real = 0.04619760827854258;
                                attribute sigma_Iyz : Real = 0.02209918015384651;
                            }
                            part <'C.1.2.3.3.4.1.3'> 'Part 1161' {
                                attribute POIconv : String = "+";
                                attribute Ipoint : Boolean = false;
                                attribute mass : Real = 0.9055529230181127;
                                attribute sigma_mass : Real = 0.28909372274994966;
                                attribute Cx : Real = -20.364547381177545;
                                attribute sigma_Cx : Real = 28.721044428837228;
                                attribute Cy : Real = -10.368261765688658;
                                attribute sigma_Cy : Real = 28.23690002309109;
                                attribute Cz : Real = 45.30077567324042;
                                attribute sigma_Cz : Real = 29.057750463592832;
                                attribute Ixx : Real = 1.1377331000815702;
                                attribute sigma_Ixx : Real = 0.37074144170588635;
                                attribute Iyy : Real = 1.0836667815234615;
                                attribute sigma_Iyy : Real = 0.3723953238821935;
                                attribute Izz : Real = 1.1487037806721623;
                                attribute sigma_Izz : Real = 0.37017423652493897;
                                attribute Ixy : Real = -0.04242739765160772;
                                attribute sigma_Ixy : Real = 0.02351283871158888;
                                attribute Ixz : Real = 0.05616368806906573;
                                attribute sigma_Ixz : Real = 0.022566176940390956;
                                attribute Iyz : Real = 0.05112533860318922;
                                attribute sigma_Iyz : Real = 0.02209918015384651;
                            }
                            part <'C.1.2.3.3.4.1.4'> 'Part 1162' {
                                attribute POIconv : String = "-";
                                attribute Ipoint : Boolean = false;
                                attribute mass : Real = 0.07659709179936908;
                                attribute sigma_mass : Real = 0.28909372274994966;
                                attribute Cx : Real = 54.52306047081947;
                                attribute sigma_Cx : Real = 28.721044428837228;
                                attribute Cy : Real = -88.03657772950828;
                                attribute sigma_Cy : Real = 28.23690002309109;
                                attribute Cz : Real = -90.6695815268904;
                                attribute sigma_Cz : Real = 29.057750463592832;
                                attribute Ixx : Real = 0.10147572257623734;
                                attribute sigma_Ixx : Real = 0.37074144170588635;
                                attribute Iyy : Real = 0.09890702791589893;
                                attribute sigma_Iyy : Real = 0.3723953238821935;
                                attribute Izz : Real = 0.09662101080797235;
                                attribute sigma_Izz : Real = 0.37017423652493897;
                                attribute Ixy : Real = -0.003850059811865432;
                                attribute sigma_Ixy : Real = 0.02351283871158888;
                                attribute Ixz : Real = -0.004894159244334374;
                                attribute sigma_Ixz : Real = 0.022566176940390956;
                                attribute Iyz : Real = -0.00534731897596152;
                                attribute sigma_Iyz : Real = 0.02209918015384651;
                            }
                        }
                        part <'C.1.2.3.3.4.2'> 'Subassembly 329' {
                            attribute POIconv : String = "-";
                            attribute Ipoint : Boolean = false;
                            attribute mass : Real = 2.503216883439338;
                            attribute sigma_mass : Real = 0.6464332159373649;
                            attribute Cx : Real = -16.92045810346625;
                            attribute sigma_Cx : Real = 25.14793383899714;
                            attribute Cy : Real = 1.6288512412159608;
                            attribute sigma_Cy : Real = 19.395872885554176;
                            attribute Cz : Real = -25.288057645688905;
                            attribute sigma_Cz : Real = 22.212232444679294;
                            attribute Ixx : Real = 11715.297642348196;
                            attribute sigma_Ixx : Real = 7129.044254410205;
                            attribute Iyy : Real = 15055.911608132963;
                            attribute sigma_Iyy : Real = 9867.359123096705;
                            attribute Izz : Real = 15614.85682136997;
                            attribute sigma_Izz : Real = 7980.684917256025;
                            attribute Ixy : Real = -5489.4429193435435;
                            attribute sigma_Ixy : Real = 3547.9312337993147;
                            attribute Ixz : Real = -4100.834376459769;
                            attribute sigma_Ixz : Real = 4730.338423194854;
                            attribute Iyz : Real = -1024.6091303081955;
                            attribute sigma_Iyz : Real = 2890.421827753637;
                            part <'C.1.2.3.3.4.2.1'> 'Part 1163' {
                                attribute POIconv : String = "+";
                                attribute Ipoint : Boolean = false;
                                attribute mass : Real = 0.21082770662684924;
                                attribute sigma_mass : Real = 0.28909372274994966;
                                attribute Cx : Real = 69.8582960292697;
                                attribute sigma_Cx : Real = 28.721044428837228;
                                attribute Cy : Real = 56.49674846790731;
                                attribute sigma_Cy : Real = 28.23690002309109;
                                attribute Cz : Real = -76.12224486656487;
                                attribute sigma_Cz : Real = 29.057750463592832;
                                attribute Ixx : Real = 0.2256526384627233;
                                attribute sigma_Ixx : Real = 0.37074144170588635;
                                attribute Iyy : Real = 0.21901422902787354;
                                attribute sigma_Iyy : Real = 0.3723953238821935;
                                attribute Izz : Real = 0.22196618404322313;
                                attribute sigma_Izz : Real = 0.37017423652493897;
                                attribute Ixy : Real = -0.0005243276115298734;
                                attribute sigma_Ixy : Real = 0.02351283871158888;
                                attribute Ixz : Real = 0.002808377481176116;
                                attribute sigma_Ixz : Real = 0.022566176940390956;
                                attribute Iyz : Real = -0.010564354526211142;
                                attribute sigma_Iyz : Real = 0.02209918015384651;
                            }
                            part <'C.1.2.3.3.4.2.2'> 'Part 1164' {
                                attribute POIconv : String = "+";
                                attribute Ipoint : Boolean = false;
                                attribute mass : Real = 0.20865075647411868;
                                attribute sigma_mass : Real = 0.28909372274994966;
                                attribute Cx : Real = 67.55500230938196;
                                attribute sigma_Cx : Real = 28.721044428837228;
                                attribute Cy : Real = 35.14960375614464;
                                attribute sigma_Cy : Real = 28.23690002309109;
                                attribute Cz : Real = -12.420725729316473;
                                attribute sigma_Cz : Real = 29.057750463592832;
                                attribute Ixx : Real = 0.2883609895685834;
                                attribute sigma_Ixx : Real = 0.37074144170588635;
                                attribute Iyy : Real = 0.2668000915645318;
                                attribute sigma_Iyy : Real = 0.3723953238821935;
                                attribute Izz : Real = 0.2836593105032307;
                                attribute sigma_Izz : Real = 0.37017423652493897;
                                attribute Ixy : Real = -0.00617069731588449;
                                attribute sigma_Ixy : Real = 0.02351283871158888;
                                attribute Ixz : Real = 0.0058078828912204485;
                                attribute sigma_Ixz : Real = 0.022566176940390956;
                                attribute Iyz : Real = -0.0025366101542495935;
                                attribute sigma_Iyz : Real = 0.02209918015384651;
                            }
                            part <'C.1.2.3.3.4.2.3'> 'Part 1165' {
                                attribute POIconv : String = "+";
                                attribute Ipoint : Boolean = false;
                                attribute mass : Real = 0.9036840868147555;
                                attribute sigma_mass : Real = 0.28909372274994966;
                                attribute Cx : Real = -37.714927503839135;
                                attribute sigma_Cx : Real = 28.721044428837228;
                                attribute Cy : Real = 33.008114295080304;
                                attribute sigma_Cy : Real = 28.23690002309109;
                                attribute Cz : Real = -45.969417644664645;
                                attribute sigma_Cz : Real = 29.057750463592832;
                                attribute Ixx : Real = 1.0490112578914066;
                                attribute sigma_Ixx : Real = 0.37074144170588635;
                                attribute Iyy : Real = 1.1896105585334824;
                                attribute sigma_Iyy : Real = 0.3723953238821935;
                                attribute Izz : Real = 1.0395761789049052;
                                attribute sigma_Izz : Real = 0.37017423652493897;
                                attribute Ixy : Real = 0.03880308333734295;
                                attribute sigma_Ixy : Real = 0.02351283871158888;
                                attribute Ixz : Real = -0.0034240903381612246;
                                attribute sigma_Ixz : Real = 0.022566176940390956;
                                attribute Iyz : Real = 0.005282077233799953;
                                attribute sigma_Iyz : Real = 0.02209918015384651;
                            }
                            part <'C.1.2.3.3.4.2.4'> 'Part 1166' {
                                attribute POIconv : String = "-";
                                attribute Ipoint : Boolean = false;
                                attribute mass : Real = 0.8923097606853116;
                                attribute sigma_mass : Real = 0.28909372274994966;
                                attribute Cx : Real = -71.1104148067534;
                                attribute sigma_Cx : Real = 28.721044428837228;
                                attribute Cy : Real = -64.32791547849774;
                                attribute sigma_Cy : Real = 28.23690002309109;
                                attribute Cz : Real = -35.727845365181565;
                                attribute sigma_Cz : Real = 29.057750463592832;
                                attribute Ixx : Real = 1.0978955725900148;
                                attribute sigma_Ixx : Real = 0.37074144170588635;
                                attribute Iyy : Real = 1.4156295401370689;
                                attribute sigma_Iyy : Real = 0.3723953238821935;
                                attribute Izz : Real = 1.1581046131238177;
                                attribute sigma_Izz : Real = 0.37017423652493897;
                                attribute Ixy : Real = -0.012990731430555928;
                                attribute sigma_Ixy : Real = 0.02351283871158888;
                                attribute Ixz : Real = -0.013012539246183279;
                                attribute sigma_Ixz : Real = 0.022566176940390956;
                                attribute Iyz : Real = 0.0701197318106209;
                                attribute sigma_Iyz : Real = 0.02209918015384651;
                            }
                            part <'C.1.2.3.3.4.2.5'> 'Part 1167' {
                                attribute POIconv : String = "+";
                                attribute Ipoint : Boolean = false;
                                attribute mass : Real = 0.2877445728383027;
                                attribute sigma_mass : Real = 0.28909372274994966;
                                attribute Cx : Real = 91.59461706876755;
                                attribute sigma_Cx : Real = 28.721044428837228;
                                attribute Cy : Real = 43.10703664086759;
                                attribute sigma_Cy : Real = 28.23690002309109;
                                attribute Cz : Real = 99.95293864049017;
                                attribute sigma_Cz : Real = 29.057750463592832;
                                attribute Ixx : Real = 0.3308934551706392;
                                attribute sigma_Ixx : Real = 0.37074144170588635;
                                attribute Iyy : Real = 0.31470614438608446;
                                attribute sigma_Iyy : Real = 0.3723953238821935;
                                attribute Izz : Real = 0.31290358849449484;
                                attribute sigma_Izz : Real = 0.37017423652493897;
                                attribute Ixy : Real = -0.024504422291383124;
                                attribute sigma_Ixy : Real = 0.02351283871158888;
                                attribute Ixz : Real = 0.0009465158771882105;
                                attribute sigma_Ixz : Real = 0.022566176940390956;
                                attribute Iyz : Real = -0.003915303088483573;
                                attribute sigma_Iyz : Real = 0.02209918015384651;
                            }
                        }
                        part <'C.1.2.3.3.4.3'> 'Subassembly 330' {
                            attribute POIconv : String = "-";
                            attribute Ipoint : Boolean = false;
                            attribute mass : Real = 1.3586764709015842;
                            attribute sigma_mass : Real = 0.5007250159521434;
                            attribute Cx : Real = 11.687921798033457;
                            attribute sigma_Cx : Real = 25.466756491003288;
                            attribute Cy : Real = -17.640130462991785;
                            attribute sigma_Cy : Real = 25.95589958350827;
                            attribute Cz : Real = 1.8496324467733223;
                            attribute sigma_Cz : Real = 26.205646745896846;
                            attribute Ixx : Real = 4591.386872997812;
                            attribute sigma_Ixx : Real = 3780.3229841461866;
                            attribute Iyy : Real = 4187.822479357164;
                            attribute sigma_Iyy : Real = 3603.862285957813;
                            attribute Izz : Real = 6988.12106905036;
                            attribute sigma_Izz : Real = 4479.749295066062;
                            attribute Ixy : Real = -3324.3356465986735;
                            attribute sigma_Ixy : Real = 2239.2992513260565;
                            attribute Ixz : Real = 522.1835281897347;
                            attribute sigma_Ixz : Real = 1475.0161553120022;
                            attribute Iyz : Real = 1050.9212480297313;
                            attribute sigma_Iyz : Real = 1624.3257064690483;
                            part <'C.1.2.3.3.4.3.1'> 'Part 1168' {
                                attribute POIconv : String = "+";
                                attribute Ipoint : Boolean = false;
                                attribute mass : Real = 0.5087709793595131;
                                attribute sigma_mass : Real = 0.28909372274994966;
                                attribute Cx : Real = 75.06642527878284;
                                attribute sigma_Cx : Real = 28.721044428837228;
                                attribute Cy : Real = 44.61297080852091;
                                attribute sigma_Cy : Real = 28.23690002309109;
                                attribute Cz : Real = -5.477722082287073;
                                attribute sigma_Cz : Real = 29.057750463592832;
                                attribute Ixx : Real = 0.6321992396457022;
                                attribute sigma_Ixx : Real = 0.37074144170588635;
                                attribute Iyy : Real = 0.6624704425798316;
                                attribute sigma_Iyy : Real = 0.3723953238821935;
                                attribute Izz : Real = 0.5840726066876287;
                                attribute sigma_Izz : Real = 0.37017423652493897;
                                attribute Ixy : Real = -0.0065827568759038195;
                                attribute sigma_Ixy : Real = 0.02351283871158888;
                                attribute Ixz : Real = -0.05471269287272852;
                                attribute sigma_Ixz : Real = 0.022566176940390956;
                                attribute Iyz : Real = 0.009373431557905815;
                                attribute sigma_Iyz : Real = 0.02209918015384651;
                            }
                            part <'C.1.2.3.3.4.3.2'> 'Part 1169' {
                                attribute POIconv : String = "-";
                                attribute Ipoint : Boolean = false;
                                attribute mass : Real = 0.10343382902443408;
                                attribute sigma_mass : Real = 0.28909372274994966;
                                attribute Cx : Real = -11.829330306500196;
                                attribute sigma_Cx : Real = 28.721044428837228;
                                attribute Cy : Real = 13.006323808804154;
                                attribute sigma_Cy : Real = 28.23690002309109;
                                attribute Cz : Real = -78.77780334092677;
                                attribute sigma_Cz : Real = 29.057750463592832;
                                attribute Ixx : Real = 0.12379197400861093;
                                attribute sigma_Ixx : Real = 0.37074144170588635;
                                attribute Iyy : Real = 0.11439372826237404;
                                attribute sigma_Iyy : Real = 0.3723953238821935;
                                attribute Izz : Real = 0.10929187094039318;
                                attribute sigma_Izz : Real = 0.37017423652493897;
                                attribute Ixy : Real = 0.000844096566023753;
                                attribute sigma_Ixy : Real = 0.02351283871158888;
                                attribute Ixz : Real = 0.006447223098256013;
                                attribute sigma_Ixz : Real = 0.022566176940390956;
                                attribute Iyz : Real = 0.01421954460641909;
                                attribute sigma_Iyz : Real = 0.02209918015384651;
                            }
                            part <'C.1.2.3.3.4.3.3'> 'Part 1170' {
                                attribute POIconv : String = "+";
                                attribute Ipoint : Boolean = false;
                                attribute mass : Real = 0.746471662517637;
                                attribute sigma_mass : Real = 0.28909372274994966;
                                attribute Cx : Real = -28.250183491036296;
                                attribute sigma_Cx : Real = 28.721044428837228;
                                attribute Cy : Real = -64.31631813757122;
                                attribute sigma_Cy : Real = 28.23690002309109;
                                attribute Cz : Real = 18.015751475468278;
                                attribute sigma_Cz : Real = 29.057750463592832;
                                attribute Ixx : Real = 0.6543642174225006;
                                attribute sigma_Ixx : Real = 0.37074144170588635;
                                attribute Iyy : Real = 0.7278075294922773;
                                attribute sigma_Iyy : Real = 0.3723953238821935;
                                attribute Izz : Real = 0.7380626975517567;
                                attribute sigma_Izz : Real = 0.37017423652493897;
                                attribute Ixy : Real = -0.011720419639288425;
                                attribute sigma_Ixy : Real = 0.02351283871158888;
                                attribute Ixz : Real = -0.020278479770480987;
                                attribute sigma_Ixz : Real = 0.022566176940390956;
                                attribute Iyz : Real = 0.00627879447604285;
                                attribute sigma_Iyz : Real = 0.02209918015384651;
                            }
                        }
                        part <'C.1.2.3.3.4.4'> 'Subassembly 331' {
                            attribute POIconv : String = "-";
                            attribute Ipoint : Boolean = false;
                            attribute mass : Real = 1.1425734868128783;
                            attribute sigma_mass : Real = 0.40884026350990615;
                            attribute Cx : Real = 29.700648450378136;
                            attribute sigma_Cx : Real = 24.111194649145048;
                            attribute Cy : Real = 40.34464931894527;
                            attribute sigma_Cy : Real = 25.007248146614316;
                            attribute Cz : Real = 3.3994090365413125;
                            attribute sigma_Cz : Real = 31.244434866234975;
                            attribute Ixx : Real = 1970.234816280717;
                            attribute sigma_Ixx : Real = 2557.8709386285655;
                            attribute Iyy : Real = 1711.293961605328;
                            attribute sigma_Iyy : Real = 2285.5742515555517;
                            attribute Izz : Real = 399.40797594950516;
                            attribute sigma_Izz : Real = 794.0938061519754;
                            attribute Ixy : Real = -150.99849864335312;
                            attribute sigma_Ixy : Real = 377.1047029220601;
                            attribute Ixz : Real = -337.5497751937751;
                            attribute sigma_Ixz : Real = 794.8251875587931;
                            attribute Iyz : Real = -733.9194577890853;
                            attribute sigma_Iyz : Real = 1072.7592470729787;
                            part <'C.1.2.3.3.4.4.1'> 'Part 1171' {
                                attribute POIconv : String = "+";
                                attribute Ipoint : Boolean = false;
                                attribute mass : Real = 0.9181259398835245;
                                attribute sigma_mass : Real = 0.28909372274994966;
                                attribute Cx : Real = 25.845273584127426;
                                attribute sigma_Cx : Real = 28.721044428837228;
                                attribute Cy : Real = 31.96282321587205;
                                attribute sigma_Cy : Real = 28.23690002309109;
                                attribute Cz : Real = -15.334486961364746;
                                attribute sigma_Cz : Real = 29.057750463592832;
                                attribute Ixx : Real = 1.225434669928097;
                                attribute sigma_Ixx : Real = 0.37074144170588635;
                                attribute Iyy : Real = 1.1688951140896207;
                                attribute sigma_Iyy : Real = 0.3723953238821935;
                                attribute Izz : Real = 1.2376403923758996;
                                attribute sigma_Izz : Real = 0.37017423652493897;
                                attribute Ixy : Real = -0.03155637926558796;
                                attribute sigma_Ixy : Real = 0.02351283871158888;
                                attribute Ixz : Real = -0.009375586480591754;
                                attribute sigma_Ixz : Real = 0.022566176940390956;
                                attribute Iyz : Real = 0.018458549869264082;
                                attribute sigma_Iyz : Real = 0.02209918015384651;
                            }
                            part <'C.1.2.3.3.4.4.2'> 'Part 1172' {
                                attribute POIconv : String = "-";
                                attribute Ipoint : Boolean = false;
                                attribute mass : Real = 0.22444754692935384;
                                attribute sigma_mass : Real = 0.28909372274994966;
                                attribute Cx : Real = 45.471458695828915;
                                attribute sigma_Cx : Real = 28.721044428837228;
                                attribute Cy : Real = 74.63137721642852;
                                attribute sigma_Cy : Real = 28.23690002309109;
                                attribute Cz : Real = 80.03235114738345;
                                attribute sigma_Cz : Real = 29.057750463592832;
                                attribute Ixx : Real = 0.33360246910305097;
                                attribute sigma_Ixx : Real = 0.37074144170588635;
                                attribute Iyy : Real = 0.3370219269586817;
                                attribute sigma_Iyy : Real = 0.3723953238821935;
                                attribute Izz : Real = 0.3402139006344269;
                                attribute sigma_Izz : Real = 0.37017423652493897;
                                attribute Ixy : Real = 0.0046649779491889;
                                attribute sigma_Ixy : Real = 0.02351283871158888;
                                attribute Ixz : Real = 0.012722194545028018;
                                attribute sigma_Ixz : Real = 0.022566176940390956;
                                attribute Iyz : Real = 0.001366865877167227;
                                attribute sigma_Iyz : Real = 0.02209918015384651;
                            }
                        }
                        part <'C.1.2.3.3.4.5'> 'Subassembly 332' {
                            attribute POIconv : String = "-";
                            attribute Ipoint : Boolean = false;
                            attribute mass : Real = 2.456790610935539;
                            attribute sigma_mass : Real = 0.6464332159373649;
                            attribute Cx : Real = -61.39151116169154;
                            attribute sigma_Cx : Real = 21.182617611377047;
                            attribute Cy : Real = -32.291391087407625;
                            attribute sigma_Cy : Real = 21.62872382753251;
                            attribute Cz : Real = 12.861543353811523;
                            attribute sigma_Cz : Real = 19.171776457208242;
                            attribute Ixx : Real = 6335.895426163233;
                            attribute sigma_Ixx : Real = 7629.224462330214;
                            attribute Iyy : Real = 6619.849306813419;
                            attribute sigma_Iyy : Real = 6193.673216078373;
                            attribute Izz : Real = 6934.821510773546;
                            attribute sigma_Izz : Real = 8594.812045107095;
                            attribute Ixy : Real = -2632.9614531627867;
                            attribute sigma_Ixy : Real = 4132.515306079434;
                            attribute Ixz : Real = -933.8806186480903;
                            attribute sigma_Ixz : Real = 2975.2878652421937;
                            attribute Iyz : Real = -1366.5968077316534;
                            attribute sigma_Iyz : Real = 3516.372973820078;
                            part <'C.1.2.3.3.4.5.1'> 'Part 1173' {
                                attribute POIconv : String = "-";
                                attribute Ipoint : Boolean = false;
                                attribute mass : Real = 0.955625822631875;
                                attribute sigma_mass : Real = 0.28909372274994966;
                                attribute Cx : Real = -80.15746069140732;
                                attribute sigma_Cx : Real = 28.721044428837228;
                                attribute Cy : Real = -30.156374536454678;
                                attribute sigma_Cy : Real = 28.23690002309109;
                                attribute Cz : Real = -12.001685472205281;
                                attribute sigma_Cz : Real = 29.057750463592832;
                                attribute Ixx : Real = 1.1106261429312312;
                                attribute sigma_Ixx : Real = 0.37074144170588635;
                                attribute Iyy : Real = 1.2485890954920487;
                                attribute sigma_Iyy : Real = 0.3723953238821935;
                                attribute Izz : Real = 1.2531707961635905;
                                attribute sigma_Izz : Real = 0.37017423652493897;
                                attribute Ixy : Real = 0.021882301753942776;
                                attribute sigma_Ixy : Real = 0.02351283871158888;
                                attribute Ixz : Real = -0.14712071527640036;
                                attribute sigma_Ixz : Real = 0.022566176940390956;
                                attribute Iyz : Real = -0.044431654822483346;
                                attribute sigma_Iyz : Real = 0.02209918015384651;
                            }
                            part <'C.1.2.3.3.4.5.2'> 'Part 1174' {
                                attribute POIconv : String = "+";
                                attribute Ipoint : Boolean = false;
                                attribute mass : Real = 0.545603597829584;
                                attribute sigma_mass : Real = 0.28909372274994966;
                                attribute Cx : Real = -86.98755013756454;
                                attribute sigma_Cx : Real = 28.721044428837228;
                                attribute Cy : Real = -53.339227847754955;
                                attribute sigma_Cy : Real = 28.23690002309109;
                                attribute Cz : Real = 56.995693407952785;
                                attribute sigma_Cz : Real = 29.057750463592832;
                                attribute Ixx : Real = 0.7432740273983538;
                                attribute sigma_Ixx : Real = 0.37074144170588635;
                                attribute Iyy : Real = 0.6576012643915549;
                                attribute sigma_Iyy : Real = 0.3723953238821935;
                                attribute Izz : Real = 0.7477311569063766;
                                attribute sigma_Izz : Real = 0.37017423652493897;
                                attribute Ixy : Real = -0.021645632840158198;
                                attribute sigma_Ixy : Real = 0.02351283871158888;
                                attribute Ixz : Real = 0.00549467540041061;
                                attribute sigma_Ixz : Real = 0.022566176940390956;
                                attribute Iyz : Real = -0.019009048199629362;
                                attribute sigma_Iyz : Real = 0.02209918015384651;
                            }
                            part <'C.1.2.3.3.4.5.3'> 'Part 1175' {
                                attribute POIconv : String = "+";
                                attribute Ipoint : Boolean = false;
                                attribute mass : Real = 0.15502261463995093;
                                attribute sigma_mass : Real = 0.28909372274994966;
                                attribute Cx : Real = 42.17293206602335;
                                attribute sigma_Cx : Real = 28.721044428837228;
                                attribute Cy : Real = 99.18043753132224;
                                attribute sigma_Cy : Real = 28.23690002309109;
                                attribute Cz : Real = 98.11067711561918;
                                attribute sigma_Cz : Real = 29.057750463592832;
                                attribute Ixx : Real = 0.16351896922744752;
                                attribute sigma_Ixx : Real = 0.37074144170588635;
                                attribute Iyy : Real = 0.15392284576391796;
                                attribute sigma_Iyy : Real = 0.3723953238821935;
                                attribute Izz : Real = 0.15985165412760657;
                                attribute sigma_Izz : Real = 0.37017423652493897;
                                attribute Ixy : Real = -0.0004269991105755182;
                                attribute sigma_Ixy : Real = 0.02351283871158888;
                                attribute Ixz : Real = 0.00033465252152815243;
                                attribute sigma_Ixz : Real = 0.022566176940390956;
                                attribute Iyz : Real = -0.004964485338095095;
                                attribute sigma_Iyz : Real = 0.02209918015384651;
                            }
                            part <'C.1.2.3.3.4.5.4'> 'Part 1176' {
                                attribute POIconv : String = "-";
                                attribute Ipoint : Boolean = false;
                                attribute mass : Real = 0.2544909297064878;
                                attribute sigma_mass : Real = 0.28909372274994966;
                                attribute Cx : Real = 8.527061203494668;
                                attribute sigma_Cx : Real = 28.721044428837228;
                                attribute Cy : Real = -20.128681743517518;
                                attribute sigma_Cy : Real = 28.23690002309109;
                                attribute Cz : Real = -3.8641369435936213;
                                attribute sigma_Cz : Real = 29.057750463592832;
                                attribute Ixx : Real = 0.32669400680453;
                                attribute sigma_Ixx : Real = 0.37074144170588635;
                                attribute Iyy : Real = 0.34179922899878074;
                                attribute sigma_Iyy : Real = 0.3723953238821935;
                                attribute Izz : Real = 0.2769346032467346;
                                attribute sigma_Izz : Real = 0.37017423652493897;
                                attribute Ixy : Real = 0.01472239043269392;
                                attribute sigma_Ixy : Real = 0.02351283871158888;
                                attribute Ixz : Real = 0.0013145797617428556;
                                attribute sigma_Ixz : Real = 0.022566176940390956;
                                attribute Iyz : Real = 0.0013911618466437097;
                                attribute sigma_Iyz : Real = 0.02209918015384651;
                            }
                            part <'C.1.2.3.3.4.5.5'> 'Part 1177' {
                                attribute POIconv : String = "-";
                                attribute Ipoint : Boolean = false;
                                attribute mass : Real = 0.5460476461276412;
                                attribute sigma_mass : Real = 0.28909372274994966;
                                attribute Cx : Real = -64.96254815720022;
                                attribute sigma_Cx : Real = 28.721044428837228;
                                attribute Cy : Real = -57.990443939343095;
                                attribute sigma_Cy : Real = 28.23690002309109;
                                attribute Cz : Real = -4.131144564598799;
                                attribute sigma_Cz : Real = 29.057750463592832;
                                attribute Ixx : Real = 0.6982731914652558;
                                attribute sigma_Ixx : Real = 0.37074144170588635;
                                attribute Iyy : Real = 0.7108185963025712;
                                attribute sigma_Iyy : Real = 0.3723953238821935;
                                attribute Izz : Real = 0.7289567208157977;
                                attribute sigma_Izz : Real = 0.37017423652493897;
                                attribute Ixy : Real = -0.07980760082283507;
                                attribute sigma_Ixy : Real = 0.02351283871158888;
                                attribute Ixz : Real = -0.012689021004058278;
                                attribute sigma_Ixz : Real = 0.022566176940390956;
                                attribute Iyz : Real = 0.02523158009672751;
                                attribute sigma_Iyz : Real = 0.02209918015384651;
                            }
                        }
                    }
                    part <'C.1.2.3.3.5'> 'Assembly 97' {
                        attribute POIconv : String = "-";
                        attribute Ipoint : Boolean = false;
                        attribute mass : Real = 11.582275818926746;
                        attribute sigma_mass : Real = 1.260130322678996;
                        attribute Cx : Real = 2.1290110725778653;
                        attribute sigma_Cx : Real = 9.841164657384184;
                        attribute Cy : Real = 15.838868124623646;
                        attribute sigma_Cy : Real = 8.70174930485096;
                        attribute Cz : Real = 2.3603408090444793;
                        attribute sigma_Cz : Real = 9.704172603764771;
                        attribute Ixx : Real = 62946.672482979746;
                        attribute sigma_Ixx : Real = 14998.303660438187;
                        attribute Iyy : Real = 78583.9026973708;
                        attribute sigma_Iyy : Real = 17531.544698771304;
                        attribute Izz : Real = 63395.90566539344;
                        attribute sigma_Izz : Real = 14809.925392786334;
                        attribute Ixy : Real = -20296.246535677667;
                        attribute sigma_Ixy : Real = 6960.466325622369;
                        attribute Ixz : Real = -741.3005685133467;
                        attribute sigma_Ixz : Real = 8412.45878565277;
                        attribute Iyz : Real = -7066.942804953164;
                        attribute sigma_Iyz : Real = 7025.708498286432;
                        part <'C.1.2.3.3.5.1'> 'Subassembly 333' {
                            attribute POIconv : String = "-";
                            attribute Ipoint : Boolean = false;
                            attribute mass : Real = 1.0247386306512636;
                            attribute sigma_mass : Real = 0.40884026350990615;
                            attribute Cx : Real = 19.604131208715234;
                            attribute sigma_Cx : Real = 40.458540065402474;
                            attribute Cy : Real = 5.059918360783365;
                            attribute sigma_Cy : Real = 21.680098654343954;
                            attribute Cz : Real = 32.23865669225487;
                            attribute sigma_Cz : Real = 27.86185063416166;
                            attribute Ixx : Real = 1339.409562993181;
                            attribute sigma_Ixx : Real = 1660.2114756622839;
                            attribute Iyy : Real = 6649.331319262816;
                            attribute sigma_Iyy : Real = 5457.452378144204;
                            attribute Izz : Real = 5362.588939628073;
                            attribute sigma_Izz : Real = 4561.337285797225;
                            attribute Ixy : Real = -370.72427429580273;
                            attribute sigma_Ixy : Real = 1375.664320167702;
                            attribute Ixz : Real = 2646.2492905849726;
                            attribute sigma_Ixz : Real = 2369.759486856703;
                            attribute Iyz : Real = 183.85866672349144;
                            attribute sigma_Iyz : Real = 687.4349650234448;
                            part <'C.1.2.3.3.5.1.1'> 'Part 1178' {
                                attribute POIconv : String = "-";
                                attribute Ipoint : Boolean = false;
                                attribute mass : Real = 0.30423817377421075;
                                attribute sigma_mass : Real = 0.28909372274994966;
                                attribute Cx : Real = -91.44046362489462;
                                attribute sigma_Cx : Real = 28.721044428837228;
                                attribute Cy : Real = -2.6556380093097687;
                                attribute sigma_Cy : Real = 28.23690002309109;
                                attribute Cz : Real = 87.31230134144425;
                                attribute sigma_Cz : Real = 29.057750463592832;
                                attribute Ixx : Real = 0.38242099653739703;
                                attribute sigma_Ixx : Real = 0.37074144170588635;
                                attribute Iyy : Real = 0.386561360595014;
                                attribute sigma_Iyy : Real = 0.3723953238821935;
                                attribute Izz : Real = 0.37932622101010294;
                                attribute sigma_Izz : Real = 0.37017423652493897;
                                attribute Ixy : Real = 0.0027441751408110006;
                                attribute sigma_Ixy : Real = 0.02351283871158888;
                                attribute Ixz : Real = 8.645390658974968e-05;
                                attribute sigma_Ixz : Real = 0.022566176940390956;
                                attribute Iyz : Real = -0.0005326007681602408;
                                attribute sigma_Iyz : Real = 0.02209918015384651;
                            }
                            part <'C.1.2.3.3.5.1.2'> 'Part 1179' {
                                attribute POIconv : String = "+";
                                attribute Ipoint : Boolean = false;
                                attribute mass : Real = 0.7205004568770528;
                                attribute sigma_mass : Real = 0.28909372274994966;
                                attribute Cx : Real = 66.49376801215112;
                                attribute sigma_Cx : Real = 28.721044428837228;
                                attribute Cy : Real = 8.3178854547441;
                                attribute sigma_Cy : Real = 28.23690002309109;
                                attribute Cz : Real = 8.983286190778017;
                                attribute sigma_Cz : Real = 29.057750463592832;
                                attribute Ixx : Real = 0.8260469850896712;
                                attribute sigma_Ixx : Real = 0.37074144170588635;
                                attribute Iyy : Real = 0.8517171435029138;
                                attribute sigma_Iyy : Real = 0.3723953238821935;
                                attribute Izz : Real = 0.7998987885800434;
                                attribute sigma_Izz : Real = 0.37017423652493897;
                                attribute Ixy : Real = -0.0025502495830517016;
                                attribute sigma_Ixy : Real = 0.02351283871158888;
                                attribute Ixz : Real = 0.018614973087416508;
                                attribute sigma_Ixz : Real = 0.022566176940390956;
                                attribute Iyz : Real = 0.007728726179584821;
                                attribute sigma_Iyz : Real = 0.02209918015384651;
                            }
                        }
                        part <'C.1.2.3.3.5.2'> 'Subassembly 334' {
                            attribute POIconv : String = "-";
                            attribute Ipoint : Boolean = false;
                            attribute mass : Real = 1.8981830119004006;
                            attribute sigma_mass : Real = 0.5007250159521434;
                            attribute Cx : Real = -18.66899461883253;
                            attribute sigma_Cx : Real = 23.73177524420619;
                            attribute Cy : Real = -9.135376316177783;
                            attribute sigma_Cy : Real = 19.87872387551883;
                            attribute Cz : Real = -12.930070733406934;
                            attribute sigma_Cz : Real = 18.61187656013661;
                            attribute Ixx : Real = 3703.279586270617;
                            attribute sigma_Ixx : Real = 3019.935666715908;
                            attribute Iyy : Real = 8150.394104867487;
                            attribute sigma_Iyy : Real = 4884.633946627255;
                            attribute Izz : Real = 9776.211594037108;
                            attribute sigma_Izz : Real = 5555.993887421059;
                            attribute Ixy : Real = -4190.791051004699;
                            attribute sigma_Ixy : Real = 2692.9559998556756;
                            attribute Ixz : Real = -875.088536427362;
                            attribute sigma_Ixz : Real = 2276.2110413278256;
                            attribute Iyz : Real = -940.0006643042313;
                            attribute sigma_Iyz : Real = 1486.248901517143;
                            part <'C.1.2.3.3.5.2.1'> 'Part 1180' {
                                attribute POIconv : String = "+";
                                attribute Ipoint : Boolean = false;
                                attribute mass : Real = 0.43127991567412394;
                                attribute sigma_mass : Real = 0.28909372274994966;
                                attribute Cx : Real = -94.51196920126677;
                                attribute sigma_Cx : Real = 28.721044428837228;
                                attribute Cy : Real = -67.62745664454997;
                                attribute sigma_Cy : Real = 28.23690002309109;
                                attribute Cz : Real = -52.49585825949907;
                                attribute sigma_Cz : Real = 29.057750463592832;
                                attribute Ixx : Real = 0.5089482644993374;
                                attribute sigma_Ixx : Real = 0.37074144170588635;
                                attribute Iyy : Real = 0.5345940656523156;
                                attribute sigma_Iyy : Real = 0.3723953238821935;
                                attribute Izz : Real = 0.43371980639452906;
                                attribute sigma_Izz : Real = 0.37017423652493897;
                                attribute Ixy : Real = -0.011467873274092637;
                                attribute sigma_Ixy : Real = 0.02351283871158888;
                                attribute Ixz : Real = -0.0385133403477958;
                                attribute sigma_Ixz : Real = 0.022566176940390956;
                                attribute Iyz : Real = 0.019367090648829827;
                                attribute sigma_Iyz : Real = 0.02209918015384651;
                            }
                            part <'C.1.2.3.3.5.2.2'> 'Part 1181' {
                                attribute POIconv : String = "+";
                                attribute Ipoint : Boolean = false;
                                attribute mass : Real = 0.6705418300102465;
                                attribute sigma_mass : Real = 0.28909372274994966;
                                attribute Cx : Real = -52.5651712436229;
                                attribute sigma_Cx : Real = 28.721044428837228;
                                attribute Cy : Real = -16.648359829559922;
                                attribute sigma_Cy : Real = 28.23690002309109;
                                attribute Cz : Real = 10.222343821078539;
                                attribute sigma_Cz : Real = 29.057750463592832;
                                attribute Ixx : Real = 0.6882377407463639;
                                attribute sigma_Ixx : Real = 0.37074144170588635;
                                attribute Iyy : Real = 0.8130383945547924;
                                attribute sigma_Iyy : Real = 0.3723953238821935;
                                attribute Izz : Real = 0.8044460212722317;
                                attribute sigma_Izz : Real = 0.37017423652493897;
                                attribute Ixy : Real = -0.06758205507190732;
                                attribute sigma_Ixy : Real = 0.02351283871158888;
                                attribute Ixz : Real = 0.00948048436581599;
                                attribute sigma_Ixz : Real = 0.022566176940390956;
                                attribute Iyz : Real = -0.002577373244791746;
                                attribute sigma_Iyz : Real = 0.02209918015384651;
                            }
                            part <'C.1.2.3.3.5.2.3'> 'Part 1182' {
                                attribute POIconv : String = "-";
                                attribute Ipoint : Boolean = false;
                                attribute mass : Real = 0.7963612662160303;
                                attribute sigma_mass : Real = 0.28909372274994966;
                                attribute Cx : Real = 50.945586524903774;
                                attribute sigma_Cx : Real = 28.721044428837228;
                                attribute Cy : Real = 28.867764305323362;
                                attribute sigma_Cy : Real = 28.23690002309109;
                                attribute Cz : Real = -10.997195355594158;
                                attribute sigma_Cz : Real = 29.057750463592832;
                                attribute Ixx : Real = 0.9934271238119846;
                                attribute sigma_Ixx : Real = 0.37074144170588635;
                                attribute Iyy : Real = 0.9628380905975602;
                                attribute sigma_Iyy : Real = 0.3723953238821935;
                                attribute Izz : Real = 0.9137027178047246;
                                attribute sigma_Izz : Real = 0.37017423652493897;
                                attribute Ixy : Real = -0.027606016120134646;
                                attribute sigma_Ixy : Real = 0.02351283871158888;
                                attribute Ixz : Real = -0.009663652927892464;
                                attribute sigma_Ixz : Real = 0.022566176940390956;
                                attribute Iyz : Real = -0.018688522023214114;
                                attribute sigma_Iyz : Real = 0.02209918015384651;
                            }
                        }
                        part <'C.1.2.3.3.5.3'> 'Subassembly 335' {
                            attribute POIconv : String = "-";
                            attribute Ipoint : Boolean = false;
                            attribute mass : Real = 2.7401569926827216;
                            attribute sigma_mass : Real = 0.6464332159373649;
                            attribute Cx : Real = 12.157575753769288;
                            attribute sigma_Cx : Real = 18.356171666544526;
                            attribute Cy : Real = 38.84660107027787;
                            attribute sigma_Cy : Real = 18.226212050979022;
                            attribute Cz : Real = 11.7036863750483;
                            attribute sigma_Cz : Real = 19.424501340651965;
                            attribute Ixx : Real = 12536.387085533186;
                            attribute sigma_Ixx : Real = 6704.490346175134;
                            attribute Iyy : Real = 14236.272088596124;
                            attribute sigma_Iyy : Real = 6897.503059177842;
                            attribute Izz : Real = 7457.5308250199005;
                            attribute sigma_Izz : Real = 4907.225573606345;
                            attribute Ixy : Real = -3101.420309847911;
                            attribute sigma_Ixy : Real = 2301.8025404555665;
                            attribute Ixz : Real = 1566.7367734972674;
                            attribute sigma_Ixz : Real = 3266.7264565406063;
                            attribute Iyz : Real = 1316.8816125424632;
                            attribute sigma_Iyz : Real = 3088.5118732357328;
                            part <'C.1.2.3.3.5.3.1'> 'Part 1183' {
                                attribute POIconv : String = "-";
                                attribute Ipoint : Boolean = false;
                                attribute mass : Real = 0.15176071408181452;
                                attribute sigma_mass : Real = 0.28909372274994966;
                                attribute Cx : Real = -47.87710816599429;
                                attribute sigma_Cx : Real = 28.721044428837228;
                                attribute Cy : Real = -6.687679141759872;
                                attribute sigma_Cy : Real = 28.23690002309109;
                                attribute Cz : Real = 18.666162760928273;
                                attribute sigma_Cz : Real = 29.057750463592832;
                                attribute Ixx : Real = 0.14729331174887475;
                                attribute sigma_Ixx : Real = 0.37074144170588635;
                                attribute Iyy : Real = 0.1632888311960722;
                                attribute sigma_Iyy : Real = 0.3723953238821935;
                                attribute Izz : Real = 0.16580822073100293;
                                attribute sigma_Izz : Real = 0.37017423652493897;
                                attribute Ixy : Real = -0.00525362367617967;
                                attribute sigma_Ixy : Real = 0.02351283871158888;
                                attribute Ixz : Real = 0.003749598748022393;
                                attribute sigma_Ixz : Real = 0.022566176940390956;
                                attribute Iyz : Real = 0.003262346801937497;
                                attribute sigma_Iyz : Real = 0.02209918015384651;
                            }
                            part <'C.1.2.3.3.5.3.2'> 'Part 1184' {
                                attribute POIconv : String = "+";
                                attribute Ipoint : Boolean = false;
                                attribute mass : Real = 0.7122307940211613;
                                attribute sigma_mass : Real = 0.28909372274994966;
                                attribute Cx : Real = -36.32677481509745;
                                attribute sigma_Cx : Real = 28.721044428837228;
                                attribute Cy : Real = 22.489570593461394;
                                attribute sigma_Cy : Real = 28.23690002309109;
                                attribute Cz : Real = 10.23847064934671;
                                attribute sigma_Cz : Real = 29.057750463592832;
                                attribute Ixx : Real = 0.8893671757828507;
                                attribute sigma_Ixx : Real = 0.37074144170588635;
                                attribute Iyy : Real = 0.7892341138406285;
                                attribute sigma_Iyy : Real = 0.3723953238821935;
                                attribute Izz : Real = 0.7585659692934383;
                                attribute sigma_Izz : Real = 0.37017423652493897;
                                attribute Ixy : Real = -0.030936303163765357;
                                attribute sigma_Ixy : Real = 0.02351283871158888;
                                attribute Ixz : Real = 0.030972816081462545;
                                attribute sigma_Ixz : Real = 0.022566176940390956;
                                attribute Iyz : Real = 0.037887868304277136;
                                attribute sigma_Iyz : Real = 0.02209918015384651;
                            }
                            part <'C.1.2.3.3.5.3.3'> 'Part 1185' {
                                attribute POIconv : String = "+";
                                attribute Ipoint : Boolean = false;
                                attribute mass : Real = 0.9492864890261553;
                                attribute sigma_mass : Real = 0.28909372274994966;
                                attribute Cx : Real = 26.686201384291053;
                                attribute sigma_Cx : Real = 28.721044428837228;
                                attribute Cy : Real = 42.90138189680874;
                                attribute sigma_Cy : Real = 28.23690002309109;
                                attribute Cz : Real = 82.12528768926859;
                                attribute sigma_Cz : Real = 29.057750463592832;
                                attribute Ixx : Real = 1.3185949116024522;
                                attribute sigma_Ixx : Real = 0.37074144170588635;
                                attribute Iyy : Real = 1.3605636494769688;
                                attribute sigma_Iyy : Real = 0.3723953238821935;
                                attribute Izz : Real = 1.3700163503232434;
                                attribute sigma_Izz : Real = 0.37017423652493897;
                                attribute Ixy : Real = -0.001411921098397805;
                                attribute sigma_Ixy : Real = 0.02351283871158888;
                                attribute Ixz : Real = -0.0005460857876098469;
                                attribute sigma_Ixz : Real = 0.022566176940390956;
                                attribute Iyz : Real = 0.02553685611001834;
                                attribute sigma_Iyz : Real = 0.02209918015384651;
                            }
                            part <'C.1.2.3.3.5.3.4'> 'Part 1186' {
                                attribute POIconv : String = "-";
                                attribute Ipoint : Boolean = false;
                                attribute mass : Real = 0.1801613999251276;
                                attribute sigma_mass : Real = 0.28909372274994966;
                                attribute Cx : Real = -28.705476876348257;
                                attribute sigma_Cx : Real = 28.721044428837228;
                                attribute Cy : Real = -42.708477610722184;
                                attribute sigma_Cy : Real = 28.23690002309109;
                                attribute Cz : Real = -37.684210017323494;
                                attribute sigma_Cz : Real = 29.057750463592832;
                                attribute Ixx : Real = 0.21981736142253447;
                                attribute sigma_Ixx : Real = 0.37074144170588635;
                                attribute Iyy : Real = 0.23640503568982682;
                                attribute sigma_Iyy : Real = 0.3723953238821935;
                                attribute Izz : Real = 0.2554400982778067;
                                attribute sigma_Izz : Real = 0.37017423652493897;
                                attribute Ixy : Real = -0.015605806845966425;
                                attribute sigma_Ixy : Real = 0.02351283871158888;
                                attribute Ixz : Real = -0.003999732426555158;
                                attribute sigma_Ixz : Real = 0.022566176940390956;
                                attribute Iyz : Real = 0.0011313666577094069;
                                attribute sigma_Iyz : Real = 0.02209918015384651;
                            }
                            part <'C.1.2.3.3.5.3.5'> 'Part 1187' {
                                attribute POIconv : String = "+";
                                attribute Ipoint : Boolean = false;
                                attribute mass : Real = 0.7467175956284627;
                                attribute sigma_mass : Real = 0.28909372274994966;
                                attribute Cx : Real = 61.99311059899628;
                                attribute sigma_Cx : Real = 28.721044428837228;
                                attribute Cy : Real = 78.22457253932953;
                                attribute sigma_Cy : Real = 28.23690002309109;
                                attribute Cz : Real = -65.92343943193555;
                                attribute sigma_Cz : Real = 29.057750463592832;
                                attribute Ixx : Real = 1.084697980021411;
                                attribute sigma_Ixx : Real = 0.37074144170588635;
                                attribute Iyy : Real = 1.016389021325471;
                                attribute sigma_Iyy : Real = 0.3723953238821935;
                                attribute Izz : Real = 1.0090557503487099;
                                attribute sigma_Izz : Real = 0.37017423652493897;
                                attribute Ixy : Real = 0.02941254032184017;
                                attribute sigma_Ixy : Real = 0.02351283871158888;
                                attribute Ixz : Real = -0.019732036770829076;
                                attribute sigma_Ixz : Real = 0.022566176940390956;
                                attribute Iyz : Real = -0.05544881808075673;
                                attribute sigma_Iyz : Real = 0.02209918015384651;
                            }
                        }
                        part <'C.1.2.3.3.5.4'> 'Subassembly 336' {
                            attribute POIconv : String = "-";
                            attribute Ipoint : Boolean = false;
                            attribute mass : Real = 2.3863400056625252;
                            attribute sigma_mass : Real = 0.5781874454998993;
                            attribute Cx : Real = -0.6111678954339127;
                            attribute sigma_Cx : Real = 21.611810702559726;
                            attribute Cy : Real = 34.77601199585753;
                            attribute sigma_Cy : Real = 18.130395895443232;
                            attribute Cz : Real = 12.312873618363309;
                            attribute sigma_Cz : Real = 24.787239115198986;
                            attribute Ixx : Real = 16286.28451170403;
                            attribute sigma_Ixx : Real = 7677.499822166542;
                            attribute Iyy : Real = 18917.958383031084;
                            attribute sigma_Iyy : Real = 9201.471627351248;
                            attribute Izz : Real = 12730.126976607542;
                            attribute sigma_Izz : Real = 6341.179203019971;
                            attribute Ixy : Real = -5178.703037141316;
                            attribute sigma_Ixy : Real = 2958.002548509245;
                            attribute Ixz : Real = 5892.8356442339245;
                            attribute sigma_Ixz : Real = 4487.725135454944;
                            attribute Iyz : Real = 3782.913818412177;
                            attribute sigma_Iyz : Real = 3221.0312030222026;
                            part <'C.1.2.3.3.5.4.1'> 'Part 1188' {
                                attribute POIconv : String = "-";
                                attribute Ipoint : Boolean = false;
                                attribute mass : Real = 0.30652864956972187;
                                attribute sigma_mass : Real = 0.28909372274994966;
                                attribute Cx : Real = -50.09635570459068;
                                attribute sigma_Cx : Real = 28.721044428837228;
                                attribute Cy : Real = 22.151227155700326;
                                attribute sigma_Cy : Real = 28.23690002309109;
                                attribute Cz : Real = -69.80069228447974;
                                attribute sigma_Cz : Real = 29.057750463592832;
                                attribute Ixx : Real = 0.2673990657396424;
                                attribute sigma_Ixx : Real = 0.37074144170588635;
                                attribute Iyy : Real = 0.28143012705003834;
                                attribute sigma_Iyy : Real = 0.3723953238821935;
                                attribute Izz : Real = 0.2824010821572576;
                                attribute sigma_Izz : Real = 0.37017423652493897;
                                attribute Ixy : Real = 0.0021955986870638416;
                                attribute sigma_Ixy : Real = 0.02351283871158888;
                                attribute Ixz : Real = -0.0060248788326431055;
                                attribute sigma_Ixz : Real = 0.022566176940390956;
                                attribute Iyz : Real = 0.0021085429844813113;
                                attribute sigma_Iyz : Real = 0.02209918015384651;
                            }
                            part <'C.1.2.3.3.5.4.2'> 'Part 1189' {
                                attribute POIconv : String = "+";
                                attribute Ipoint : Boolean = false;
                                attribute mass : Real = 0.3564685169577133;
                                attribute sigma_mass : Real = 0.28909372274994966;
                                attribute Cx : Real = 87.0281957089901;
                                attribute sigma_Cx : Real = 28.721044428837228;
                                attribute Cy : Real = 51.38806686736643;
                                attribute sigma_Cy : Real = 28.23690002309109;
                                attribute Cz : Real = -99.0100737195462;
                                attribute sigma_Cz : Real = 29.057750463592832;
                                attribute Ixx : Real = 0.42564427308635416;
                                attribute sigma_Ixx : Real = 0.37074144170588635;
                                attribute Iyy : Real = 0.3901718824277889;
                                attribute sigma_Iyy : Real = 0.3723953238821935;
                                attribute Izz : Real = 0.3940133923018378;
                                attribute sigma_Izz : Real = 0.37017423652493897;
                                attribute Ixy : Real = -0.030680840415619727;
                                attribute sigma_Ixy : Real = 0.02351283871158888;
                                attribute Ixz : Real = 0.010308071453695848;
                                attribute sigma_Ixz : Real = 0.022566176940390956;
                                attribute Iyz : Real = 0.010548218201815469;
                                attribute sigma_Iyz : Real = 0.02209918015384651;
                            }
                            part <'C.1.2.3.3.5.4.3'> 'Part 1190' {
                                attribute POIconv : String = "-";
                                attribute Ipoint : Boolean = false;
                                attribute mass : Real = 0.8649283096198924;
                                attribute sigma_mass : Real = 0.28909372274994966;
                                attribute Cx : Real = -58.17913496866822;
                                attribute sigma_Cx : Real = 28.721044428837228;
                                attribute Cy : Real = -19.52681289985776;
                                attribute sigma_Cy : Real = 28.23690002309109;
                                attribute Cz : Real = 86.42389038577676;
                                attribute sigma_Cz : Real = 29.057750463592832;
                                attribute Ixx : Real = 0.9090796287805308;
                                attribute sigma_Ixx : Real = 0.37074144170588635;
                                attribute Iyy : Real = 0.971970392989424;
                                attribute sigma_Iyy : Real = 0.3723953238821935;
                                attribute Izz : Real = 0.9327991036545203;
                                attribute sigma_Izz : Real = 0.37017423652493897;
                                attribute Ixy : Real = -0.0333727449582402;
                                attribute sigma_Ixy : Real = 0.02351283871158888;
                                attribute Ixz : Real = 0.037570048234289735;
                                attribute sigma_Ixz : Real = 0.022566176940390956;
                                attribute Iyz : Real = 0.026644244251755662;
                                attribute sigma_Iyz : Real = 0.02209918015384651;
                            }
                            part <'C.1.2.3.3.5.4.4'> 'Part 1191' {
                                attribute POIconv : String = "+";
                                attribute Ipoint : Boolean = false;
                                attribute mass : Real = 0.8584145295151975;
                                attribute sigma_mass : Real = 0.28909372274994966;
                                attribute Cx : Real = 38.670690823346376;
                                attribute sigma_Cx : Real = 28.721044428837228;
                                attribute Cy : Real = 87.10065549239516;
                                attribute sigma_Cy : Real = 28.23690002309109;
                                attribute Cz : Real = 13.189571211114526;
                                attribute sigma_Cz : Real = 29.057750463592832;
                                attribute Ixx : Real = 1.0480924814204073;
                                attribute sigma_Ixx : Real = 0.37074144170588635;
                                attribute Iyy : Real = 1.0738066373458006;
                                attribute sigma_Iyy : Real = 0.3723953238821935;
                                attribute Izz : Real = 1.0088989081062059;
                                attribute sigma_Izz : Real = 0.37017423652493897;
                                attribute Ixy : Real = -0.018266017881797332;
                                attribute sigma_Ixy : Real = 0.02351283871158888;
                                attribute Ixz : Real = 0.024966079391719312;
                                attribute sigma_Ixz : Real = 0.022566176940390956;
                                attribute Iyz : Real = 0.026818487219560486;
                                attribute sigma_Iyz : Real = 0.02209918015384651;
                            }
                        }
                        part <'C.1.2.3.3.5.5'> 'Subassembly 337' {
                            attribute POIconv : String = "-";
                            attribute Ipoint : Boolean = false;
                            attribute mass : Real = 3.532857178029837;
                            attribute sigma_mass : Real = 0.6464332159373649;
                            attribute Cx : Real = 2.307378730997234;
                            attribute sigma_Cx : Real = 17.563683083286303;
                            attribute Cy : Real = 1.747165837339958;
                            attribute sigma_Cy : Real = 16.197237975316472;
                            attribute Cz : Real = -12.060232508944434;
                            attribute sigma_Cz : Real = 17.61673630137475;
                            attribute Ixx : Real = 22201.653717276662;
                            attribute sigma_Ixx : Real = 9192.466581721907;
                            attribute Iyy : Real = 26633.48645161378;
                            attribute sigma_Iyy : Real = 10232.136095156306;
                            attribute Izz : Real = 22331.00821536807;
                            attribute sigma_Izz : Real = 9042.84970897053;
                            attribute Ixy : Real = -6162.148372453927;
                            attribute sigma_Ixy : Real = 4427.660132956734;
                            attribute Ixz : Real = -8650.761594696098;
                            attribute sigma_Ixz : Real = 4969.156919030336;
                            attribute Iyz : Real = -9259.04555014673;
                            attribute sigma_Iyz : Real = 4517.569420066207;
                            part <'C.1.2.3.3.5.5.1'> 'Part 1192' {
                                attribute POIconv : String = "-";
                                attribute Ipoint : Boolean = false;
                                attribute mass : Real = 0.9428046576266642;
                                attribute sigma_mass : Real = 0.28909372274994966;
                                attribute Cx : Real = 42.17588757164776;
                                attribute sigma_Cx : Real = 28.721044428837228;
                                attribute Cy : Real = -39.76542754098773;
                                attribute sigma_Cy : Real = 28.23690002309109;
                                attribute Cz : Real = -48.03979825228453;
                                attribute sigma_Cz : Real = 29.057750463592832;
                                attribute Ixx : Real = 1.5016593240103169;
                                attribute sigma_Ixx : Real = 0.37074144170588635;
                                attribute Iyy : Real = 1.4856591940433062;
                                attribute sigma_Iyy : Real = 0.3723953238821935;
                                attribute Izz : Real = 1.4914883729948292;
                                attribute sigma_Izz : Real = 0.37017423652493897;
                                attribute Ixy : Real = -0.0029911272411354776;
                                attribute sigma_Ixy : Real = 0.02351283871158888;
                                attribute Ixz : Real = 0.0091901297588101;
                                attribute sigma_Ixz : Real = 0.022566176940390956;
                                attribute Iyz : Real = 0.00747554309784382;
                                attribute sigma_Iyz : Real = 0.02209918015384651;
                            }
                            part <'C.1.2.3.3.5.5.2'> 'Part 1193' {
                                attribute POIconv : String = "-";
                                attribute Ipoint : Boolean = false;
                                attribute mass : Real = 0.585549096090952;
                                attribute sigma_mass : Real = 0.28909372274994966;
                                attribute Cx : Real = -96.35233390145004;
                                attribute sigma_Cx : Real = 28.721044428837228;
                                attribute Cy : Real = -65.29715922661126;
                                attribute sigma_Cy : Real = 28.23690002309109;
                                attribute Cz : Real = -76.59457600675523;
                                attribute sigma_Cz : Real = 29.057750463592832;
                                attribute Ixx : Real = 0.6676553794336636;
                                attribute sigma_Ixx : Real = 0.37074144170588635;
                                attribute Iyy : Real = 0.6905996315274058;
                                attribute sigma_Iyy : Real = 0.3723953238821935;
                                attribute Izz : Real = 0.5542419726701172;
                                attribute sigma_Izz : Real = 0.37017423652493897;
                                attribute Ixy : Real = 0.004805677805926533;
                                attribute sigma_Ixy : Real = 0.02351283871158888;
                                attribute Ixz : Real = 0.011210819131525003;
                                attribute sigma_Ixz : Real = 0.022566176940390956;
                                attribute Iyz : Real = -0.012690994353789543;
                                attribute sigma_Iyz : Real = 0.02209918015384651;
                            }
                            part <'C.1.2.3.3.5.5.3'> 'Part 1194' {
                                attribute POIconv : String = "-";
                                attribute Ipoint : Boolean = false;
                                attribute mass : Real = 0.7877497131845448;
                                attribute sigma_mass : Real = 0.28909372274994966;
                                attribute Cx : Real = -47.519047698006034;
                                attribute sigma_Cx : Real = 28.721044428837228;
                                attribute Cy : Real = 7.04563488252461;
                                attribute sigma_Cy : Real = 28.23690002309109;
                                attribute Cz : Real = -14.089943142607808;
                                attribute sigma_Cz : Real = 29.057750463592832;
                                attribute Ixx : Real = 1.070217593462583;
                                attribute sigma_Ixx : Real = 0.37074144170588635;
                                attribute Iyy : Real = 1.1285310651563765;
                                attribute sigma_Iyy : Real = 0.3723953238821935;
                                attribute Izz : Real = 1.0565678866398924;
                                attribute sigma_Izz : Real = 0.37017423652493897;
                                attribute Ixy : Real = -0.08852486178805327;
                                attribute sigma_Ixy : Real = 0.02351283871158888;
                                attribute Ixz : Real = 0.046988081763396826;
                                attribute sigma_Ixz : Real = 0.022566176940390956;
                                attribute Iyz : Real = -0.03055792171898878;
                                attribute sigma_Iyz : Real = 0.02209918015384651;
                            }
                            part <'C.1.2.3.3.5.5.4'> 'Part 1195' {
                                attribute POIconv : String = "+";
                                attribute Ipoint : Boolean = false;
                                attribute mass : Real = 0.28552112196339297;
                                attribute sigma_mass : Real = 0.28909372274994966;
                                attribute Cx : Real = -8.38005430996418;
                                attribute sigma_Cx : Real = 28.721044428837228;
                                attribute Cy : Real = 43.30366440117359;
                                attribute sigma_Cy : Real = 28.23690002309109;
                                attribute Cz : Real = -69.53580663539469;
                                attribute sigma_Cz : Real = 29.057750463592832;
                                attribute Ixx : Real = 0.31747065019210713;
                                attribute sigma_Ixx : Real = 0.37074144170588635;
                                attribute Iyy : Real = 0.32630019347221356;
                                attribute sigma_Iyy : Real = 0.3723953238821935;
                                attribute Izz : Real = 0.2859609680657334;
                                attribute sigma_Izz : Real = 0.37017423652493897;
                                attribute Ixy : Real = -0.010608600942390902;
                                attribute sigma_Ixy : Real = 0.02351283871158888;
                                attribute Ixz : Real = 0.028667899001052006;
                                attribute sigma_Ixz : Real = 0.022566176940390956;
                                attribute Iyz : Real = -0.01877017513384474;
                                attribute sigma_Iyz : Real = 0.02209918015384651;
                            }
                            part <'C.1.2.3.3.5.5.5'> 'Part 1196' {
                                attribute POIconv : String = "-";
                                attribute Ipoint : Boolean = false;
                                attribute mass : Real = 0.9312325891642831;
                                attribute sigma_mass : Real = 0.28909372274994966;
                                attribute Cx : Real = 69.40568634308875;
                                attribute sigma_Cx : Real = 28.721044428837228;
                                attribute Cy : Real = 68.70883093215525;
                                attribute sigma_Cy : Real = 28.23690002309109;
                                attribute Cz : Real = 84.28425122983754;
                                attribute sigma_Cz : Real = 29.057750463592832;
                                attribute Ixx : Real = 1.1384510280928442;
                                attribute sigma_Ixx : Real = 0.37074144170588635;
                                attribute Iyy : Real = 1.266617248300143;
                                attribute sigma_Iyy : Real = 0.3723953238821935;
                                attribute Izz : Real = 1.0806625961862404;
                                attribute sigma_Izz : Real = 0.37017423652493897;
                                attribute Ixy : Real = -0.03547099763743248;
                                attribute sigma_Ixy : Real = 0.02351283871158888;
                                attribute Ixz : Real = 0.0028423682856433853;
                                attribute sigma_Ixz : Real = 0.022566176940390956;
                                attribute Iyz : Real = -0.07038055531427001;
                                attribute sigma_Iyz : Real = 0.02209918015384651;
                            }
                        }
                    }
                }
                part <'C.1.2.3.4'> 'Subsystem 26' {
                    attribute POIconv : String = "-";
                    attribute Ipoint : Boolean = false;
                    attribute mass : Real = 19.220285945237848;
                    attribute sigma_mass : Real = 1.7345623364996978;
                    attribute Cx : Real = -8.06254323343061;
                    attribute sigma_Cx : Real = 7.82781614409347;
                    attribute Cy : Real = -19.495682737700434;
                    attribute sigma_Cy : Real = 7.978531687525078;
                    attribute Cz : Real = -2.405793286531435;
                    attribute sigma_Cz : Real = 7.833441193586397;
                    attribute Ixx : Real = 124778.90880287146;
                    attribute sigma_Ixx : Real = 22934.030859265036;
                    attribute Iyy : Real = 113740.7597249113;
                    attribute sigma_Iyy : Real = 22357.29726250783;
                    attribute Izz : Real = 116015.30324120735;
                    attribute sigma_Izz : Real = 23289.629552003684;
                    attribute Ixy : Real = 1853.959321895718;
                    attribute sigma_Ixy : Real = 10741.205702109122;
                    attribute Ixz : Real = 3547.1534504171323;
                    attribute sigma_Ixz : Real = 10658.600545041925;
                    attribute Iyz : Real = 3801.9467838775963;
                    attribute sigma_Iyz : Real = 11109.274937157175;
                    part <'C.1.2.3.4.1'> 'Assembly 98' {
                        attribute POIconv : String = "-";
                        attribute Ipoint : Boolean = false;
                        attribute mass : Real = 9.332037358067929;
                        attribute sigma_mass : Real = 1.2265207905297184;
                        attribute Cx : Real = -2.195416458288913;
                        attribute sigma_Cx : Real = 11.053607888475488;
                        attribute Cy : Real = -33.592537096533206;
                        attribute sigma_Cy : Real = 11.309818804620395;
                        attribute Cz : Real = -12.171385301167343;
                        attribute sigma_Cz : Real = 11.801858446278215;
                        attribute Ixx : Real = 58021.53856455765;
                        attribute sigma_Ixx : Real = 16770.205343589732;
                        attribute Iyy : Real = 55549.447025677306;
                        attribute sigma_Iyy : Real = 16376.954278768757;
                        attribute Izz : Real = 50472.475092585315;
                        attribute sigma_Izz : Real = 15303.214689959257;
                        attribute Ixy : Real = -6675.970527695868;
                        attribute sigma_Ixy : Real = 7279.055654087476;
                        attribute Ixz : Real = -1464.0168874705469;
                        attribute sigma_Ixz : Real = 7896.029458149697;
                        attribute Iyz : Real = 2492.8065595221674;
                        attribute sigma_Iyz : Real = 8036.852884660343;
                        part <'C.1.2.3.4.1.1'> 'Subassembly 338' {
                            attribute POIconv : String = "-";
                            attribute Ipoint : Boolean = false;
                            attribute mass : Real = 1.862563399863895;
                            attribute sigma_mass : Real = 0.5007250159521434;
                            attribute Cx : Real = 11.308303730273606;
                            attribute sigma_Cx : Real = 26.600774819971814;
                            attribute Cy : Real = -54.14339072933332;
                            attribute sigma_Cy : Real = 25.81478691603238;
                            attribute Cz : Real = -51.39793284229541;
                            attribute sigma_Cz : Real = 22.03728090372452;
                            attribute Ixx : Real = 5714.985934875342;
                            attribute sigma_Ixx : Real = 5761.64400431326;
                            attribute Iyy : Real = 10261.189823317969;
                            attribute sigma_Iyy : Real = 6142.799281746899;
                            attribute Izz : Real = 11535.94229508743;
                            attribute sigma_Izz : Real = 7766.260388907695;
                            attribute Ixy : Real = -2583.4575448585338;
                            attribute sigma_Ixy : Real = 3682.659556531402;
                            attribute Ixz : Real = -4088.0634799195964;
                            attribute sigma_Ixz : Real = 2979.3967068967922;
                            attribute Iyz : Real = -1924.6360455544605;
                            attribute sigma_Iyz : Real = 2541.2408223858793;
                            part <'C.1.2.3.4.1.1.1'> 'Part 1197' {
                                attribute POIconv : String = "+";
                                attribute Ipoint : Boolean = false;
                                attribute mass : Real = 0.23018171754688957;
                                attribute sigma_mass : Real = 0.28909372274994966;
                                attribute Cx : Real = 95.5246795900166;
                                attribute sigma_Cx : Real = 28.721044428837228;
                                attribute Cy : Real = 61.187514662742615;
                                attribute sigma_Cy : Real = 28.23690002309109;
                                attribute Cz : Real = 11.674417508766055;
                                attribute sigma_Cz : Real = 29.057750463592832;
                                attribute Ixx : Real = 0.3069745118789222;
                                attribute sigma_Ixx : Real = 0.37074144170588635;
                                attribute Iyy : Real = 0.31744604207443594;
                                attribute sigma_Iyy : Real = 0.3723953238821935;
                                attribute Izz : Real = 0.2842426748752614;
                                attribute sigma_Izz : Real = 0.37017423652493897;
                                attribute Ixy : Real = -0.0017517065207401897;
                                attribute sigma_Ixy : Real = 0.02351283871158888;
                                attribute Ixz : Real = 5.268557993259696e-05;
                                attribute sigma_Ixz : Real = 0.022566176940390956;
                                attribute Iyz : Real = 0.002290491340160407;
                                attribute sigma_Iyz : Real = 0.02209918015384651;
                            }
                            part <'C.1.2.3.4.1.1.2'> 'Part 1198' {
                                attribute POIconv : String = "-";
                                attribute Ipoint : Boolean = false;
                                attribute mass : Real = 0.6359203600841574;
                                attribute sigma_mass : Real = 0.28909372274994966;
                                attribute Cx : Real = 76.43651869148016;
                                attribute sigma_Cx : Real = 28.721044428837228;
                                attribute Cy : Real = -70.00100016593933;
                                attribute sigma_Cy : Real = 28.23690002309109;
                                attribute Cz : Real = -26.721250219270587;
                                attribute sigma_Cz : Real = 29.057750463592832;
                                attribute Ixx : Real = 0.6089424688423378;
                                attribute sigma_Ixx : Real = 0.37074144170588635;
                                attribute Iyy : Real = 0.6029232542657164;
                                attribute sigma_Iyy : Real = 0.3723953238821935;
                                attribute Izz : Real = 0.6187962497176541;
                                attribute sigma_Izz : Real = 0.37017423652493897;
                                attribute Ixy : Real = 0.003989223897206991;
                                attribute sigma_Ixy : Real = 0.02351283871158888;
                                attribute Ixz : Real = 0.0054633789357295065;
                                attribute sigma_Ixz : Real = 0.022566176940390956;
                                attribute Iyz : Real = 0.014061730982386188;
                                attribute sigma_Iyz : Real = 0.02209918015384651;
                            }
                            part <'C.1.2.3.4.1.1.3'> 'Part 1199' {
                                attribute POIconv : String = "+";
                                attribute Ipoint : Boolean = false;
                                attribute mass : Real = 0.996461322232848;
                                attribute sigma_mass : Real = 0.28909372274994966;
                                attribute Cx : Real = -49.709044955670834;
                                attribute sigma_Cx : Real = 28.721044428837228;
                                attribute Cy : Real = -70.66474366001785;
                                attribute sigma_Cy : Real = 28.23690002309109;
                                attribute Cz : Real = -81.71572457067668;
                                attribute sigma_Cz : Real = 29.057750463592832;
                                attribute Ixx : Real = 1.6295741725204236;
                                attribute sigma_Ixx : Real = 0.37074144170588635;
                                attribute Iyy : Real = 1.5705576093834526;
                                attribute sigma_Iyy : Real = 0.3723953238821935;
                                attribute Izz : Real = 1.5862381149068372;
                                attribute sigma_Izz : Real = 0.37017423652493897;
                                attribute Ixy : Real = 0.008185031127095163;
                                attribute sigma_Ixy : Real = 0.02351283871158888;
                                attribute Ixz : Real = 0.02361246937058287;
                                attribute sigma_Ixz : Real = 0.022566176940390956;
                                attribute Iyz : Real = -0.012441359767488645;
                                attribute sigma_Iyz : Real = 0.02209918015384651;
                            }
                        }
                        part <'C.1.2.3.4.1.2'> 'Subassembly 339' {
                            attribute POIconv : String = "-";
                            attribute Ipoint : Boolean = false;
                            attribute mass : Real = 1.2223081288905815;
                            attribute sigma_mass : Real = 0.5007250159521434;
                            attribute Cx : Real = 38.85672052721935;
                            attribute sigma_Cx : Real = 20.70114639105002;
                            attribute Cy : Real = 5.38350685270701;
                            attribute sigma_Cy : Real = 31.9174811161835;
                            attribute Cz : Real = 38.65434004485102;
                            attribute sigma_Cz : Real = 32.03087068570242;
                            attribute Ixx : Real = 9552.066672148969;
                            attribute sigma_Ixx : Real = 6046.983532384434;
                            attribute Iyy : Real = 4724.00041301589;
                            attribute sigma_Iyy : Real = 4221.096123373816;
                            attribute Izz : Real = 6133.314088782636;
                            attribute sigma_Izz : Real = 3965.3924729923265;
                            attribute Ixy : Real = 660.1352966160993;
                            attribute sigma_Ixy : Real = 1728.8700953504976;
                            attribute Ixz : Real = -1258.1076735744473;
                            attribute sigma_Ixz : Real = 1740.7984185108314;
                            attribute Iyz : Real = 4085.3607835107728;
                            attribute sigma_Iyz : Real = 2866.648970391299;
                            part <'C.1.2.3.4.1.2.1'> 'Part 1200' {
                                attribute POIconv : String = "+";
                                attribute Ipoint : Boolean = false;
                                attribute mass : Real = 0.24791463754395954;
                                attribute sigma_mass : Real = 0.28909372274994966;
                                attribute Cx : Real = -6.434924015775323;
                                attribute sigma_Cx : Real = 28.721044428837228;
                                attribute Cy : Real = 69.44263693876565;
                                attribute sigma_Cy : Real = 28.23690002309109;
                                attribute Cz : Real = -59.38496878370643;
                                attribute sigma_Cz : Real = 29.057750463592832;
                                attribute Ixx : Real = 0.30408178827658733;
                                attribute sigma_Ixx : Real = 0.37074144170588635;
                                attribute Iyy : Real = 0.27296056539851027;
                                attribute sigma_Iyy : Real = 0.3723953238821935;
                                attribute Izz : Real = 0.305565162131866;
                                attribute sigma_Izz : Real = 0.37017423652493897;
                                attribute Ixy : Real = 0.026278982918982823;
                                attribute sigma_Ixy : Real = 0.02351283871158888;
                                attribute Ixz : Real = -0.008359360133204959;
                                attribute sigma_Ixz : Real = 0.022566176940390956;
                                attribute Iyz : Real = -0.004857278496176114;
                                attribute sigma_Iyz : Real = 0.02209918015384651;
                            }
                            part <'C.1.2.3.4.1.2.2'> 'Part 1201' {
                                attribute POIconv : String = "+";
                                attribute Ipoint : Boolean = false;
                                attribute mass : Real = 0.5133475823018234;
                                attribute sigma_mass : Real = 0.28909372274994966;
                                attribute Cx : Real = 46.79508386179805;
                                attribute sigma_Cx : Real = 28.721044428837228;
                                attribute Cy : Real = -73.16190833225846;
                                attribute sigma_Cy : Real = 28.23690002309109;
                                attribute Cz : Real = 95.17118851654232;
                                attribute sigma_Cz : Real = 29.057750463592832;
                                attribute Ixx : Real = 0.715867958016512;
                                attribute sigma_Ixx : Real = 0.37074144170588635;
                                attribute Iyy : Real = 0.7125286319649866;
                                attribute sigma_Iyy : Real = 0.3723953238821935;
                                attribute Izz : Real = 0.6832705343005893;
                                attribute sigma_Izz : Real = 0.37017423652493897;
                                attribute Ixy : Real = 0.017785012597743538;
                                attribute sigma_Ixy : Real = 0.02351283871158888;
                                attribute Ixz : Real = 0.009670737119423515;
                                attribute sigma_Ixz : Real = 0.022566176940390956;
                                attribute Iyz : Real = -0.013902577959321566;
                                attribute sigma_Iyz : Real = 0.02209918015384651;
                            }
                            part <'C.1.2.3.4.1.2.3'> 'Part 1202' {
                                attribute POIconv : String = "+";
                                attribute Ipoint : Boolean = false;
                                attribute mass : Real = 0.4610459090447985;
                                attribute sigma_mass : Real = 0.28909372274994966;
                                attribute Cx : Real = 54.372142907232046;
                                attribute sigma_Cx : Real = 28.721044428837228;
                                attribute Cy : Real = 58.3932017441839;
                                attribute sigma_Cy : Real = 28.23690002309109;
                                attribute Cz : Real = 28.444060077890754;
                                attribute sigma_Cz : Real = 29.057750463592832;
                                attribute Ixx : Real = 0.4639649931737143;
                                attribute sigma_Ixx : Real = 0.37074144170588635;
                                attribute Iyy : Real = 0.4647832601030392;
                                attribute sigma_Iyy : Real = 0.3723953238821935;
                                attribute Izz : Real = 0.5081465023688937;
                                attribute sigma_Izz : Real = 0.37017423652493897;
                                attribute Ixy : Real = -0.005759403203507457;
                                attribute sigma_Ixy : Real = 0.02351283871158888;
                                attribute Ixz : Real = -0.0008844889951697874;
                                attribute sigma_Ixz : Real = 0.022566176940390956;
                                attribute Iyz : Real = -0.0008495170848509825;
                                attribute sigma_Iyz : Real = 0.02209918015384651;
                            }
                        }
                        part <'C.1.2.3.4.1.3'> 'Subassembly 340' {
                            attribute POIconv : String = "-";
                            attribute Ipoint : Boolean = false;
                            attribute mass : Real = 0.8071248161033727;
                            attribute sigma_mass : Real = 0.5007250159521434;
                            attribute Cx : Real = -15.75088532512785;
                            attribute sigma_Cx : Real = 44.511394288223315;
                            attribute Cy : Real = -77.98181025355821;
                            attribute sigma_Cy : Real = 41.55296570248543;
                            attribute Cz : Real = -25.81363264906389;
                            attribute sigma_Cz : Real = 35.5637384096611;
                            attribute Ixx : Real = 868.1220955734846;
                            attribute sigma_Ixx : Real = 4499.4701867795175;
                            attribute Iyy : Real = 1145.726808159069;
                            attribute sigma_Iyy : Real = 4879.199706470025;
                            attribute Izz : Real = 1359.4658509527144;
                            attribute sigma_Izz : Real = 5899.986052574611;
                            attribute Ixy : Real = -475.4236798452745;
                            attribute sigma_Ixy : Real = 2943.6903996615692;
                            attribute Ixz : Real = -457.352443198893;
                            attribute sigma_Ixz : Real = 2339.6591818388333;
                            attribute Iyz : Real = -402.73174473740715;
                            attribute sigma_Iyz : Real = 2190.1113281046123;
                            part <'C.1.2.3.4.1.3.1'> 'Part 1203' {
                                attribute POIconv : String = "+";
                                attribute Ipoint : Boolean = false;
                                attribute mass : Real = 0.1624557269010693;
                                attribute sigma_mass : Real = 0.28909372274994966;
                                attribute Cx : Real = 11.05682710185647;
                                attribute sigma_Cx : Real = 28.721044428837228;
                                attribute Cy : Real = -95.06013114005327;
                                attribute sigma_Cy : Real = 28.23690002309109;
                                attribute Cz : Real = -27.754372963681817;
                                attribute sigma_Cz : Real = 29.057750463592832;
                                attribute Ixx : Real = 0.21477369924159126;
                                attribute sigma_Ixx : Real = 0.37074144170588635;
                                attribute Iyy : Real = 0.22027546416693852;
                                attribute sigma_Iyy : Real = 0.3723953238821935;
                                attribute Izz : Real = 0.19791697571173067;
                                attribute sigma_Izz : Real = 0.37017423652493897;
                                attribute Ixy : Real = -0.00016067511720010313;
                                attribute sigma_Ixy : Real = 0.02351283871158888;
                                attribute Ixz : Real = -0.010071054849285995;
                                attribute sigma_Ixz : Real = 0.022566176940390956;
                                attribute Iyz : Real = -0.0006930712087562078;
                                attribute sigma_Iyz : Real = 0.02209918015384651;
                            }
                            part <'C.1.2.3.4.1.3.2'> 'Part 1204' {
                                attribute POIconv : String = "+";
                                attribute Ipoint : Boolean = false;
                                attribute mass : Real = 0.05097084034536965;
                                attribute sigma_mass : Real = 0.28909372274994966;
                                attribute Cx : Real = 87.67452016472816;
                                attribute sigma_Cx : Real = 28.721044428837228;
                                attribute Cy : Real = 19.559049466624856;
                                attribute sigma_Cy : Real = 28.23690002309109;
                                attribute Cz : Real = 51.411914359778166;
                                attribute sigma_Cz : Real = 29.057750463592832;
                                attribute Ixx : Real = 0.05850068915165696;
                                attribute sigma_Ixx : Real = 0.37074144170588635;
                                attribute Iyy : Real = 0.0473749776713285;
                                attribute sigma_Iyy : Real = 0.3723953238821935;
                                attribute Izz : Real = 0.058831512975141484;
                                attribute sigma_Izz : Real = 0.37017423652493897;
                                attribute Ixy : Real = 0.0015162668333161418;
                                attribute sigma_Ixy : Real = 0.02351283871158888;
                                attribute Ixz : Real = -0.0004681152694180767;
                                attribute sigma_Ixz : Real = 0.022566176940390956;
                                attribute Iyz : Real = 0.0036207800377799073;
                                attribute sigma_Iyz : Real = 0.02209918015384651;
                            }
                            part <'C.1.2.3.4.1.3.3'> 'Part 1205' {
                                attribute POIconv : String = "+";
                                attribute Ipoint : Boolean = false;
                                attribute mass : Real = 0.5936982488569338;
                                attribute sigma_mass : Real = 0.28909372274994966;
                                attribute Cx : Real = -31.96576596237719;
                                attribute sigma_Cx : Real = 28.721044428837228;
                                attribute Cy : Real = -81.68279565870762;
                                attribute sigma_Cy : Real = 28.23690002309109;
                                attribute Cz : Real = -31.912634382024407;
                                attribute sigma_Cz : Real = 29.057750463592832;
                                attribute Ixx : Real = 0.7103963088838084;
                                attribute sigma_Ixx : Real = 0.37074144170588635;
                                attribute Iyy : Real = 0.7123187970002711;
                                attribute sigma_Iyy : Real = 0.3723953238821935;
                                attribute Izz : Real = 0.6744500804816671;
                                attribute sigma_Izz : Real = 0.37017423652493897;
                                attribute Ixy : Real = -0.03308433945396749;
                                attribute sigma_Ixy : Real = 0.02351283871158888;
                                attribute Ixz : Real = -0.006865272574987081;
                                attribute sigma_Ixz : Real = 0.022566176940390956;
                                attribute Iyz : Real = -0.002164742475760066;
                                attribute sigma_Iyz : Real = 0.02209918015384651;
                            }
                        }
                        part <'C.1.2.3.4.1.4'> 'Subassembly 341' {
                            attribute POIconv : String = "-";
                            attribute Ipoint : Boolean = false;
                            attribute mass : Real = 2.4507236979817972;
                            attribute sigma_mass : Real = 0.6464332159373649;
                            attribute Cx : Real = 28.110350754680297;
                            attribute sigma_Cx : Real = 20.64885451686135;
                            attribute Cy : Real = 1.5961808875890524;
                            attribute sigma_Cy : Real = 19.53626827326276;
                            attribute Cz : Real = -35.66656183022059;
                            attribute sigma_Cz : Real = 25.268317310376077;
                            attribute Ixx : Real = 14777.183493957367;
                            attribute sigma_Ixx : Real = 8681.249448821543;
                            attribute Iyy : Real = 12061.34131527716;
                            attribute sigma_Iyy : Real = 9103.924413059083;
                            attribute Izz : Real = 7908.7474618333345;
                            attribute sigma_Izz : Real = 5770.6231350298785;
                            attribute Ixy : Real = 2221.1756249842515;
                            attribute sigma_Ixy : Real = 2205.15532467763;
                            attribute Ixz : Real = -976.052527647495;
                            attribute sigma_Ixz : Real = 4196.512863098072;
                            attribute Iyz : Real = 3615.0648197996957;
                            attribute sigma_Iyz : Real = 3973.556087559801;
                            part <'C.1.2.3.4.1.4.1'> 'Part 1206' {
                                attribute POIconv : String = "-";
                                attribute Ipoint : Boolean = false;
                                attribute mass : Real = 0.31053965022508057;
                                attribute sigma_mass : Real = 0.28909372274994966;
                                attribute Cx : Real = 82.16296834871173;
                                attribute sigma_Cx : Real = 28.721044428837228;
                                attribute Cy : Real = -86.53600011020899;
                                attribute sigma_Cy : Real = 28.23690002309109;
                                attribute Cz : Real = 83.69044973514974;
                                attribute sigma_Cz : Real = 29.057750463592832;
                                attribute Ixx : Real = 0.4079048880869448;
                                attribute sigma_Ixx : Real = 0.37074144170588635;
                                attribute Iyy : Real = 0.4047036148068717;
                                attribute sigma_Iyy : Real = 0.3723953238821935;
                                attribute Izz : Real = 0.3969730315135618;
                                attribute sigma_Izz : Real = 0.37017423652493897;
                                attribute Ixy : Real = -0.010514561044438549;
                                attribute sigma_Ixy : Real = 0.02351283871158888;
                                attribute Ixz : Real = -0.014689737737081814;
                                attribute sigma_Ixz : Real = 0.022566176940390956;
                                attribute Iyz : Real = -0.018116262146247918;
                                attribute sigma_Iyz : Real = 0.02209918015384651;
                            }
                            part <'C.1.2.3.4.1.4.2'> 'Part 1207' {
                                attribute POIconv : String = "-";
                                attribute Ipoint : Boolean = false;
                                attribute mass : Real = 0.49811331197991965;
                                attribute sigma_mass : Real = 0.28909372274994966;
                                attribute Cx : Real = 20.360221806913614;
                                attribute sigma_Cx : Real = 28.721044428837228;
                                attribute Cy : Real = 48.02275183610618;
                                attribute sigma_Cy : Real = 28.23690002309109;
                                attribute Cz : Real = 1.006604265421629;
                                attribute sigma_Cz : Real = 29.057750463592832;
                                attribute Ixx : Real = 0.5984804433932001;
                                attribute sigma_Ixx : Real = 0.37074144170588635;
                                attribute Iyy : Real = 0.5752190953439233;
                                attribute sigma_Iyy : Real = 0.3723953238821935;
                                attribute Izz : Real = 0.6300229557218794;
                                attribute sigma_Izz : Real = 0.37017423652493897;
                                attribute Ixy : Real = -0.04374052153113046;
                                attribute sigma_Ixy : Real = 0.02351283871158888;
                                attribute Ixz : Real = 0.009637759466288764;
                                attribute sigma_Ixz : Real = 0.022566176940390956;
                                attribute Iyz : Real = -0.02597242703731132;
                                attribute sigma_Iyz : Real = 0.02209918015384651;
                            }
                            part <'C.1.2.3.4.1.4.3'> 'Part 1208' {
                                attribute POIconv : String = "-";
                                attribute Ipoint : Boolean = false;
                                attribute mass : Real = 0.11268071484123357;
                                attribute sigma_mass : Real = 0.28909372274994966;
                                attribute Cx : Real = -81.21525156311691;
                                attribute sigma_Cx : Real = 28.721044428837228;
                                attribute Cy : Real = -13.229603786021471;
                                attribute sigma_Cy : Real = 28.23690002309109;
                                attribute Cz : Real = 64.56721709109843;
                                attribute sigma_Cz : Real = 29.057750463592832;
                                attribute Ixx : Real = 0.1564561731672315;
                                attribute sigma_Ixx : Real = 0.37074144170588635;
                                attribute Iyy : Real = 0.12706718029504815;
                                attribute sigma_Iyy : Real = 0.3723953238821935;
                                attribute Izz : Real = 0.12985450859143252;
                                attribute sigma_Izz : Real = 0.37017423652493897;
                                attribute Ixy : Real = 0.005109733356001928;
                                attribute sigma_Ixy : Real = 0.02351283871158888;
                                attribute Ixz : Real = -0.001743523363976774;
                                attribute sigma_Ixz : Real = 0.022566176940390956;
                                attribute Iyz : Real = 0.0005201249573662269;
                                attribute sigma_Iyz : Real = 0.02209918015384651;
                            }
                            part <'C.1.2.3.4.1.4.4'> 'Part 1209' {
                                attribute POIconv : String = "-";
                                attribute Ipoint : Boolean = false;
                                attribute mass : Real = 0.6608180928584189;
                                attribute sigma_mass : Real = 0.28909372274994966;
                                attribute Cx : Real = 11.376993404701352;
                                attribute sigma_Cx : Real = 28.721044428837228;
                                attribute Cy : Real = 44.547165324911475;
                                attribute sigma_Cy : Real = 28.23690002309109;
                                attribute Cz : Real = -96.19570393115282;
                                attribute sigma_Cz : Real = 29.057750463592832;
                                attribute Ixx : Real = 0.667427557780151;
                                attribute sigma_Ixx : Real = 0.37074144170588635;
                                attribute Iyy : Real = 0.8490477648961487;
                                attribute sigma_Iyy : Real = 0.3723953238821935;
                                attribute Izz : Real = 0.8200092016943944;
                                attribute sigma_Izz : Real = 0.37017423652493897;
                                attribute Ixy : Real = -0.03128442379208227;
                                attribute sigma_Ixy : Real = 0.02351283871158888;
                                attribute Ixz : Real = -0.03570983146907562;
                                attribute sigma_Ixz : Real = 0.022566176940390956;
                                attribute Iyz : Real = -0.008300927296662545;
                                attribute sigma_Iyz : Real = 0.02209918015384651;
                            }
                            part <'C.1.2.3.4.1.4.5'> 'Part 1210' {
                                attribute POIconv : String = "-";
                                attribute Ipoint : Boolean = false;
                                attribute mass : Real = 0.8685719280771446;
                                attribute sigma_mass : Real = 0.28909372274994966;
                                attribute Cx : Real = 40.143382688984275;
                                attribute sigma_Cx : Real = 28.721044428837228;
                                attribute Cy : Real = -24.273137748241425;
                                attribute sigma_Cy : Real = 28.23690002309109;
                                attribute Cz : Real = -66.32394045591354;
                                attribute sigma_Cz : Real = 29.057750463592832;
                                attribute Ixx : Real = 1.1325989543113293;
                                attribute sigma_Ixx : Real = 0.37074144170588635;
                                attribute Iyy : Real = 1.1793036439015683;
                                attribute sigma_Iyy : Real = 0.3723953238821935;
                                attribute Izz : Real = 1.1874154851252992;
                                attribute sigma_Izz : Real = 0.37017423652493897;
                                attribute Ixy : Real = 0.01116998637174376;
                                attribute sigma_Ixy : Real = 0.02351283871158888;
                                attribute Ixz : Real = 0.007753968223140213;
                                attribute sigma_Ixz : Real = 0.022566176940390956;
                                attribute Iyz : Real = -0.00021081693427738328;
                                attribute sigma_Iyz : Real = 0.02209918015384651;
                            }
                        }
                        part <'C.1.2.3.4.1.5'> 'Subassembly 342' {
                            attribute POIconv : String = "-";
                            attribute Ipoint : Boolean = false;
                            attribute mass : Real = 2.9893173152282833;
                            attribute sigma_mass : Real = 0.5781874454998993;
                            attribute Cx : Real = -48.58058995678994;
                            attribute sigma_Cx : Real = 15.243926010615889;
                            attribute Cy : Real = -53.58827604525543;
                            attribute sigma_Cy : Real = 15.891035779776374;
                            attribute Cz : Real = 14.432821749959597;
                            attribute sigma_Cz : Real = 17.401800159804356;
                            attribute Ixx : Real = 9003.159640994614;
                            attribute sigma_Ixx : Real = 5275.967940880682;
                            attribute Iyy : Real = 6484.338905706003;
                            attribute sigma_Iyy : Real = 4438.244536802102;
                            attribute Izz : Real = 3840.8588575397307;
                            attribute sigma_Izz : Real = 3282.255110338725;
                            attribute Ixy : Real = 812.2419693279553;
                            attribute sigma_Ixy : Real = 1638.073739057574;
                            attribute Ixz : Real = 1594.611032918313;
                            attribute sigma_Ixz : Real = 2126.7526945624486;
                            attribute Iyz : Real = -2085.0235161863047;
                            attribute sigma_Iyz : Real = 2579.863992985912;
                            part <'C.1.2.3.4.1.5.1'> 'Part 1211' {
                                attribute POIconv : String = "-";
                                attribute Ipoint : Boolean = false;
                                attribute mass : Real = 0.9253771292541642;
                                attribute sigma_mass : Real = 0.28909372274994966;
                                attribute Cx : Real = -28.540639532729983;
                                attribute sigma_Cx : Real = 28.721044428837228;
                                attribute Cy : Real = -95.02116250805557;
                                attribute sigma_Cy : Real = 28.23690002309109;
                                attribute Cz : Real = -38.96304341033101;
                                attribute sigma_Cz : Real = 29.057750463592832;
                                attribute Ixx : Real = 1.0252569865246104;
                                attribute sigma_Ixx : Real = 0.37074144170588635;
                                attribute Iyy : Real = 0.9229744478406416;
                                attribute sigma_Iyy : Real = 0.3723953238821935;
                                attribute Izz : Real = 1.045445330723407;
                                attribute sigma_Izz : Real = 0.37017423652493897;
                                attribute Ixy : Real = 0.02305420714401632;
                                attribute sigma_Ixy : Real = 0.02351283871158888;
                                attribute Ixz : Real = 0.004392272488573504;
                                attribute sigma_Ixz : Real = 0.022566176940390956;
                                attribute Iyz : Real = -0.05310164370673251;
                                attribute sigma_Iyz : Real = 0.02209918015384651;
                            }
                            part <'C.1.2.3.4.1.5.2'> 'Part 1212' {
                                attribute POIconv : String = "+";
                                attribute Ipoint : Boolean = false;
                                attribute mass : Real = 0.45486251785163767;
                                attribute sigma_mass : Real = 0.28909372274994966;
                                attribute Cx : Real = -71.5090564917773;
                                attribute sigma_Cx : Real = 28.721044428837228;
                                attribute Cy : Real = -73.38967970572412;
                                attribute sigma_Cy : Real = 28.23690002309109;
                                attribute Cz : Real = 70.67902246490121;
                                attribute sigma_Cz : Real = 29.057750463592832;
                                attribute Ixx : Real = 0.5514238221369002;
                                attribute sigma_Ixx : Real = 0.37074144170588635;
                                attribute Iyy : Real = 0.5024478682098392;
                                attribute sigma_Iyy : Real = 0.3723953238821935;
                                attribute Izz : Real = 0.5572153127795414;
                                attribute sigma_Izz : Real = 0.37017423652493897;
                                attribute Ixy : Real = -0.05230570696090774;
                                attribute sigma_Ixy : Real = 0.02351283871158888;
                                attribute Ixz : Real = -0.04305566859936216;
                                attribute sigma_Ixz : Real = 0.022566176940390956;
                                attribute Iyz : Real = 0.058557911928675585;
                                attribute sigma_Iyz : Real = 0.02209918015384651;
                            }
                            part <'C.1.2.3.4.1.5.3'> 'Part 1213' {
                                attribute POIconv : String = "+";
                                attribute Ipoint : Boolean = false;
                                attribute mass : Real = 0.9754483755626716;
                                attribute sigma_mass : Real = 0.28909372274994966;
                                attribute Cx : Real = -51.88042349182069;
                                attribute sigma_Cx : Real = 28.721044428837228;
                                attribute Cy : Real = -26.834622118622065;
                                attribute sigma_Cy : Real = 28.23690002309109;
                                attribute Cz : Real = 52.94147925451398;
                                attribute sigma_Cz : Real = 29.057750463592832;
                                attribute Ixx : Real = 1.1983844929711078;
                                attribute sigma_Ixx : Real = 0.37074144170588635;
                                attribute Iyy : Real = 1.1612650039841859;
                                attribute sigma_Iyy : Real = 0.3723953238821935;
                                attribute Izz : Real = 1.3067747228430784;
                                attribute sigma_Izz : Real = 0.37017423652493897;
                                attribute Ixy : Real = 0.0022367138590890334;
                                attribute sigma_Ixy : Real = 0.02351283871158888;
                                attribute Ixz : Real = 0.06018785323751287;
                                attribute sigma_Ixz : Real = 0.022566176940390956;
                                attribute Iyz : Real = -0.014070412968562263;
                                attribute sigma_Iyz : Real = 0.02209918015384651;
                            }
                            part <'C.1.2.3.4.1.5.4'> 'Part 1214' {
                                attribute POIconv : String = "+";
                                attribute Ipoint : Boolean = false;
                                attribute mass : Real = 0.6336292925598099;
                                attribute sigma_mass : Real = 0.28909372274994966;
                                attribute Cx : Real = -56.30812807939947;
                                attribute sigma_Cx : Real = 28.721044428837228;
                                attribute Cy : Real = -20.049495808780193;
                                attribute sigma_Cy : Real = 28.23690002309109;
                                attribute Cz : Real = -7.245758501812816;
                                attribute sigma_Cz : Real = 29.057750463592832;
                                attribute Ixx : Real = 0.8636118697043312;
                                attribute sigma_Ixx : Real = 0.37074144170588635;
                                attribute Iyy : Real = 0.8661840310807734;
                                attribute sigma_Iyy : Real = 0.3723953238821935;
                                attribute Izz : Real = 0.8793129906532933;
                                attribute sigma_Izz : Real = 0.37017423652493897;
                                attribute Ixy : Real = 0.003248584527473052;
                                attribute sigma_Ixy : Real = 0.02351283871158888;
                                attribute Ixz : Real = -0.009569388216360506;
                                attribute sigma_Ixz : Real = 0.022566176940390956;
                                attribute Iyz : Real = 0.019240501890227;
                                attribute sigma_Iyz : Real = 0.02209918015384651;
                            }
                        }
                    }
                    part <'C.1.2.3.4.2'> 'Assembly 99' {
                        attribute POIconv : String = "-";
                        attribute Ipoint : Boolean = false;
                        attribute mass : Real = 5.164257677931571;
                        attribute sigma_mass : Real = 0.958815407608614;
                        attribute Cx : Real = -5.834941897852287;
                        attribute sigma_Cx : Real = 15.675335769646052;
                        attribute Cy : Real = -15.867963452414607;
                        attribute sigma_Cy : Real = 15.052335543302767;
                        attribute Cz : Real = 18.155881957492923;
                        attribute sigma_Cz : Real = 13.415566365385375;
                        attribute Ixx : Real = 19827.080211716493;
                        attribute sigma_Ixx : Real = 8503.614656462307;
                        attribute Iyy : Real = 19002.956321126003;
                        attribute sigma_Iyy : Real = 9282.494532887546;
                        attribute Izz : Real = 17473.672691650736;
                        attribute sigma_Izz : Real = 11070.332395994224;
                        attribute Ixy : Real = -1330.5602811493566;
                        attribute sigma_Ixy : Real = 4748.356887409877;
                        attribute Ixz : Real = 1987.9532376015266;
                        attribute sigma_Ixz : Real = 3889.7279654495464;
                        attribute Iyz : Real = -2322.06477677574;
                        attribute sigma_Iyz : Real = 3809.501689674625;
                        part <'C.1.2.3.4.2.1'> 'Subassembly 343' {
                            attribute POIconv : String = "-";
                            attribute Ipoint : Boolean = false;
                            attribute mass : Real = 2.4094469474058133;
                            attribute sigma_mass : Real = 0.5781874454998993;
                            attribute Cx : Real = 19.584921165985477;
                            attribute sigma_Cx : Real = 18.24159088705449;
                            attribute Cy : Real = -13.510238159551383;
                            attribute sigma_Cy : Real = 21.6569867964939;
                            attribute Cz : Real = 13.284000597829282;
                            attribute sigma_Cz : Real = 18.886348403330118;
                            attribute Ixx : Real = 8066.908493850824;
                            attribute sigma_Ixx : Real = 5606.803879895767;
                            attribute Iyy : Real = 5111.709488629322;
                            attribute sigma_Iyy : Real = 3818.3866243020293;
                            attribute Izz : Real = 5461.410483792623;
                            attribute sigma_Izz : Real = 5286.015421898027;
                            attribute Ixy : Real = 2109.561443506857;
                            attribute sigma_Ixy : Real = 2429.261011266988;
                            attribute Ixz : Real = 1365.3583441340265;
                            attribute sigma_Ixz : Real = 1678.046173342884;
                            attribute Iyz : Real = -3333.909019786802;
                            attribute sigma_Iyz : Real = 2349.9045205303332;
                            part <'C.1.2.3.4.2.1.1'> 'Part 1215' {
                                attribute POIconv : String = "-";
                                attribute Ipoint : Boolean = false;
                                attribute mass : Real = 0.14018993839807808;
                                attribute sigma_mass : Real = 0.28909372274994966;
                                attribute Cx : Real = -45.284552266821265;
                                attribute sigma_Cx : Real = 28.721044428837228;
                                attribute Cy : Real = 89.37675203196704;
                                attribute sigma_Cy : Real = 28.23690002309109;
                                attribute Cz : Real = 24.78629555553198;
                                attribute sigma_Cz : Real = 29.057750463592832;
                                attribute Ixx : Real = 0.1744797053004497;
                                attribute sigma_Ixx : Real = 0.37074144170588635;
                                attribute Iyy : Real = 0.17509864320516141;
                                attribute sigma_Iyy : Real = 0.3723953238821935;
                                attribute Izz : Real = 0.1784922198168826;
                                attribute sigma_Izz : Real = 0.37017423652493897;
                                attribute Ixy : Real = 0.0002647897538149731;
                                attribute sigma_Ixy : Real = 0.02351283871158888;
                                attribute Ixz : Real = -0.002589744232280417;
                                attribute sigma_Ixz : Real = 0.022566176940390956;
                                attribute Iyz : Real = 0.0008030236557246436;
                                attribute sigma_Iyz : Real = 0.02209918015384651;
                            }
                            part <'C.1.2.3.4.2.1.2'> 'Part 1216' {
                                attribute POIconv : String = "+";
                                attribute Ipoint : Boolean = false;
                                attribute mass : Real = 0.7928675107622984;
                                attribute sigma_mass : Real = 0.28909372274994966;
                                attribute Cx : Real = 4.040313791483641;
                                attribute sigma_Cx : Real = 28.721044428837228;
                                attribute Cy : Real = 3.4724437166005373;
                                attribute sigma_Cy : Real = 28.23690002309109;
                                attribute Cz : Real = 35.18093270249665;
                                attribute sigma_Cz : Real = 29.057750463592832;
                                attribute Ixx : Real = 0.9577415870941725;
                                attribute sigma_Ixx : Real = 0.37074144170588635;
                                attribute Iyy : Real = 1.0402156415950787;
                                attribute sigma_Iyy : Real = 0.3723953238821935;
                                attribute Izz : Real = 0.9765896306246936;
                                attribute sigma_Izz : Real = 0.37017423652493897;
                                attribute Ixy : Real = -0.04703818005083778;
                                attribute sigma_Ixy : Real = 0.02351283871158888;
                                attribute Ixz : Real = -0.006281842424107953;
                                attribute sigma_Ixz : Real = 0.022566176940390956;
                                attribute Iyz : Real = -0.024303674803286247;
                                attribute sigma_Iyz : Real = 0.02209918015384651;
                            }
                            part <'C.1.2.3.4.2.1.3'> 'Part 1217' {
                                attribute POIconv : String = "+";
                                attribute Ipoint : Boolean = false;
                                attribute mass : Real = 0.9245441264738329;
                                attribute sigma_mass : Real = 0.28909372274994966;
                                attribute Cx : Real = 26.067066425457597;
                                attribute sigma_Cx : Real = 28.721044428837228;
                                attribute Cy : Real = -4.1976196225732565;
                                attribute sigma_Cy : Real = 28.23690002309109;
                                attribute Cz : Real = 36.482014786452055;
                                attribute sigma_Cz : Real = 29.057750463592832;
                                attribute Ixx : Real = 1.0852840923621443;
                                attribute sigma_Ixx : Real = 0.37074144170588635;
                                attribute Iyy : Real = 1.2421879160354485;
                                attribute sigma_Iyy : Real = 0.3723953238821935;
                                attribute Izz : Real = 1.0625009303747057;
                                attribute sigma_Izz : Real = 0.37017423652493897;
                                attribute Ixy : Real = -0.09720429671983283;
                                attribute sigma_Ixy : Real = 0.02351283871158888;
                                attribute Ixz : Real = 0.005432631705803893;
                                attribute sigma_Ixz : Real = 0.022566176940390956;
                                attribute Iyz : Real = 0.011272388517156107;
                                attribute sigma_Iyz : Real = 0.02209918015384651;
                            }
                            part <'C.1.2.3.4.2.1.4'> 'Part 1218' {
                                attribute POIconv : String = "-";
                                attribute Ipoint : Boolean = false;
                                attribute mass : Real = 0.5518453717716039;
                                attribute sigma_mass : Real = 0.28909372274994966;
                                attribute Cx : Real = 47.53809990361333;
                                attribute sigma_Cx : Real = 28.721044428837228;
                                attribute Cy : Real = -79.64953398332;
                                attribute sigma_Cy : Real = 28.23690002309109;
                                attribute Cz : Real = -59.963800152763724;
                                attribute sigma_Cz : Real = 29.057750463592832;
                                attribute Ixx : Real = 0.7960976542480551;
                                attribute sigma_Ixx : Real = 0.37074144170588635;
                                attribute Iyy : Real = 0.6601283153450173;
                                attribute sigma_Iyy : Real = 0.3723953238821935;
                                attribute Izz : Real = 0.771462029499174;
                                attribute sigma_Izz : Real = 0.37017423652493897;
                                attribute Ixy : Real = 0.0064732761073713315;
                                attribute sigma_Ixy : Real = 0.02351283871158888;
                                attribute Ixz : Real = 0.0001370927398551994;
                                attribute sigma_Ixz : Real = 0.022566176940390956;
                                attribute Iyz : Real = 0.0056868588587633915;
                                attribute sigma_Iyz : Real = 0.02209918015384651;
                            }
                        }
                        part <'C.1.2.3.4.2.2'> 'Subassembly 344' {
                            attribute POIconv : String = "-";
                            attribute Ipoint : Boolean = false;
                            attribute mass : Real = 1.4983116182899103;
                            attribute sigma_mass : Real = 0.6464332159373649;
                            attribute Cx : Real = -27.436888064139854;
                            attribute sigma_Cx : Real = 38.83537291654996;
                            attribute Cy : Real = -10.995690348724423;
                            attribute sigma_Cy : Real = 33.1108367104503;
                            attribute Cz : Real = -22.576820232487265;
                            attribute sigma_Cz : Real = 17.86276757109216;
                            attribute Ixx : Real = 4042.2771617094504;
                            attribute sigma_Ixx : Real = 4527.751027780985;
                            attribute Iyy : Real = 4130.312084451443;
                            attribute sigma_Iyy : Real = 6243.349154929699;
                            attribute Izz : Real = 8117.247975549872;
                            attribute sigma_Izz : Real = 8901.551348256706;
                            attribute Ixy : Real = -3344.366268096465;
                            attribute sigma_Ixy : Real = 3570.139970140082;
                            attribute Ixz : Real = -70.42596874063342;
                            attribute sigma_Ixz : Real = 1203.750985907872;
                            attribute Iyz : Real = 93.45427948548365;
                            attribute sigma_Iyz : Real = 1228.4503745199943;
                            part <'C.1.2.3.4.2.2.1'> 'Part 1219' {
                                attribute POIconv : String = "+";
                                attribute Ipoint : Boolean = false;
                                attribute mass : Real = 0.7624184520461131;
                                attribute sigma_mass : Real = 0.28909372274994966;
                                attribute Cx : Real = -71.00615780800581;
                                attribute sigma_Cx : Real = 28.721044428837228;
                                attribute Cy : Real = -55.46005740761757;
                                attribute sigma_Cy : Real = 28.23690002309109;
                                attribute Cz : Real = -22.927511716261506;
                                attribute sigma_Cz : Real = 29.057750463592832;
                                attribute Ixx : Real = 1.0095357094737216;
                                attribute sigma_Ixx : Real = 0.37074144170588635;
                                attribute Iyy : Real = 1.1377047745366777;
                                attribute sigma_Iyy : Real = 0.3723953238821935;
                                attribute Izz : Real = 1.0601915514187823;
                                attribute sigma_Izz : Real = 0.37017423652493897;
                                attribute Ixy : Real = 0.02556427045370066;
                                attribute sigma_Ixy : Real = 0.02351283871158888;
                                attribute Ixz : Real = 0.006520758893302737;
                                attribute sigma_Ixz : Real = 0.022566176940390956;
                                attribute Iyz : Real = 0.038324921894748065;
                                attribute sigma_Iyz : Real = 0.02209918015384651;
                            }
                            part <'C.1.2.3.4.2.2.2'> 'Part 1220' {
                                attribute POIconv : String = "-";
                                attribute Ipoint : Boolean = false;
                                attribute mass : Real = 0.14356255016545766;
                                attribute sigma_mass : Real = 0.28909372274994966;
                                attribute Cx : Real = 88.90291755087674;
                                attribute sigma_Cx : Real = 28.721044428837228;
                                attribute Cy : Real = 57.48446565121412;
                                attribute sigma_Cy : Real = 28.23690002309109;
                                attribute Cz : Real = -17.33270059339702;
                                attribute sigma_Cz : Real = 29.057750463592832;
                                attribute Ixx : Real = 0.13944234729379065;
                                attribute sigma_Ixx : Real = 0.37074144170588635;
                                attribute Iyy : Real = 0.16751054277071004;
                                attribute sigma_Iyy : Real = 0.3723953238821935;
                                attribute Izz : Real = 0.1698670173879568;
                                attribute sigma_Izz : Real = 0.37017423652493897;
                                attribute Ixy : Real = 0.014379577080152263;
                                attribute sigma_Ixy : Real = 0.02351283871158888;
                                attribute Ixz : Real = 0.006816857611360043;
                                attribute sigma_Ixz : Real = 0.022566176940390956;
                                attribute Iyz : Real = -0.0026793842114052387;
                                attribute sigma_Iyz : Real = 0.02209918015384651;
                            }
                            part <'C.1.2.3.4.2.2.3'> 'Part 1221' {
                                attribute POIconv : String = "+";
                                attribute Ipoint : Boolean = false;
                                attribute mass : Real = 0.020360782307572663;
                                attribute sigma_mass : Real = 0.28909372274994966;
                                attribute Cx : Real = 93.1681405287236;
                                attribute sigma_Cx : Real = 28.721044428837228;
                                attribute Cy : Real = -56.24124030582607;
                                attribute sigma_Cy : Real = 28.23690002309109;
                                attribute Cz : Real = -12.299714935943484;
                                attribute sigma_Cz : Real = 29.057750463592832;
                                attribute Ixx : Real = 0.021332907875465813;
                                attribute sigma_Ixx : Real = 0.37074144170588635;
                                attribute Iyy : Real = 0.02227305120744767;
                                attribute sigma_Iyy : Real = 0.3723953238821935;
                                attribute Izz : Real = 0.021259712341645094;
                                attribute sigma_Izz : Real = 0.37017423652493897;
                                attribute Ixy : Real = -0.0003766152262650409;
                                attribute sigma_Ixy : Real = 0.02351283871158888;
                                attribute Ixz : Real = -0.0022143657647772422;
                                attribute sigma_Ixz : Real = 0.022566176940390956;
                                attribute Iyz : Real = 0.0004996824690278931;
                                attribute sigma_Iyz : Real = 0.02209918015384651;
                            }
                            part <'C.1.2.3.4.2.2.4'> 'Part 1222' {
                                attribute POIconv : String = "+";
                                attribute Ipoint : Boolean = false;
                                attribute mass : Real = 0.12226045999093912;
                                attribute sigma_mass : Real = 0.28909372274994966;
                                attribute Cx : Real = 18.275998765602708;
                                attribute sigma_Cx : Real = 28.721044428837228;
                                attribute Cy : Real = 99.76903623901308;
                                attribute sigma_Cy : Real = 28.23690002309109;
                                attribute Cz : Real = -35.02549366094172;
                                attribute sigma_Cz : Real = 29.057750463592832;
                                attribute Ixx : Real = 0.15440117370761738;
                                attribute sigma_Ixx : Real = 0.37074144170588635;
                                attribute Iyy : Real = 0.17499414128639668;
                                attribute sigma_Iyy : Real = 0.3723953238821935;
                                attribute Izz : Real = 0.17801505497646525;
                                attribute sigma_Izz : Real = 0.37017423652493897;
                                attribute Ixy : Real = 0.005247241173813501;
                                attribute sigma_Ixy : Real = 0.02351283871158888;
                                attribute Ixz : Real = 0.00015115575163074472;
                                attribute sigma_Ixz : Real = 0.022566176940390956;
                                attribute Iyz : Real = -1.3542479617262708e-05;
                                attribute sigma_Iyz : Real = 0.02209918015384651;
                            }
                            part <'C.1.2.3.4.2.2.5'> 'Part 1223' {
                                attribute POIconv : String = "-";
                                attribute Ipoint : Boolean = false;
                                attribute mass : Real = 0.4497093737798277;
                                attribute sigma_mass : Real = 0.28909372274994966;
                                attribute Cx : Real = -8.599200425669551;
                                attribute sigma_Cx : Real = 28.721044428837228;
                                attribute Cy : Real = 14.461542945355177;
                                attribute sigma_Cy : Real = 28.23690002309109;
                                attribute Cz : Real = -20.737309753894806;
                                attribute sigma_Cz : Real = 29.057750463592832;
                                attribute Ixx : Real = 0.5709853260537264;
                                attribute sigma_Ixx : Real = 0.37074144170588635;
                                attribute Iyy : Real = 0.5260483799173741;
                                attribute sigma_Iyy : Real = 0.3723953238821935;
                                attribute Izz : Real = 0.4750191227716839;
                                attribute sigma_Izz : Real = 0.37017423652493897;
                                attribute Ixy : Real = 0.03167733982626806;
                                attribute sigma_Ixy : Real = 0.02351283871158888;
                                attribute Ixz : Real = 0.05429001158268744;
                                attribute sigma_Ixz : Real = 0.022566176940390956;
                                attribute Iyz : Real = -0.04972857273891146;
                                attribute sigma_Iyz : Real = 0.02209918015384651;
                            }
                        }
                        part <'C.1.2.3.4.2.3'> 'Subassembly 345' {
                            attribute POIconv : String = "-";
                            attribute Ipoint : Boolean = false;
                            attribute mass : Real = 1.256499112235848;
                            attribute sigma_mass : Real = 0.40884026350990615;
                            attribute Cx : Real = -28.82052482645744;
                            attribute sigma_Cx : Real = 21.59471578398693;
                            attribute Cy : Real = -26.199047081556603;
                            attribute sigma_Cy : Real = 22.91331827146485;
                            attribute Cz : Real = 76.0698270587101;
                            attribute sigma_Cz : Real = 21.80954016747912;
                            attribute Ixx : Real = 777.3779880684085;
                            attribute sigma_Ixx : Real = 1231.020657496452;
                            attribute Iyy : Real = 83.54401178642084;
                            attribute sigma_Iyy : Real = 391.3226085637128;
                            attribute Izz : Real = 791.9999523035907;
                            attribute sigma_Izz : Real = 1243.3211783771858;
                            attribute Ixy : Real = 189.3276813025771;
                            attribute sigma_Ixy : Real = 607.3295931471107;
                            attribute Ixz : Real = 40.36787385676786;
                            attribute sigma_Ixz : Real = 196.02929748956592;
                            attribute Iyz : Real = -158.423255941266;
                            attribute sigma_Iyz : Real = 606.5487666856868;
                            part <'C.1.2.3.4.2.3.1'> 'Part 1224' {
                                attribute POIconv : String = "-";
                                attribute Ipoint : Boolean = false;
                                attribute mass : Real = 0.84417522983253;
                                attribute sigma_mass : Real = 0.28909372274994966;
                                attribute Cx : Real = -24.486743193119764;
                                attribute sigma_Cx : Real = 28.721044428837228;
                                attribute Cy : Real = -43.18207474425435;
                                attribute sigma_Cy : Real = 28.23690002309109;
                                attribute Cz : Real = 72.44566157460213;
                                attribute sigma_Cz : Real = 29.057750463592832;
                                attribute Ixx : Real = 1.065894861419456;
                                attribute sigma_Ixx : Real = 0.37074144170588635;
                                attribute Iyy : Real = 0.8832950542897401;
                                attribute sigma_Iyy : Real = 0.3723953238821935;
                                attribute Izz : Real = 1.1219573249609962;
                                attribute sigma_Izz : Real = 0.37017423652493897;
                                attribute Ixy : Real = -0.015019019399915906;
                                attribute sigma_Ixy : Real = 0.02351283871158888;
                                attribute Ixz : Real = -0.04183599286311755;
                                attribute sigma_Ixz : Real = 0.022566176940390956;
                                attribute Iyz : Real = -0.0867870770375726;
                                attribute sigma_Iyz : Real = 0.02209918015384651;
                            }
                            part <'C.1.2.3.4.2.3.2'> 'Part 1225' {
                                attribute POIconv : String = "+";
                                attribute Ipoint : Boolean = false;
                                attribute mass : Real = 0.41232388240331785;
                                attribute sigma_mass : Real = 0.28909372274994966;
                                attribute Cx : Real = -37.69333395175636;
                                attribute sigma_Cx : Real = 28.721044428837228;
                                attribute Cy : Real = 8.571316441521049;
                                attribute sigma_Cy : Real = 28.23690002309109;
                                attribute Cz : Real = 83.48979679867625;
                                attribute sigma_Cz : Real = 29.057750463592832;
                                attribute Ixx : Real = 0.5530045015707653;
                                attribute sigma_Ixx : Real = 0.37074144170588635;
                                attribute Iyy : Real = 0.5560193317403082;
                                attribute sigma_Iyy : Real = 0.3723953238821935;
                                attribute Izz : Real = 0.5917422654359216;
                                attribute sigma_Izz : Real = 0.37017423652493897;
                                attribute Ixy : Real = -0.004414012317710063;
                                attribute sigma_Ixy : Real = 0.02351283871158888;
                                attribute Ixz : Real = -0.005060237547583198;
                                attribute sigma_Ixz : Real = 0.022566176940390956;
                                attribute Iyz : Real = 0.0005534629840237461;
                                attribute sigma_Iyz : Real = 0.02209918015384651;
                            }
                        }
                    }
                    part <'C.1.2.3.4.3'> 'Assembly 100' {
                        attribute POIconv : String = "-";
                        attribute Ipoint : Boolean = false;
                        attribute mass : Real = 4.723990909238346;
                        attribute sigma_mass : Real = 0.7648700959862226;
                        attribute Cx : Real = -22.088004929642143;
                        attribute sigma_Cx : Real = 15.368738506161124;
                        attribute Cy : Real = 4.386220615420559;
                        attribute sigma_Cy : Real = 15.96695688952877;
                        attribute Cz : Real = -5.592276926120654;
                        attribute sigma_Cz : Real = 15.266036886130117;
                        attribute Ixx : Real = 39192.255912441455;
                        attribute sigma_Ixx : Real = 11696.523753988276;
                        attribute Iyy : Real = 34790.928725812366;
                        attribute sigma_Iyy : Real = 11249.998875934516;
                        attribute Izz : Real = 42176.27372910047;
                        attribute sigma_Izz : Real = 12543.72151872759;
                        attribute Ixy : Real = 7548.065580255243;
                        attribute sigma_Ixy : Real = 5746.853435991742;
                        attribute Ixz : Real = 2936.192756786965;
                        attribute sigma_Ixz : Real = 5551.325038627188;
                        attribute Iyz : Real = 4941.61165076786;
                        attribute sigma_Iyz : Real = 5929.670184180172;
                        part <'C.1.2.3.4.3.1'> 'Subassembly 346' {
                            attribute POIconv : String = "-";
                            attribute Ipoint : Boolean = false;
                            attribute mass : Real = 2.387065225509228;
                            attribute sigma_mass : Real = 0.5007250159521434;
                            attribute Cx : Real = -22.64326565204128;
                            attribute sigma_Cx : Real = 23.86791245960752;
                            attribute Cy : Real = 2.734800946513343;
                            attribute sigma_Cy : Real = 20.4624162044351;
                            attribute Cz : Real = 42.31249276583046;
                            attribute sigma_Cz : Real = 18.025763231726543;
                            attribute Ixx : Real = 10215.471743204314;
                            attribute sigma_Ixx : Real = 5665.01293907542;
                            attribute Iyy : Real = 17887.34321101772;
                            attribute sigma_Iyy : Real = 8356.227635966452;
                            attribute Izz : Real = 23783.184933155448;
                            attribute sigma_Izz : Real = 9437.270549715608;
                            attribute Ixy : Real = 905.921257243358;
                            attribute sigma_Ixy : Real = 4190.434769907726;
                            attribute Ixz : Real = 5462.43219693744;
                            attribute sigma_Ixz : Real = 3773.21217007988;
                            attribute Iyz : Real = -1759.481262824642;
                            attribute sigma_Iyz : Real = 2686.2390463870543;
                            part <'C.1.2.3.4.3.1.1'> 'Part 1226' {
                                attribute POIconv : String = "+";
                                attribute Ipoint : Boolean = false;
                                attribute mass : Real = 0.8887760209697299;
                                attribute sigma_mass : Real = 0.28909372274994966;
                                attribute Cx : Real = -94.55333561636508;
                                attribute sigma_Cx : Real = 28.721044428837228;
                                attribute Cy : Real = -48.07567927055061;
                                attribute sigma_Cy : Real = 28.23690002309109;
                                attribute Cz : Real = 57.3687335010618;
                                attribute sigma_Cz : Real = 29.057750463592832;
                                attribute Ixx : Real = 0.9681078607984221;
                                attribute sigma_Ixx : Real = 0.37074144170588635;
                                attribute Iyy : Real = 1.1566886408285675;
                                attribute sigma_Iyy : Real = 0.3723953238821935;
                                attribute Izz : Real = 1.2213536333227448;
                                attribute sigma_Izz : Real = 0.37017423652493897;
                                attribute Ixy : Real = -0.05163081342588777;
                                attribute sigma_Ixy : Real = 0.02351283871158888;
                                attribute Ixz : Real = -0.002221971143847304;
                                attribute sigma_Ixz : Real = 0.022566176940390956;
                                attribute Iyz : Real = -0.03507299904897307;
                                attribute sigma_Iyz : Real = 0.02209918015384651;
                            }
                            part <'C.1.2.3.4.3.1.2'> 'Part 1227' {
                                attribute POIconv : String = "-";
                                attribute Ipoint : Boolean = false;
                                attribute mass : Real = 0.7454087423814927;
                                attribute sigma_mass : Real = 0.28909372274994966;
                                attribute Cx : Real = -55.25266686454415;
                                attribute sigma_Cx : Real = 28.721044428837228;
                                attribute Cy : Real = 87.32788013294339;
                                attribute sigma_Cy : Real = 28.23690002309109;
                                attribute Cz : Real = 68.57433654367924;
                                attribute sigma_Cz : Real = 29.057750463592832;
                                attribute Ixx : Real = 0.9078750677648647;
                                attribute sigma_Ixx : Real = 0.37074144170588635;
                                attribute Iyy : Real = 0.9632076687982218;
                                attribute sigma_Iyy : Real = 0.3723953238821935;
                                attribute Izz : Real = 0.9166185560589292;
                                attribute sigma_Izz : Real = 0.37017423652493897;
                                attribute Ixy : Real = -0.08312485854645174;
                                attribute sigma_Ixy : Real = 0.02351283871158888;
                                attribute Ixz : Real = -0.006210118563222998;
                                attribute sigma_Ixz : Real = 0.022566176940390956;
                                attribute Iyz : Real = -0.046088217079240434;
                                attribute sigma_Iyz : Real = 0.02209918015384651;
                            }
                            part <'C.1.2.3.4.3.1.3'> 'Part 1228' {
                                attribute POIconv : String = "+";
                                attribute Ipoint : Boolean = false;
                                attribute mass : Real = 0.7528804621580056;
                                attribute sigma_mass : Real = 0.28909372274994966;
                                attribute Cx : Real = 94.53241233713925;
                                attribute sigma_Cx : Real = 28.721044428837228;
                                attribute Cy : Real = -21.036946680396795;
                                attribute sigma_Cy : Real = 28.23690002309109;
                                attribute Cz : Real = -1.4626286923885345;
                                attribute sigma_Cz : Real = 29.057750463592832;
                                attribute Ixx : Real = 1.1623795318550816;
                                attribute sigma_Ixx : Real = 0.37074144170588635;
                                attribute Iyy : Real = 1.2200190900400096;
                                attribute sigma_Iyy : Real = 0.3723953238821935;
                                attribute Izz : Real = 1.1891856418239375;
                                attribute sigma_Izz : Real = 0.37017423652493897;
                                attribute Ixy : Real = 0.009139032848586894;
                                attribute sigma_Ixy : Real = 0.02351283871158888;
                                attribute Ixz : Real = 0.002468363796709512;
                                attribute sigma_Ixz : Real = 0.022566176940390956;
                                attribute Iyz : Real = -0.03659010146709007;
                                attribute sigma_Iyz : Real = 0.02209918015384651;
                            }
                        }
                        part <'C.1.2.3.4.3.2'> 'Subassembly 347' {
                            attribute POIconv : String = "-";
                            attribute Ipoint : Boolean = false;
                            attribute mass : Real = 2.3369256837291177;
                            attribute sigma_mass : Real = 0.5781874454998993;
                            attribute Cx : Real = -21.52083089806787;
                            attribute sigma_Cx : Real = 19.254960300988373;
                            attribute Cy : Real = 6.073072059528063;
                            attribute sigma_Cy : Real = 24.588657220172127;
                            attribute Cz : Real = -54.52485987638784;
                            attribute sigma_Cz : Real = 19.009675780651865;
                            attribute Ixx : Real = 17890.09801196607;
                            attribute sigma_Ixx : Real = 8093.888287181621;
                            attribute Iyy : Real = 5828.571253443852;
                            attribute sigma_Iyy : Real = 4194.579057275634;
                            attribute Izz : Real = 18378.441452188956;
                            attribute sigma_Izz : Real = 8259.09509851347;
                            attribute Ixy : Real = 6646.569012965272;
                            attribute sigma_Ixy : Real = 3930.670240667024;
                            attribute Ixz : Real = -2654.591885725723;
                            attribute sigma_Ixz : Real = 2069.0699053013063;
                            attribute Iyz : Real = 6319.355569990257;
                            attribute sigma_Iyz : Real = 3814.3698763740026;
                            part <'C.1.2.3.4.3.2.1'> 'Part 1229' {
                                attribute POIconv : String = "+";
                                attribute Ipoint : Boolean = false;
                                attribute mass : Real = 0.9425255339709111;
                                attribute sigma_mass : Real = 0.28909372274994966;
                                attribute Cx : Real = -36.0169883351773;
                                attribute sigma_Cx : Real = 28.721044428837228;
                                attribute Cy : Real = 62.73062382824719;
                                attribute sigma_Cy : Real = 28.23690002309109;
                                attribute Cz : Real = -82.23370020277798;
                                attribute sigma_Cz : Real = 29.057750463592832;
                                attribute Ixx : Real = 1.4166508101749156;
                                attribute sigma_Ixx : Real = 0.37074144170588635;
                                attribute Iyy : Real = 1.440371333419505;
                                attribute sigma_Iyy : Real = 0.3723953238821935;
                                attribute Izz : Real = 1.3544307702319267;
                                attribute sigma_Izz : Real = 0.37017423652493897;
                                attribute Ixy : Real = 0.014497383935852032;
                                attribute sigma_Ixy : Real = 0.02351283871158888;
                                attribute Ixz : Real = -0.0167696320586855;
                                attribute sigma_Ixz : Real = 0.022566176940390956;
                                attribute Iyz : Real = -0.019881132629455324;
                                attribute sigma_Iyz : Real = 0.02209918015384651;
                            }
                            part <'C.1.2.3.4.3.2.2'> 'Part 1230' {
                                attribute POIconv : String = "-";
                                attribute Ipoint : Boolean = false;
                                attribute mass : Real = 0.9229548323696944;
                                attribute sigma_mass : Real = 0.28909372274994966;
                                attribute Cx : Real = 20.20778814330697;
                                attribute sigma_Cx : Real = 28.721044428837228;
                                attribute Cy : Real = -92.37292567268014;
                                attribute sigma_Cy : Real = 28.23690002309109;
                                attribute Cz : Real = -13.204154325649142;
                                attribute sigma_Cz : Real = 29.057750463592832;
                                attribute Ixx : Real = 1.3288876260886053;
                                attribute sigma_Ixx : Real = 0.37074144170588635;
                                attribute Iyy : Real = 1.3289935895365619;
                                attribute sigma_Iyy : Real = 0.3723953238821935;
                                attribute Izz : Real = 1.3753190819520789;
                                attribute sigma_Izz : Real = 0.37017423652493897;
                                attribute Ixy : Real = 0.02210176413775327;
                                attribute sigma_Ixy : Real = 0.02351283871158888;
                                attribute Ixz : Real = -0.020497363215445624;
                                attribute sigma_Ixz : Real = 0.022566176940390956;
                                attribute Iyz : Real = -0.0422153746267752;
                                attribute sigma_Iyz : Real = 0.02209918015384651;
                            }
                            part <'C.1.2.3.4.3.2.3'> 'Part 1231' {
                                attribute POIconv : String = "+";
                                attribute Ipoint : Boolean = false;
                                attribute mass : Real = 0.02166795061598532;
                                attribute sigma_mass : Real = 0.28909372274994966;
                                attribute Cx : Real = -31.414156267419457;
                                attribute sigma_Cx : Real = 28.721044428837228;
                                attribute Cy : Real = -23.786183400079608;
                                attribute sigma_Cy : Real = 28.23690002309109;
                                attribute Cz : Real = -27.62659047730267;
                                attribute sigma_Cz : Real = 29.057750463592832;
                                attribute Ixx : Real = 0.027248941858548866;
                                attribute sigma_Ixx : Real = 0.37074144170588635;
                                attribute Iyy : Real = 0.02807880583631137;
                                attribute sigma_Iyy : Real = 0.3723953238821935;
                                attribute Izz : Real = 0.024251381342115255;
                                attribute sigma_Izz : Real = 0.37017423652493897;
                                attribute Ixy : Real = 0.0004164934185500108;
                                attribute sigma_Ixy : Real = 0.02351283871158888;
                                attribute Ixz : Real = -0.0020605139397297757;
                                attribute sigma_Ixz : Real = 0.022566176940390956;
                                attribute Iyz : Real = -0.0009501757923268289;
                                attribute sigma_Iyz : Real = 0.02209918015384651;
                            }
                            part <'C.1.2.3.4.3.2.4'> 'Part 1232' {
                                attribute POIconv : String = "+";
                                attribute Ipoint : Boolean = false;
                                attribute mass : Real = 0.4497773667725269;
                                attribute sigma_mass : Real = 0.28909372274994966;
                                attribute Cx : Real = -76.29518327303231;
                                attribute sigma_Cx : Real = 28.721044428837228;
                                attribute Cy : Real = 90.79723069444299;
                                attribute sigma_Cy : Real = 28.23690002309109;
                                attribute Cz : Real = -82.54691399633884;
                                attribute sigma_Cz : Real = 29.057750463592832;
                                attribute Ixx : Real = 0.5551721838350132;
                                attribute sigma_Ixx : Real = 0.37074144170588635;
                                attribute Iyy : Real = 0.6718741175144284;
                                attribute sigma_Iyy : Real = 0.3723953238821935;
                                attribute Izz : Real = 0.5437058027664015;
                                attribute sigma_Izz : Real = 0.37017423652493897;
                                attribute Ixy : Real = -0.05112265010763005;
                                attribute sigma_Ixy : Real = 0.02351283871158888;
                                attribute Ixz : Real = 0.0013925075738839372;
                                attribute sigma_Ixz : Real = 0.022566176940390956;
                                attribute Iyz : Real = -0.0031026503560824294;
                                attribute sigma_Iyz : Real = 0.02209918015384651;
                            }
                        }
                    }
                }
                part <'C.1.2.3.5'> 'Subsystem 27' {
                    attribute POIconv : String = "-";
                    attribute Ipoint : Boolean = false;
                    attribute mass : Real = 17.14329705919861;
                    attribute sigma_mass : Real = 1.7103015285819827;
                    attribute Cx : Real = -11.212983629804372;
                    attribute sigma_Cx : Real = 7.449711432265508;
                    attribute Cy : Real = -8.131463547254004;
                    attribute sigma_Cy : Real = 8.227318609587062;
                    attribute Cz : Real = -17.703412458715743;
                    attribute sigma_Cz : Real = 7.787448204186316;
                    attribute Ixx : Real = 108880.22867851518;
                    attribute sigma_Ixx : Real = 19962.149835449953;
                    attribute Iyy : Real = 81155.67703113279;
                    attribute sigma_Iyy : Real = 17054.481086831514;
                    attribute Izz : Real = 103951.23822434613;
                    attribute sigma_Izz : Real = 19287.67014573379;
                    attribute Ixy : Real = -11281.30560530797;
                    attribute sigma_Ixy : Real = 8558.02156826214;
                    attribute Ixz : Real = 6394.672383493447;
                    attribute sigma_Ixz : Real = 8221.289359458155;
                    attribute Iyz : Real = 4859.463521042942;
                    attribute sigma_Iyz : Real = 9211.890169720371;
                    part <'C.1.2.3.5.1'> 'Assembly 101' {
                        attribute POIconv : String = "-";
                        attribute Ipoint : Boolean = false;
                        attribute mass : Real = 6.898967222390463;
                        attribute sigma_mass : Real = 1.1196551737036593;
                        attribute Cx : Real = -10.652042879028334;
                        attribute sigma_Cx : Real = 11.348584343897054;
                        attribute Cy : Real = -33.91931885100988;
                        attribute sigma_Cy : Real = 13.264592535126082;
                        attribute Cz : Real = -7.381550565818802;
                        attribute sigma_Cz : Real = 12.630997877301537;
                        attribute Ixx : Real = 45505.79833316272;
                        attribute sigma_Ixx : Real = 13291.8878760016;
                        attribute Iyy : Real = 30785.689400169133;
                        attribute sigma_Iyy : Real = 10551.800137195398;
                        attribute Izz : Real = 39982.467855563584;
                        attribute sigma_Izz : Real = 11951.171882462431;
                        attribute Ixy : Real = 1045.6728897854816;
                        attribute sigma_Ixy : Real = 5377.014094233176;
                        attribute Ixz : Real = 6724.498449721683;
                        attribute sigma_Ixz : Real = 5004.1455407698595;
                        attribute Iyz : Real = -5305.964472569759;
                        attribute sigma_Iyz : Real = 6193.207745312579;
                        part <'C.1.2.3.5.1.1'> 'Subassembly 348' {
                            attribute POIconv : String = "-";
                            attribute Ipoint : Boolean = false;
                            attribute mass : Real = 1.8178348974084946;
                            attribute sigma_mass : Real = 0.5007250159521434;
                            attribute Cx : Real = -19.30743881899232;
                            attribute sigma_Cx : Real = 21.525563736237135;
                            attribute Cy : Real = -23.93156147058142;
                            attribute sigma_Cy : Real = 28.31961155253832;
                            attribute Cz : Real = -32.210448296638035;
                            attribute sigma_Cz : Real = 23.833169269344115;
                            attribute Ixx : Real = 13042.919774325632;
                            attribute sigma_Ixx : Real = 7466.20354621751;
                            attribute Iyy : Real = 6093.709359890806;
                            attribute sigma_Iyy : Real = 4561.359738102614;
                            attribute Izz : Real = 10439.490556032935;
                            attribute sigma_Izz : Real = 6706.874156318698;
                            attribute Ixy : Real = -3705.537627988303;
                            attribute sigma_Ixy : Real = 3123.295572444439;
                            attribute Ixz : Real = 127.88984343916098;
                            attribute sigma_Ixz : Real = 2233.1269180894587;
                            attribute Iyz : Real = 2157.1099146351626;
                            attribute sigma_Iyz : Real = 3573.8447782139206;
                            part <'C.1.2.3.5.1.1.1'> 'Part 1233' {
                                attribute POIconv : String = "+";
                                attribute Ipoint : Boolean = false;
                                attribute mass : Real = 0.22666995134670287;
                                attribute sigma_mass : Real = 0.28909372274994966;
                                attribute Cx : Real = 46.82083432562649;
                                attribute sigma_Cx : Real = 28.721044428837228;
                                attribute Cy : Real = 83.26813052408397;
                                attribute sigma_Cy : Real = 28.23690002309109;
                                attribute Cz : Real = 39.585072034969926;
                                attribute sigma_Cz : Real = 29.057750463592832;
                                attribute Ixx : Real = 0.3001066899636975;
                                attribute sigma_Ixx : Real = 0.37074144170588635;
                                attribute Iyy : Real = 0.33782805497635304;
                                attribute sigma_Iyy : Real = 0.3723953238821935;
                                attribute Izz : Real = 0.2760758527342382;
                                attribute sigma_Izz : Real = 0.37017423652493897;
                                attribute Ixy : Real = -0.006456171252190321;
                                attribute sigma_Ixy : Real = 0.02351283871158888;
                                attribute Ixz : Real = -0.011820872916293256;
                                attribute sigma_Ixz : Real = 0.022566176940390956;
                                attribute Iyz : Real = 0.006681835140664046;
                                attribute sigma_Iyz : Real = 0.02209918015384651;
                            }
                            part <'C.1.2.3.5.1.1.2'> 'Part 1234' {
                                attribute POIconv : String = "+";
                                attribute Ipoint : Boolean = false;
                                attribute mass : Real = 0.7957524172503035;
                                attribute sigma_mass : Real = 0.28909372274994966;
                                attribute Cx : Real = -48.327252035960555;
                                attribute sigma_Cx : Real = 28.721044428837228;
                                attribute Cy : Real = -99.13239404559135;
                                attribute sigma_Cy : Real = 28.23690002309109;
                                attribute Cz : Real = 1.0650597047060728;
                                attribute sigma_Cz : Real = 29.057750463592832;
                                attribute Ixx : Real = 1.0207718461420159;
                                attribute sigma_Ixx : Real = 0.37074144170588635;
                                attribute Iyy : Real = 1.0369276008840338;
                                attribute sigma_Iyy : Real = 0.3723953238821935;
                                attribute Izz : Real = 1.2135886026228058;
                                attribute sigma_Izz : Real = 0.37017423652493897;
                                attribute Ixy : Real = -0.0016952285537999532;
                                attribute sigma_Ixy : Real = 0.02351283871158888;
                                attribute Ixz : Real = -0.04848621631579215;
                                attribute sigma_Ixz : Real = 0.022566176940390956;
                                attribute Iyz : Real = -0.047769847241058414;
                                attribute sigma_Iyz : Real = 0.02209918015384651;
                            }
                            part <'C.1.2.3.5.1.1.3'> 'Part 1235' {
                                attribute POIconv : String = "+";
                                attribute Ipoint : Boolean = false;
                                attribute mass : Real = 0.7954125288114883;
                                attribute sigma_mass : Real = 0.28909372274994966;
                                attribute Cx : Real = -9.119902458041906;
                                attribute sigma_Cx : Real = 28.721044428837228;
                                attribute Cy : Real = 20.752541488036513;
                                attribute sigma_Cy : Real = 28.23690002309109;
                                attribute Cz : Real = -85.95985691063106;
                                attribute sigma_Cz : Real = 29.057750463592832;
                                attribute Ixx : Real = 1.02956872042714;
                                attribute sigma_Ixx : Real = 0.37074144170588635;
                                attribute Iyy : Real = 0.9809241146418645;
                                attribute sigma_Iyy : Real = 0.3723953238821935;
                                attribute Izz : Real = 0.9628925351956685;
                                attribute sigma_Izz : Real = 0.37017423652493897;
                                attribute Ixy : Real = 0.02808652490844335;
                                attribute sigma_Ixy : Real = 0.02351283871158888;
                                attribute Ixz : Real = -0.028776776377454537;
                                attribute sigma_Ixz : Real = 0.022566176940390956;
                                attribute Iyz : Real = 0.0006470697068030823;
                                attribute sigma_Iyz : Real = 0.02209918015384651;
                            }
                        }
                        part <'C.1.2.3.5.1.2'> 'Subassembly 349' {
                            attribute POIconv : String = "-";
                            attribute Ipoint : Boolean = false;
                            attribute mass : Real = 1.8079734581937084;
                            attribute sigma_mass : Real = 0.6464332159373649;
                            attribute Cx : Real = -18.777575918248772;
                            attribute sigma_Cx : Real = 24.213509296879536;
                            attribute Cy : Real = -35.42858593031538;
                            attribute sigma_Cy : Real = 26.493142846824107;
                            attribute Cz : Real = 23.288017550691308;
                            attribute sigma_Cz : Real = 28.362336875445457;
                            attribute Ixx : Real = 16398.38000574394;
                            attribute sigma_Ixx : Real = 8014.610700590063;
                            attribute Iyy : Real = 10138.931468116101;
                            attribute sigma_Iyy : Real = 6764.734522005486;
                            attribute Izz : Real = 13784.969571416843;
                            attribute sigma_Izz : Real = 7221.427811737076;
                            attribute Ixy : Real = 5311.484505971655;
                            attribute sigma_Ixy : Real = 3251.117924807097;
                            attribute Ixz : Real = 4385.7063343066075;
                            attribute sigma_Ixz : Real = 3286.760800927934;
                            attribute Iyz : Real = -5181.146452940692;
                            attribute sigma_Iyz : Real = 3578.6121237990606;
                            part <'C.1.2.3.5.1.2.1'> 'Part 1236' {
                                attribute POIconv : String = "-";
                                attribute Ipoint : Boolean = false;
                                attribute mass : Real = 0.028669977720361204;
                                attribute sigma_mass : Real = 0.28909372274994966;
                                attribute Cx : Real = 7.8325701877474785;
                                attribute sigma_Cx : Real = 28.721044428837228;
                                attribute Cy : Real = -30.79293561168015;
                                attribute sigma_Cy : Real = 28.23690002309109;
                                attribute Cz : Real = -27.09494512528181;
                                attribute sigma_Cz : Real = 29.057750463592832;
                                attribute Ixx : Real = 0.038764728341863675;
                                attribute sigma_Ixx : Real = 0.37074144170588635;
                                attribute Iyy : Real = 0.038298783306221294;
                                attribute sigma_Iyy : Real = 0.3723953238821935;
                                attribute Izz : Real = 0.037384705712386244;
                                attribute sigma_Izz : Real = 0.37017423652493897;
                                attribute Ixy : Real = 7.174932599655494e-05;
                                attribute sigma_Ixy : Real = 0.02351283871158888;
                                attribute Ixz : Real = -0.0011627568211055;
                                attribute sigma_Ixz : Real = 0.022566176940390956;
                                attribute Iyz : Real = 0.001549302083599849;
                                attribute sigma_Iyz : Real = 0.02209918015384651;
                            }
                            part <'C.1.2.3.5.1.2.2'> 'Part 1237' {
                                attribute POIconv : String = "+";
                                attribute Ipoint : Boolean = false;
                                attribute mass : Real = 0.09765278878458776;
                                attribute sigma_mass : Real = 0.28909372274994966;
                                attribute Cx : Real = 63.3061442989856;
                                attribute sigma_Cx : Real = 28.721044428837228;
                                attribute Cy : Real = -41.65270128287375;
                                attribute sigma_Cy : Real = 28.23690002309109;
                                attribute Cz : Real = -66.70942339114845;
                                attribute sigma_Cz : Real = 29.057750463592832;
                                attribute Ixx : Real = 0.1177821649008545;
                                attribute sigma_Ixx : Real = 0.37074144170588635;
                                attribute Iyy : Real = 0.10623754770298825;
                                attribute sigma_Iyy : Real = 0.3723953238821935;
                                attribute Izz : Real = 0.09981332575065407;
                                attribute sigma_Izz : Real = 0.37017423652493897;
                                attribute Ixy : Real = -0.002843364233600392;
                                attribute sigma_Ixy : Real = 0.02351283871158888;
                                attribute Ixz : Real = -0.0008723067838638854;
                                attribute sigma_Ixz : Real = 0.022566176940390956;
                                attribute Iyz : Real = -0.005602734921786284;
                                attribute sigma_Iyz : Real = 0.02209918015384651;
                            }
                            part <'C.1.2.3.5.1.2.3'> 'Part 1238' {
                                attribute POIconv : String = "+";
                                attribute Ipoint : Boolean = false;
                                attribute mass : Real = 0.46308294393727556;
                                attribute sigma_mass : Real = 0.28909372274994966;
                                attribute Cx : Real = 23.701453488320112;
                                attribute sigma_Cx : Real = 28.721044428837228;
                                attribute Cy : Real = -90.69789256900549;
                                attribute sigma_Cy : Real = 28.23690002309109;
                                attribute Cz : Real = -58.624538173899055;
                                attribute sigma_Cz : Real = 29.057750463592832;
                                attribute Ixx : Real = 0.49092931833873765;
                                attribute sigma_Ixx : Real = 0.37074144170588635;
                                attribute Iyy : Real = 0.5073879525343943;
                                attribute sigma_Iyy : Real = 0.3723953238821935;
                                attribute Izz : Real = 0.46441618652834865;
                                attribute sigma_Izz : Real = 0.37017423652493897;
                                attribute Ixy : Real = -0.007232296814225083;
                                attribute sigma_Ixy : Real = 0.02351283871158888;
                                attribute Ixz : Real = 0.05245730264999222;
                                attribute sigma_Ixz : Real = 0.022566176940390956;
                                attribute Iyz : Real = -0.016793137364945365;
                                attribute sigma_Iyz : Real = 0.02209918015384651;
                            }
                            part <'C.1.2.3.5.1.2.4'> 'Part 1239' {
                                attribute POIconv : String = "-";
                                attribute Ipoint : Boolean = false;
                                attribute mass : Real = 0.5503887898386456;
                                attribute sigma_mass : Real = 0.28909372274994966;
                                attribute Cx : Real = -81.84429737739265;
                                attribute sigma_Cx : Real = 28.721044428837228;
                                attribute Cy : Real = 75.48872185871005;
                                attribute sigma_Cy : Real = 28.23690002309109;
                                attribute Cz : Real = 85.14078063890338;
                                attribute sigma_Cz : Real = 29.057750463592832;
                                attribute Ixx : Real = 0.5804846695536577;
                                attribute sigma_Ixx : Real = 0.37074144170588635;
                                attribute Iyy : Real = 0.623510434223508;
                                attribute sigma_Iyy : Real = 0.3723953238821935;
                                attribute Izz : Real = 0.5971426047870412;
                                attribute sigma_Izz : Real = 0.37017423652493897;
                                attribute Ixy : Real = 0.038983880094853436;
                                attribute sigma_Ixy : Real = 0.02351283871158888;
                                attribute Ixz : Real = -0.017644884867001318;
                                attribute sigma_Ixz : Real = 0.022566176940390956;
                                attribute Iyz : Real = -0.028764995279669227;
                                attribute sigma_Iyz : Real = 0.02209918015384651;
                            }
                            part <'C.1.2.3.5.1.2.5'> 'Part 1240' {
                                attribute POIconv : String = "-";
                                attribute Ipoint : Boolean = false;
                                attribute mass : Real = 0.6681789579128381;
                                attribute sigma_mass : Real = 0.28909372274994966;
                                attribute Cx : Real = -9.4069036655128;
                                attribute sigma_Cx : Real = 28.721044428837228;
                                attribute Cy : Real = -87.77754264883697;
                                attribute sigma_Cy : Real = 28.23690002309109;
                                attribute Cz : Real = 44.423402566462755;
                                attribute sigma_Cz : Real = 29.057750463592832;
                                attribute Ixx : Real = 0.8602232134964805;
                                attribute sigma_Ixx : Real = 0.37074144170588635;
                                attribute Iyy : Real = 0.9943086804372709;
                                attribute sigma_Iyy : Real = 0.3723953238821935;
                                attribute Izz : Real = 0.7938467565876774;
                                attribute sigma_Izz : Real = 0.37017423652493897;
                                attribute Ixy : Real = 0.014941206709004678;
                                attribute sigma_Ixy : Real = 0.02351283871158888;
                                attribute Ixz : Real = -0.031483272468263074;
                                attribute sigma_Ixz : Real = 0.022566176940390956;
                                attribute Iyz : Real = 0.0371749812087482;
                                attribute sigma_Iyz : Real = 0.02209918015384651;
                            }
                        }
                        part <'C.1.2.3.5.1.3'> 'Subassembly 350' {
                            attribute POIconv : String = "-";
                            attribute Ipoint : Boolean = false;
                            attribute mass : Real = 1.1923265313031153;
                            attribute sigma_mass : Real = 0.5007250159521434;
                            attribute Cx : Real = -28.66138557345014;
                            attribute sigma_Cx : Real = 20.502762475147314;
                            attribute Cy : Real = -15.130838024062248;
                            attribute sigma_Cy : Real = 31.07271620773676;
                            attribute Cz : Real = 12.171276907518521;
                            attribute sigma_Cz : Real = 24.30281746810332;
                            attribute Ixx : Real = 6956.297603409481;
                            attribute sigma_Ixx : Real = 4218.258340606512;
                            attribute Iyy : Real = 2859.829166731788;
                            attribute sigma_Iyy : Real = 2346.306919176377;
                            attribute Izz : Real = 5908.405267492784;
                            attribute sigma_Izz : Real = 3854.939119307428;
                            attribute Ixy : Real = -1893.7686295038184;
                            attribute sigma_Ixy : Real = 1692.3757079164986;
                            attribute Ixz : Real = 116.98484455643074;
                            attribute sigma_Ixz : Real = 1090.6724804764756;
                            attribute Iyz : Real = -1175.287574155041;
                            attribute sigma_Iyz : Real = 1897.853788402806;
                            part <'C.1.2.3.5.1.3.1'> 'Part 1241' {
                                attribute POIconv : String = "-";
                                attribute Ipoint : Boolean = false;
                                attribute mass : Real = 0.4524043802027591;
                                attribute sigma_mass : Real = 0.28909372274994966;
                                attribute Cx : Real = -61.25743710435927;
                                attribute sigma_Cx : Real = 28.721044428837228;
                                attribute Cy : Real = -97.67109882086515;
                                attribute sigma_Cy : Real = 28.23690002309109;
                                attribute Cz : Real = -3.21130333468318;
                                attribute sigma_Cz : Real = 29.057750463592832;
                                attribute Ixx : Real = 0.5669003066787957;
                                attribute sigma_Ixx : Real = 0.37074144170588635;
                                attribute Iyy : Real = 0.5355483741996078;
                                attribute sigma_Iyy : Real = 0.3723953238821935;
                                attribute Izz : Real = 0.5607491378991943;
                                attribute sigma_Izz : Real = 0.37017423652493897;
                                attribute Ixy : Real = 0.031807412311889764;
                                attribute sigma_Ixy : Real = 0.02351283871158888;
                                attribute Ixz : Real = 0.011423964063863649;
                                attribute sigma_Ixz : Real = 0.022566176940390956;
                                attribute Iyz : Real = 0.010511086375891064;
                                attribute sigma_Iyz : Real = 0.02209918015384651;
                            }
                            part <'C.1.2.3.5.1.3.2'> 'Part 1242' {
                                attribute POIconv : String = "-";
                                attribute Ipoint : Boolean = false;
                                attribute mass : Real = 0.42198422060185115;
                                attribute sigma_mass : Real = 0.28909372274994966;
                                attribute Cx : Real = -20.270169293507934;
                                attribute sigma_Cx : Real = 28.721044428837228;
                                attribute Cy : Real = 41.306568309664726;
                                attribute sigma_Cy : Real = 28.23690002309109;
                                attribute Cz : Real = 64.15808480232954;
                                attribute sigma_Cz : Real = 29.057750463592832;
                                attribute Ixx : Real = 0.49600471211019675;
                                attribute sigma_Ixx : Real = 0.37074144170588635;
                                attribute Iyy : Real = 0.46659338265001865;
                                attribute sigma_Iyy : Real = 0.3723953238821935;
                                attribute Izz : Real = 0.4304747934405064;
                                attribute sigma_Izz : Real = 0.37017423652493897;
                                attribute Ixy : Real = -0.026736246160264487;
                                attribute sigma_Ixy : Real = 0.02351283871158888;
                                attribute Ixz : Real = -0.021840414064926175;
                                attribute sigma_Ixz : Real = 0.022566176940390956;
                                attribute Iyz : Real = 0.0006159228948878891;
                                attribute sigma_Iyz : Real = 0.02209918015384651;
                            }
                            part <'C.1.2.3.5.1.3.3'> 'Part 1243' {
                                attribute POIconv : String = "+";
                                attribute Ipoint : Boolean = false;
                                attribute mass : Real = 0.317937930498505;
                                attribute sigma_mass : Real = 0.28909372274994966;
                                attribute Cx : Real = 6.58334163017571;
                                attribute sigma_Cx : Real = 28.721044428837228;
                                attribute Cy : Real = 27.41168146021664;
                                attribute sigma_Cy : Real = 28.23690002309109;
                                attribute Cz : Real = -34.940012730658054;
                                attribute sigma_Cz : Real = 29.057750463592832;
                                attribute Ixx : Real = 0.35929360465398785;
                                attribute sigma_Ixx : Real = 0.37074144170588635;
                                attribute Iyy : Real = 0.322735092206;
                                attribute sigma_Iyy : Real = 0.3723953238821935;
                                attribute Izz : Real = 0.37621190582861225;
                                attribute sigma_Izz : Real = 0.37017423652493897;
                                attribute Ixy : Real = 0.027161517331259592;
                                attribute sigma_Ixy : Real = 0.02351283871158888;
                                attribute Ixz : Real = -0.007271241202886192;
                                attribute sigma_Ixz : Real = 0.022566176940390956;
                                attribute Iyz : Real = 0.008641019117807451;
                                attribute sigma_Iyz : Real = 0.02209918015384651;
                            }
                        }
                        part <'C.1.2.3.5.1.4'> 'Subassembly 351' {
                            attribute POIconv : String = "-";
                            attribute Ipoint : Boolean = false;
                            attribute mass : Real = 2.0808323354851455;
                            attribute sigma_mass : Real = 0.5781874454998993;
                            attribute Cx : Real = 14.288864218577883;
                            attribute sigma_Cx : Real = 20.098308526505612;
                            attribute Cy : Real = -52.099247440168334;
                            attribute sigma_Cy : Real = 20.57146727184692;
                            attribute Cz : Real = -23.54252747617454;
                            attribute sigma_Cz : Real = 18.715150044776756;
                            attribute Ixx : Real = 3993.532304651501;
                            attribute sigma_Ixx : Real = 3914.118412893321;
                            attribute Iyy : Real = 5935.993756725393;
                            attribute sigma_Iyy : Real = 3854.336526312853;
                            attribute Izz : Real = 6618.861191656667;
                            attribute sigma_Izz : Real = 4345.07379862734;
                            attribute Ixy : Real = -148.42578156998587;
                            attribute sigma_Ixy : Real = 1656.1652193523412;
                            attribute Ixz : Real = 775.4403225430805;
                            attribute sigma_Ixz : Real = 1725.5516288576982;
                            attribute Iyz : Real = -591.7423520008089;
                            attribute sigma_Iyz : Real = 1819.3539194595203;
                            part <'C.1.2.3.5.1.4.1'> 'Part 1244' {
                                attribute POIconv : String = "-";
                                attribute Ipoint : Boolean = false;
                                attribute mass : Real = 0.4470364071626682;
                                attribute sigma_mass : Real = 0.28909372274994966;
                                attribute Cx : Real = -27.962521743029356;
                                attribute sigma_Cx : Real = 28.721044428837228;
                                attribute Cy : Real = -86.31998859345913;
                                attribute sigma_Cy : Real = 28.23690002309109;
                                attribute Cz : Real = 9.86206135712564;
                                attribute sigma_Cz : Real = 29.057750463592832;
                                attribute Ixx : Real = 0.5680081333668138;
                                attribute sigma_Ixx : Real = 0.37074144170588635;
                                attribute Iyy : Real = 0.6240042609967352;
                                attribute sigma_Iyy : Real = 0.3723953238821935;
                                attribute Izz : Real = 0.5478544600513949;
                                attribute sigma_Izz : Real = 0.37017423652493897;
                                attribute Ixy : Real = 0.005604570655368566;
                                attribute sigma_Ixy : Real = 0.02351283871158888;
                                attribute Ixz : Real = 0.007457408282342681;
                                attribute sigma_Ixz : Real = 0.022566176940390956;
                                attribute Iyz : Real = 0.01745886173598111;
                                attribute sigma_Iyz : Real = 0.02209918015384651;
                            }
                            part <'C.1.2.3.5.1.4.2'> 'Part 1245' {
                                attribute POIconv : String = "+";
                                attribute Ipoint : Boolean = false;
                                attribute mass : Real = 0.5333260146111716;
                                attribute sigma_mass : Real = 0.28909372274994966;
                                attribute Cx : Real = 88.41905957087874;
                                attribute sigma_Cx : Real = 28.721044428837228;
                                attribute Cy : Real = -65.50305760465562;
                                attribute sigma_Cy : Real = 28.23690002309109;
                                attribute Cz : Real = -40.15970500186086;
                                attribute sigma_Cz : Real = 29.057750463592832;
                                attribute Ixx : Real = 0.7734150683740445;
                                attribute sigma_Ixx : Real = 0.37074144170588635;
                                attribute Iyy : Real = 0.6847862206467095;
                                attribute sigma_Iyy : Real = 0.3723953238821935;
                                attribute Izz : Real = 0.7274667406800986;
                                attribute sigma_Izz : Real = 0.37017423652493897;
                                attribute Ixy : Real = -0.01956274793327845;
                                attribute sigma_Ixy : Real = 0.02351283871158888;
                                attribute Ixz : Real = 0.07132569432285725;
                                attribute sigma_Ixz : Real = 0.022566176940390956;
                                attribute Iyz : Real = -0.008152531502002923;
                                attribute sigma_Iyz : Real = 0.02209918015384651;
                            }
                            part <'C.1.2.3.5.1.4.3'> 'Part 1246' {
                                attribute POIconv : String = "+";
                                attribute Ipoint : Boolean = false;
                                attribute mass : Real = 0.887260308253346;
                                attribute sigma_mass : Real = 0.28909372274994966;
                                attribute Cx : Real = -10.44005542062223;
                                attribute sigma_Cx : Real = 28.721044428837228;
                                attribute Cy : Real = -48.2870539650321;
                                attribute sigma_Cy : Real = 28.23690002309109;
                                attribute Cz : Real = -43.64437595941126;
                                attribute sigma_Cz : Real = 29.057750463592832;
                                attribute Ixx : Real = 1.3035226829313638;
                                attribute sigma_Ixx : Real = 0.37074144170588635;
                                attribute Iyy : Real = 1.3894795576716723;
                                attribute sigma_Iyy : Real = 0.3723953238821935;
                                attribute Izz : Real = 1.2572713525036767;
                                attribute sigma_Izz : Real = 0.37017423652493897;
                                attribute Ixy : Real = 0.015121147284160176;
                                attribute sigma_Ixy : Real = 0.02351283871158888;
                                attribute Ixz : Real = -0.007767246486558844;
                                attribute sigma_Ixz : Real = 0.022566176940390956;
                                attribute Iyz : Real = 0.04812820856883939;
                                attribute sigma_Iyz : Real = 0.02209918015384651;
                            }
                            part <'C.1.2.3.5.1.4.4'> 'Part 1247' {
                                attribute POIconv : String = "-";
                                attribute Ipoint : Boolean = false;
                                attribute mass : Real = 0.2132096054579597;
                                attribute sigma_mass : Real = 0.28909372274994966;
                                attribute Cx : Real = 20.354890124872327;
                                attribute sigma_Cx : Real = 28.721044428837228;
                                attribute Cy : Real = 37.31562593020499;
                                attribute sigma_Cy : Real = 28.23690002309109;
                                attribute Cz : Real = 31.637340923771262;
                                attribute sigma_Cz : Real = 29.057750463592832;
                                attribute Ixx : Real = 0.2404530294255714;
                                attribute sigma_Ixx : Real = 0.37074144170588635;
                                attribute Iyy : Real = 0.24095081871753804;
                                attribute sigma_Iyy : Real = 0.3723953238821935;
                                attribute Izz : Real = 0.2531414246098385;
                                attribute sigma_Izz : Real = 0.37017423652493897;
                                attribute Ixy : Real = -0.004698048216591972;
                                attribute sigma_Ixy : Real = 0.02351283871158888;
                                attribute Ixz : Real = 0.004672059347782935;
                                attribute sigma_Ixz : Real = 0.022566176940390956;
                                attribute Iyz : Real = 0.011519409308047391;
                                attribute sigma_Iyz : Real = 0.02209918015384651;
                            }
                        }
                    }
                    part <'C.1.2.3.5.2'> 'Assembly 102' {
                        attribute POIconv : String = "-";
                        attribute Ipoint : Boolean = false;
                        attribute mass : Real = 4.211869442117633;
                        attribute sigma_mass : Real = 0.7081321085790055;
                        attribute Cx : Real = 3.6154110864127635;
                        attribute sigma_Cx : Real = 14.800383277812871;
                        attribute Cy : Real = 21.78972678112239;
                        attribute sigma_Cy : Real = 15.236740023696619;
                        attribute Cz : Real = -15.141603380028643;
                        attribute sigma_Cz : Real = 14.056471645802866;
                        attribute Ixx : Real = 19971.83508448767;
                        attribute sigma_Ixx : Real = 7941.618782866414;
                        attribute Iyy : Real = 18404.770381052498;
                        attribute sigma_Iyy : Real = 7620.752207371995;
                        attribute Izz : Real = 23665.719498613806;
                        attribute sigma_Izz : Real = 8783.927882954911;
                        attribute Ixy : Real = -7404.314237027555;
                        attribute sigma_Ixy : Real = 4306.276779760647;
                        attribute Ixz : Real = 3694.8350725033374;
                        attribute sigma_Ixz : Real = 3729.996322377712;
                        attribute Iyz : Real = 6586.529076167617;
                        attribute sigma_Iyz : Real = 3865.191343264245;
                        part <'C.1.2.3.5.2.1'> 'Subassembly 352' {
                            attribute POIconv : String = "-";
                            attribute Ipoint : Boolean = false;
                            attribute mass : Real = 1.7402017343693879;
                            attribute sigma_mass : Real = 0.5007250159521434;
                            attribute Cx : Real = 21.17325137482041;
                            attribute sigma_Cx : Real = 20.763236810413556;
                            attribute Cy : Real = -5.346566803079962;
                            attribute sigma_Cy : Real = 22.36813702250115;
                            attribute Cz : Real = -3.7188847475218294;
                            attribute sigma_Cz : Real = 20.45027728944299;
                            attribute Ixx : Real = 6154.297363596639;
                            attribute sigma_Ixx : Real = 4058.0125856348022;
                            attribute Iyy : Real = 5745.355488592844;
                            attribute sigma_Iyy : Real = 4060.7337059818246;
                            attribute Izz : Real = 6646.768949406586;
                            attribute sigma_Izz : Real = 4222.685623129849;
                            attribute Ixy : Real = -2354.9401406434963;
                            attribute sigma_Ixy : Real = 2001.0434497879946;
                            attribute Ixz : Real = 2844.8989668052914;
                            attribute sigma_Ixz : Real = 2030.19266327793;
                            attribute Iyz : Real = 2376.381245811827;
                            attribute sigma_Iyz : Real = 1925.0087865726152;
                            part <'C.1.2.3.5.2.1.1'> 'Part 1248' {
                                attribute POIconv : String = "-";
                                attribute Ipoint : Boolean = false;
                                attribute mass : Real = 0.29437477652193045;
                                attribute sigma_mass : Real = 0.28909372274994966;
                                attribute Cx : Real = 14.658892247825861;
                                attribute sigma_Cx : Real = 28.721044428837228;
                                attribute Cy : Real = 59.79750747792423;
                                attribute sigma_Cy : Real = 28.23690002309109;
                                attribute Cz : Real = -6.9031111896038055;
                                attribute sigma_Cz : Real = 29.057750463592832;
                                attribute Ixx : Real = 0.3679380766441123;
                                attribute sigma_Ixx : Real = 0.37074144170588635;
                                attribute Iyy : Real = 0.31934331779487013;
                                attribute sigma_Iyy : Real = 0.3723953238821935;
                                attribute Izz : Real = 0.42167607734835183;
                                attribute sigma_Izz : Real = 0.37017423652493897;
                                attribute Ixy : Real = -0.005047470923799126;
                                attribute sigma_Ixy : Real = 0.02351283871158888;
                                attribute Ixz : Real = -0.01310841618579281;
                                attribute sigma_Ixz : Real = 0.022566176940390956;
                                attribute Iyz : Real = -0.017902217264677375;
                                attribute sigma_Iyz : Real = 0.02209918015384651;
                            }
                            part <'C.1.2.3.5.2.1.2'> 'Part 1249' {
                                attribute POIconv : String = "+";
                                attribute Ipoint : Boolean = false;
                                attribute mass : Real = 0.7738428878854029;
                                attribute sigma_mass : Real = 0.28909372274994966;
                                attribute Cx : Real = -20.669632637873292;
                                attribute sigma_Cx : Real = 28.721044428837228;
                                attribute Cy : Real = -53.4666140563786;
                                attribute sigma_Cy : Real = 28.23690002309109;
                                attribute Cz : Real = 36.612317990511656;
                                attribute sigma_Cz : Real = 29.057750463592832;
                                attribute Ixx : Real = 0.9762497857757203;
                                attribute sigma_Ixx : Real = 0.37074144170588635;
                                attribute Iyy : Real = 0.8357901172397927;
                                attribute sigma_Iyy : Real = 0.3723953238821935;
                                attribute Izz : Real = 1.057359780191937;
                                attribute sigma_Izz : Real = 0.37017423652493897;
                                attribute Ixy : Real = -0.051994891628190154;
                                attribute sigma_Ixy : Real = 0.02351283871158888;
                                attribute Ixz : Real = -0.008879176366365746;
                                attribute sigma_Ixz : Real = 0.022566176940390956;
                                attribute Iyz : Real = 0.052016808910468046;
                                attribute sigma_Iyz : Real = 0.02209918015384651;
                            }
                            part <'C.1.2.3.5.2.1.3'> 'Part 1250' {
                                attribute POIconv : String = "+";
                                attribute Ipoint : Boolean = false;
                                attribute mass : Real = 0.6719840699620545;
                                attribute sigma_mass : Real = 0.28909372274994966;
                                attribute Cx : Real = 72.21237975172698;
                                attribute sigma_Cx : Real = 28.721044428837228;
                                attribute Cy : Real = 21.529939398169518;
                                attribute sigma_Cy : Real = 28.23690002309109;
                                attribute Cz : Real = -48.76855155453086;
                                attribute sigma_Cz : Real = 29.057750463592832;
                                attribute Ixx : Real = 0.936002883890469;
                                attribute sigma_Ixx : Real = 0.37074144170588635;
                                attribute Iyy : Real = 0.8341371909865365;
                                attribute sigma_Iyy : Real = 0.3723953238821935;
                                attribute Izz : Real = 0.897219455667445;
                                attribute sigma_Izz : Real = 0.37017423652493897;
                                attribute Ixy : Real = -0.003378685298492448;
                                attribute sigma_Ixy : Real = 0.02351283871158888;
                                attribute Ixz : Real = -0.0023557849089775726;
                                attribute sigma_Ixz : Real = 0.022566176940390956;
                                attribute Iyz : Real = 0.06268085830089416;
                                attribute sigma_Iyz : Real = 0.02209918015384651;
                            }
                        }
                        part <'C.1.2.3.5.2.2'> 'Subassembly 353' {
                            attribute POIconv : String = "-";
                            attribute Ipoint : Boolean = false;
                            attribute mass : Real = 2.4716677077482454;
                            attribute sigma_mass : Real = 0.5007250159521434;
                            attribute Cx : Real = -8.74635745791287;
                            attribute sigma_Cx : Real = 20.08630527080029;
                            attribute Cy : Real = 40.895298703897915;
                            attribute sigma_Cy : Real = 19.51736673551708;
                            attribute Cz : Real = -23.18387973990839;
                            attribute sigma_Cz : Real = 18.93228336851094;
                            attribute Ixx : Real = 11246.9534850104;
                            attribute sigma_Ixx : Real = 6105.643166515369;
                            attribute Iyy : Real = 11358.323700971412;
                            attribute sigma_Iyy : Real = 6097.72062190611;
                            attribute Izz : Real = 13921.119030567614;
                            attribute sigma_Izz : Real = 6928.79591044661;
                            attribute Ixy : Real = -6462.256569213655;
                            attribute sigma_Ixy : Real = 3432.9518896534623;
                            attribute Ixz : Real = 1444.673146622765;
                            attribute sigma_Ixz : Real = 2953.611479609217;
                            attribute Iyz : Real = 3290.959668097105;
                            attribute sigma_Iyz : Real = 3020.5834156128367;
                            part <'C.1.2.3.5.2.2.1'> 'Part 1251' {
                                attribute POIconv : String = "+";
                                attribute Ipoint : Boolean = false;
                                attribute mass : Real = 0.8867515277513303;
                                attribute sigma_mass : Real = 0.28909372274994966;
                                attribute Cx : Real = 10.376930655911565;
                                attribute sigma_Cx : Real = 28.721044428837228;
                                attribute Cy : Real = 83.76390621997416;
                                attribute sigma_Cy : Real = 28.23690002309109;
                                attribute Cz : Real = -79.20667519792914;
                                attribute sigma_Cz : Real = 29.057750463592832;
                                attribute Ixx : Real = 0.9303535111971629;
                                attribute sigma_Ixx : Real = 0.37074144170588635;
                                attribute Iyy : Real = 1.117018648060944;
                                attribute sigma_Iyy : Real = 0.3723953238821935;
                                attribute Izz : Real = 1.0119365011393968;
                                attribute sigma_Izz : Real = 0.37017423652493897;
                                attribute Ixy : Real = 0.06932017897973057;
                                attribute sigma_Ixy : Real = 0.02351283871158888;
                                attribute Ixz : Real = -0.12742892376013726;
                                attribute sigma_Ixz : Real = 0.022566176940390956;
                                attribute Iyz : Real = -0.027492673171577067;
                                attribute sigma_Iyz : Real = 0.02209918015384651;
                            }
                            part <'C.1.2.3.5.2.2.2'> 'Part 1252' {
                                attribute POIconv : String = "+";
                                attribute Ipoint : Boolean = false;
                                attribute mass : Real = 0.942455944892019;
                                attribute sigma_mass : Real = 0.28909372274994966;
                                attribute Cx : Real = -72.35633078962564;
                                attribute sigma_Cx : Real = 28.721044428837228;
                                attribute Cy : Real = -26.404158677905798;
                                attribute sigma_Cy : Real = 28.23690002309109;
                                attribute Cz : Real = 7.8602418303489685;
                                attribute sigma_Cz : Real = 29.057750463592832;
                                attribute Ixx : Real = 1.3336256706147664;
                                attribute sigma_Ixx : Real = 0.37074144170588635;
                                attribute Iyy : Real = 1.3748005075173215;
                                attribute sigma_Iyy : Real = 0.3723953238821935;
                                attribute Izz : Real = 1.325117687275256;
                                attribute sigma_Izz : Real = 0.37017423652493897;
                                attribute Ixy : Real = 0.05723250374521085;
                                attribute sigma_Ixy : Real = 0.02351283871158888;
                                attribute Ixz : Real = 0.03623217068390695;
                                attribute sigma_Ixz : Real = 0.022566176940390956;
                                attribute Iyz : Real = -0.05147582875410803;
                                attribute sigma_Iyz : Real = 0.02209918015384651;
                            }
                            part <'C.1.2.3.5.2.2.3'> 'Part 1253' {
                                attribute POIconv : String = "-";
                                attribute Ipoint : Boolean = false;
                                attribute mass : Real = 0.6424602351048961;
                                attribute sigma_mass : Real = 0.28909372274994966;
                                attribute Cx : Real = 58.17139125429094;
                                attribute sigma_Cx : Real = 28.721044428837228;
                                attribute Cy : Real = 80.45100830495358;
                                attribute sigma_Cy : Real = 28.23690002309109;
                                attribute Cz : Real = 8.601095294579864;
                                attribute sigma_Cz : Real = 29.057750463592832;
                                attribute Ixx : Real = 0.8101251969999419;
                                attribute sigma_Ixx : Real = 0.37074144170588635;
                                attribute Iyy : Real = 0.7620250017627846;
                                attribute sigma_Iyy : Real = 0.3723953238821935;
                                attribute Izz : Real = 0.7628121625498019;
                                attribute sigma_Izz : Real = 0.37017423652493897;
                                attribute Ixy : Real = -0.026948795968022937;
                                attribute sigma_Ixy : Real = 0.02351283871158888;
                                attribute Ixz : Real = -0.013666729350058542;
                                attribute sigma_Ixz : Real = 0.022566176940390956;
                                attribute Iyz : Real = -0.03666297346373025;
                                attribute sigma_Iyz : Real = 0.02209918015384651;
                            }
                        }
                    }
                    part <'C.1.2.3.5.3'> 'Assembly 103' {
                        attribute POIconv : String = "-";
                        attribute Ipoint : Boolean = false;
                        attribute mass : Real = 6.032460394690512;
                        attribute sigma_mass : Real = 1.081689663197327;
                        attribute Cx : Real = -22.207697244928447;
                        attribute sigma_Cx : Real = 12.885987369066326;
                        attribute Cy : Real = 0.46957448130110196;
                        attribute sigma_Cy : Real = 12.873776818400362;
                        attribute Cz : Real = -31.296571283325957;
                        attribute sigma_Cz : Real = 13.231752898556687;
                        attribute Ixx : Real = 32720.32279075709;
                        attribute sigma_Ixx : Real = 10519.721268155225;
                        attribute Iyy : Real = 28430.403589739908;
                        attribute sigma_Iyy : Real = 10339.500794889724;
                        attribute Izz : Real = 29840.5753096481;
                        attribute sigma_Izz : Real = 10278.437101852614;
                        attribute Ixy : Real = -3724.1905338447377;
                        attribute sigma_Ixy : Real = 4004.280123698427;
                        attribute Ixz : Real = -2923.1493541984687;
                        attribute sigma_Ixz : Real = 5026.924957760237;
                        attribute Iyz : Real = 1360.1039548030435;
                        attribute sigma_Iyz : Real = 4556.621865671962;
                        part <'C.1.2.3.5.3.1'> 'Subassembly 354' {
                            attribute POIconv : String = "-";
                            attribute Ipoint : Boolean = false;
                            attribute mass : Real = 1.5453536982573568;
                            attribute sigma_mass : Real = 0.5781874454998993;
                            attribute Cx : Real = -33.028331059959086;
                            attribute sigma_Cx : Real = 17.78192312751541;
                            attribute Cy : Real = -41.37068506888205;
                            attribute sigma_Cy : Real = 27.531645246622666;
                            attribute Cz : Real = -15.222569530568437;
                            attribute sigma_Cz : Real = 20.91213173707594;
                            attribute Ixx : Real = 7393.092636675257;
                            attribute sigma_Ixx : Real = 4900.927761698822;
                            attribute Iyy : Real = 2921.3953973744565;
                            attribute sigma_Iyy : Real = 2439.7580199752033;
                            attribute Izz : Real = 5995.177391861657;
                            attribute sigma_Izz : Real = 4418.087825272484;
                            attribute Ixy : Real = 601.881836700788;
                            attribute sigma_Ixy : Real = 1437.868182463138;
                            attribute Ixz : Real = 22.545615001849626;
                            attribute sigma_Ixz : Real = 1144.7639234795556;
                            attribute Iyz : Real = -940.6419756546269;
                            attribute sigma_Iyz : Real = 1821.964218897135;
                            part <'C.1.2.3.5.3.1.1'> 'Part 1254' {
                                attribute POIconv : String = "+";
                                attribute Ipoint : Boolean = false;
                                attribute mass : Real = 0.33016640045610257;
                                attribute sigma_mass : Real = 0.28909372274994966;
                                attribute Cx : Real = -35.44810418970883;
                                attribute sigma_Cx : Real = 28.721044428837228;
                                attribute Cy : Real = 65.93697317875922;
                                attribute sigma_Cy : Real = 28.23690002309109;
                                attribute Cz : Real = 14.03087368234992;
                                attribute sigma_Cz : Real = 29.057750463592832;
                                attribute Ixx : Real = 0.4841319693156862;
                                attribute sigma_Ixx : Real = 0.37074144170588635;
                                attribute Iyy : Real = 0.49410997565877923;
                                attribute sigma_Iyy : Real = 0.3723953238821935;
                                attribute Izz : Real = 0.5139325157423997;
                                attribute sigma_Izz : Real = 0.37017423652493897;
                                attribute Ixy : Real = -0.01368839964348144;
                                attribute sigma_Ixy : Real = 0.02351283871158888;
                                attribute Ixz : Real = 0.019441801700544624;
                                attribute sigma_Ixz : Real = 0.022566176940390956;
                                attribute Iyz : Real = 0.02784312114829495;
                                attribute sigma_Iyz : Real = 0.02209918015384651;
                            }
                            part <'C.1.2.3.5.3.1.2'> 'Part 1255' {
                                attribute POIconv : String = "-";
                                attribute Ipoint : Boolean = false;
                                attribute mass : Real = 0.602905201816;
                                attribute sigma_mass : Real = 0.28909372274994966;
                                attribute Cx : Real = -41.07709606178105;
                                attribute sigma_Cx : Real = 28.721044428837228;
                                attribute Cy : Real = -57.330096093937755;
                                attribute sigma_Cy : Real = 28.23690002309109;
                                attribute Cz : Real = -59.63577590882778;
                                attribute sigma_Cz : Real = 29.057750463592832;
                                attribute Ixx : Real = 0.867166398110262;
                                attribute sigma_Ixx : Real = 0.37074144170588635;
                                attribute Iyy : Real = 0.8600417004258021;
                                attribute sigma_Iyy : Real = 0.3723953238821935;
                                attribute Izz : Real = 0.8067052110298519;
                                attribute sigma_Izz : Real = 0.37017423652493897;
                                attribute Ixy : Real = 0.008920014766684324;
                                attribute sigma_Ixy : Real = 0.02351283871158888;
                                attribute Ixz : Real = 0.011488415818434811;
                                attribute sigma_Ixz : Real = 0.022566176940390956;
                                attribute Iyz : Real = 0.055085227572233525;
                                attribute sigma_Iyz : Real = 0.02209918015384651;
                            }
                            part <'C.1.2.3.5.3.1.3'> 'Part 1256' {
                                attribute POIconv : String = "-";
                                attribute Ipoint : Boolean = false;
                                attribute mass : Real = 0.2283896844435949;
                                attribute sigma_mass : Real = 0.28909372274994966;
                                attribute Cx : Real = -66.60578926093876;
                                attribute sigma_Cx : Real = 28.721044428837228;
                                attribute Cy : Real = -60.728950053453445;
                                attribute sigma_Cy : Real = 28.23690002309109;
                                attribute Cz : Real = 36.63800577633083;
                                attribute sigma_Cz : Real = 29.057750463592832;
                                attribute Ixx : Real = 0.25787027317159444;
                                attribute sigma_Ixx : Real = 0.37074144170588635;
                                attribute Iyy : Real = 0.24653307990206466;
                                attribute sigma_Iyy : Real = 0.3723953238821935;
                                attribute Izz : Real = 0.21522451145446275;
                                attribute sigma_Izz : Real = 0.37017423652493897;
                                attribute Ixy : Real = -0.004176609088616075;
                                attribute sigma_Ixy : Real = 0.02351283871158888;
                                attribute Ixz : Real = -0.0004126912672390296;
                                attribute sigma_Ixz : Real = 0.022566176940390956;
                                attribute Iyz : Real = 0.0021269974645339936;
                                attribute sigma_Iyz : Real = 0.02209918015384651;
                            }
                            part <'C.1.2.3.5.3.1.4'> 'Part 1257' {
                                attribute POIconv : String = "+";
                                attribute Ipoint : Boolean = false;
                                attribute mass : Real = 0.3838924115416594;
                                attribute sigma_mass : Real = 0.28909372274994966;
                                attribute Cx : Real = 1.6697112936526537;
                                attribute sigma_Cx : Real = 28.721044428837228;
                                attribute Cy : Real = -97.07937496714294;
                                attribute sigma_Cy : Real = 28.23690002309109;
                                attribute Cz : Real = -1.4842706732451916;
                                attribute sigma_Cz : Real = 29.057750463592832;
                                attribute Ixx : Real = 0.5868579035477605;
                                attribute sigma_Ixx : Real = 0.37074144170588635;
                                attribute Iyy : Real = 0.6083982273421362;
                                attribute sigma_Iyy : Real = 0.3723953238821935;
                                attribute Izz : Real = 0.5775773199641188;
                                attribute sigma_Izz : Real = 0.37017423652493897;
                                attribute Ixy : Real = 0.02605880122359817;
                                attribute sigma_Ixy : Real = 0.02351283871158888;
                                attribute Ixz : Real = 0.0030654902422688705;
                                attribute sigma_Ixz : Real = 0.022566176940390956;
                                attribute Iyz : Real = -0.007850604691216578;
                                attribute sigma_Iyz : Real = 0.02209918015384651;
                            }
                        }
                        part <'C.1.2.3.5.3.2'> 'Subassembly 355' {
                            attribute POIconv : String = "-";
                            attribute Ipoint : Boolean = false;
                            attribute mass : Real = 1.1871399216249119;
                            attribute sigma_mass : Real = 0.40884026350990615;
                            attribute Cx : Real = -25.76079316681858;
                            attribute sigma_Cx : Real = 21.71961268510551;
                            attribute Cy : Real = 48.71761130505844;
                            attribute sigma_Cy : Real = 21.182871470419467;
                            attribute Cz : Real = -57.83491937744587;
                            attribute sigma_Cz : Real = 22.09389219676332;
                            attribute Ixx : Real = 208.1036071963097;
                            attribute sigma_Ixx : Real = 611.8283993529893;
                            attribute Iyy : Real = 269.9997782889854;
                            attribute sigma_Iyy : Real = 701.8954714863926;
                            attribute Izz : Real = 163.1499980995095;
                            attribute sigma_Izz : Real = 534.2110679184101;
                            attribute Ixy : Real = -74.6191161842923;
                            attribute sigma_Ixy : Real = 264.9563320540363;
                            attribute Ixz : Real = 132.47425542468537;
                            attribute sigma_Ixz : Real = 350.1081598513761;
                            attribute Iyz : Real = 88.4429945673379;
                            attribute sigma_Iyz : Real = 300.35098234599855;
                            part <'C.1.2.3.5.3.2.1'> 'Part 1258' {
                                attribute POIconv : String = "-";
                                attribute Ipoint : Boolean = false;
                                attribute mass : Real = 0.7904170762877911;
                                attribute sigma_mass : Real = 0.28909372274994966;
                                attribute Cx : Real = -18.88536843471229;
                                attribute sigma_Cx : Real = 28.721044428837228;
                                attribute Cy : Real = 53.307269886136055;
                                attribute sigma_Cy : Real = 28.23690002309109;
                                attribute Cz : Real = -65.97607689909637;
                                attribute sigma_Cz : Real = 29.057750463592832;
                                attribute Ixx : Real = 1.0564934970951025;
                                attribute sigma_Ixx : Real = 0.37074144170588635;
                                attribute Iyy : Real = 0.9080027013385203;
                                attribute sigma_Iyy : Real = 0.3723953238821935;
                                attribute Izz : Real = 1.054648457058773;
                                attribute sigma_Izz : Real = 0.37017423652493897;
                                attribute Ixy : Real = -0.0060826693920741585;
                                attribute sigma_Ixy : Real = 0.02351283871158888;
                                attribute Ixz : Real = 0.09063436123285354;
                                attribute sigma_Ixz : Real = 0.022566176940390956;
                                attribute Iyz : Real = 0.018272587087929896;
                                attribute sigma_Iyz : Real = 0.02209918015384651;
                            }
                            part <'C.1.2.3.5.3.2.2'> 'Part 1259' {
                                attribute POIconv : String = "-";
                                attribute Ipoint : Boolean = false;
                                attribute mass : Real = 0.3967228453371208;
                                attribute sigma_mass : Real = 0.28909372274994966;
                                attribute Cx : Real = -39.45915508083999;
                                attribute sigma_Cx : Real = 28.721044428837228;
                                attribute Cy : Real = 39.57333196885884;
                                attribute sigma_Cy : Real = 28.23690002309109;
                                attribute Cz : Real = -41.61475459113717;
                                attribute sigma_Cz : Real = 29.057750463592832;
                                attribute Ixx : Real = 0.46098099894650835;
                                attribute sigma_Ixx : Real = 0.37074144170588635;
                                attribute Iyy : Real = 0.5215819349007708;
                                attribute sigma_Iyy : Real = 0.3723953238821935;
                                attribute Izz : Real = 0.4648527426251887;
                                attribute sigma_Izz : Real = 0.37017423652493897;
                                attribute Ixy : Real = 0.023408180701812185;
                                attribute sigma_Ixy : Real = 0.02351283871158888;
                                attribute Ixz : Real = -0.006842838268444533;
                                attribute sigma_Ixz : Real = 0.022566176940390956;
                                attribute Iyz : Real = 0.04806855519917744;
                                attribute sigma_Iyz : Real = 0.02209918015384651;
                            }
                        }
                        part <'C.1.2.3.5.3.3'> 'Subassembly 356' {
                            attribute POIconv : String = "-";
                            attribute Ipoint : Boolean = false;
                            attribute mass : Real = 1.7445432037173305;
                            attribute sigma_mass : Real = 0.5007250159521434;
                            attribute Cx : Real = -24.879250735903295;
                            attribute sigma_Cx : Real = 26.347900031993554;
                            attribute Cy : Real = -11.627061050678748;
                            attribute sigma_Cy : Real = 19.783480028143572;
                            attribute Cz : Real = -10.29105502587315;
                            attribute sigma_Cz : Real = 23.06110591007381;
                            attribute Ixx : Real = 7770.094491838621;
                            attribute sigma_Ixx : Real = 4555.024932666035;
                            attribute Iyy : Real = 12508.337607647984;
                            attribute sigma_Iyy : Real = 6648.578770022206;
                            attribute Izz : Real = 9466.66500475186;
                            attribute sigma_Izz : Real = 5723.097865950139;
                            attribute Ixy : Real = -2170.072172679544;
                            attribute sigma_Ixy : Real = 2367.3060055734463;
                            attribute Ixz : Real = -3221.071851584651;
                            attribute sigma_Ixz : Real = 2942.5783664480196;
                            attribute Iyz : Real = 1604.954267475082;
                            attribute sigma_Iyz : Real = 2169.730216579338;
                            part <'C.1.2.3.5.3.3.1'> 'Part 1260' {
                                attribute POIconv : String = "+";
                                attribute Ipoint : Boolean = false;
                                attribute mass : Real = 0.7011275064474903;
                                attribute sigma_mass : Real = 0.28909372274994966;
                                attribute Cx : Real = -66.1839063744992;
                                attribute sigma_Cx : Real = 28.721044428837228;
                                attribute Cy : Real = 8.027808088809252;
                                attribute sigma_Cy : Real = 28.23690002309109;
                                attribute Cz : Real = -78.1874118372798;
                                attribute sigma_Cz : Real = 29.057750463592832;
                                attribute Ixx : Real = 0.8246837649337543;
                                attribute sigma_Ixx : Real = 0.37074144170588635;
                                attribute Iyy : Real = 0.8229540591235416;
                                attribute sigma_Iyy : Real = 0.3723953238821935;
                                attribute Izz : Real = 0.8000623016461933;
                                attribute sigma_Izz : Real = 0.37017423652493897;
                                attribute Ixy : Real = -0.0032319440869591825;
                                attribute sigma_Ixy : Real = 0.02351283871158888;
                                attribute Ixz : Real = 0.007726934799492403;
                                attribute sigma_Ixz : Real = 0.022566176940390956;
                                attribute Iyz : Real = -0.014373984120215306;
                                attribute sigma_Iyz : Real = 0.02209918015384651;
                            }
                            part <'C.1.2.3.5.3.3.2'> 'Part 1261' {
                                attribute POIconv : String = "-";
                                attribute Ipoint : Boolean = false;
                                attribute mass : Real = 0.6089722820075695;
                                attribute sigma_mass : Real = 0.28909372274994966;
                                attribute Cx : Real = -56.18304922245443;
                                attribute sigma_Cx : Real = 28.721044428837228;
                                attribute Cy : Real = -60.97481483593583;
                                attribute sigma_Cy : Real = 28.23690002309109;
                                attribute Cz : Real = 36.10155996866524;
                                attribute sigma_Cz : Real = 29.057750463592832;
                                attribute Ixx : Real = 0.7827329456311622;
                                attribute sigma_Ixx : Real = 0.37074144170588635;
                                attribute Iyy : Real = 0.8547375049333515;
                                attribute sigma_Iyy : Real = 0.3723953238821935;
                                attribute Izz : Real = 0.8269510657506963;
                                attribute sigma_Izz : Real = 0.37017423652493897;
                                attribute Ixy : Real = 0.0436862200873175;
                                attribute sigma_Ixy : Real = 0.02351283871158888;
                                attribute Ixz : Real = 0.011838626742432367;
                                attribute sigma_Ixz : Real = 0.022566176940390956;
                                attribute Iyz : Real = -0.07517959808866224;
                                attribute sigma_Iyz : Real = 0.02209918015384651;
                            }
                            part <'C.1.2.3.5.3.3.3'> 'Part 1262' {
                                attribute POIconv : String = "-";
                                attribute Ipoint : Boolean = false;
                                attribute mass : Real = 0.4344434152622707;
                                attribute sigma_mass : Real = 0.28909372274994966;
                                attribute Cx : Real = 85.65983013249934;
                                attribute sigma_Cx : Real = 28.721044428837228;
                                attribute Cy : Real = 25.82510020583868;
                                attribute sigma_Cy : Real = 28.23690002309109;
                                attribute Cz : Real = 34.25372582860291;
                                attribute sigma_Cz : Real = 29.057750463592832;
                                attribute Ixx : Real = 0.43072646685810545;
                                attribute sigma_Ixx : Real = 0.37074144170588635;
                                attribute Iyy : Real = 0.4666613761837854;
                                attribute sigma_Iyy : Real = 0.3723953238821935;
                                attribute Izz : Real = 0.4943183701840302;
                                attribute sigma_Izz : Real = 0.37017423652493897;
                                attribute Ixy : Real = -0.03311439435726936;
                                attribute sigma_Ixy : Real = 0.02351283871158888;
                                attribute Ixz : Real = -0.025238821831793795;
                                attribute sigma_Ixz : Real = 0.022566176940390956;
                                attribute Iyz : Real = -0.017855909603244017;
                                attribute sigma_Iyz : Real = 0.02209918015384651;
                            }
                        }
                        part <'C.1.2.3.5.3.4'> 'Subassembly 357' {
                            attribute POIconv : String = "-";
                            attribute Ipoint : Boolean = false;
                            attribute mass : Real = 0.31968369444529526;
                            attribute sigma_mass : Real = 0.40884026350990615;
                            attribute Cx : Real = 50.42275724313868;
                            attribute sigma_Cx : Real = 41.84485067966422;
                            attribute Cy : Real = 35.59254627180566;
                            attribute sigma_Cy : Real = 20.615376592227683;
                            attribute Cz : Real = -15.946734148900171;
                            attribute sigma_Cz : Real = 119.58093984250439;
                            attribute Ixx : Real = 2404.021026330085;
                            attribute sigma_Ixx : Real = 3969.825237119986;
                            attribute Iyy : Real = 2631.513894564346;
                            attribute sigma_Iyy : Real = 4330.697155392986;
                            attribute Izz : Real = 228.75165528440237;
                            attribute sigma_Izz : Real = 494.5464938713026;
                            attribute Ixy : Real = -10.125131666003181;
                            attribute sigma_Ixy : Real = 166.2436735201026;
                            attribute Ixz : Real = 740.1662502176662;
                            attribute sigma_Ixz : Real = 1305.9717004405677;
                            attribute Iyz : Real = 32.893961341425594;
                            attribute sigma_Iyz : Real = 539.2802648200485;
                            part <'C.1.2.3.5.3.4.1'> 'Part 1263' {
                                attribute POIconv : String = "-";
                                attribute Ipoint : Boolean = false;
                                attribute mass : Real = 0.12083789502293803;
                                attribute sigma_mass : Real = 0.28909372274994966;
                                attribute Cx : Real = 16.167417960241437;
                                attribute sigma_Cx : Real = 28.721044428837228;
                                attribute Cy : Real = 34.07032806426287;
                                attribute sigma_Cy : Real = 28.23690002309109;
                                attribute Cz : Real = 95.27612244710326;
                                attribute sigma_Cz : Real = 29.057750463592832;
                                attribute Ixx : Real = 0.16208459719037385;
                                attribute sigma_Ixx : Real = 0.37074144170588635;
                                attribute Iyy : Real = 0.1379671616600087;
                                attribute sigma_Iyy : Real = 0.3723953238821935;
                                attribute Izz : Real = 0.1608687897282162;
                                attribute sigma_Izz : Real = 0.37017423652493897;
                                attribute Ixy : Real = 0.007945272000720708;
                                attribute sigma_Ixy : Real = 0.02351283871158888;
                                attribute Ixz : Real = 0.0001940737438532174;
                                attribute sigma_Ixz : Real = 0.022566176940390956;
                                attribute Iyz : Real = -0.0005141544973517658;
                                attribute sigma_Iyz : Real = 0.02209918015384651;
                            }
                            part <'C.1.2.3.5.3.4.2'> 'Part 1264' {
                                attribute POIconv : String = "-";
                                attribute Ipoint : Boolean = false;
                                attribute mass : Real = 0.19884579942235722;
                                attribute sigma_mass : Real = 0.28909372274994966;
                                attribute Cx : Real = 71.2396068032831;
                                attribute sigma_Cx : Real = 28.721044428837228;
                                attribute Cy : Real = 36.51759293861687;
                                attribute sigma_Cy : Real = 28.23690002309109;
                                attribute Cz : Real = -83.5364740807563;
                                attribute sigma_Cz : Real = 29.057750463592832;
                                attribute Ixx : Real = 0.1789578156280865;
                                attribute sigma_Ixx : Real = 0.37074144170588635;
                                attribute Iyy : Real = 0.18341294754277443;
                                attribute sigma_Iyy : Real = 0.3723953238821935;
                                attribute Izz : Real = 0.17794810838382322;
                                attribute sigma_Izz : Real = 0.37017423652493897;
                                attribute Ixy : Real = -0.00300798546050413;
                                attribute sigma_Ixy : Real = 0.02351283871158888;
                                attribute Ixz : Real = -0.0006300995043304796;
                                attribute sigma_Ixz : Real = 0.022566176940390956;
                                attribute Iyz : Real = 0.0033925289272170645;
                                attribute sigma_Iyz : Real = 0.02209918015384651;
                            }
                        }
                        part <'C.1.2.3.5.3.5'> 'Subassembly 358' {
                            attribute POIconv : String = "-";
                            attribute Ipoint : Boolean = false;
                            attribute mass : Real = 1.2357398766456171;
                            attribute sigma_mass : Real = 0.5007250159521434;
                            attribute Cx : Real = -20.28043325607771;
                            attribute sigma_Cx : Real = 30.334982159821525;
                            attribute Cy : Real = 14.43342838599731;
                            attribute sigma_Cy : Real = 26.691315446444925;
                            attribute Cz : Real = -59.528571811132736;
                            attribute sigma_Cz : Real = 25.654827882043282;
                            attribute Ixx : Real = 5520.21653537311;
                            attribute sigma_Ixx : Real = 3924.7437558792462;
                            attribute Iyy : Real = 5134.425076163196;
                            attribute sigma_Iyy : Real = 4169.094152433814;
                            attribute Izz : Real = 5728.053441348747;
                            attribute sigma_Izz : Real = 4369.874131521334;
                            attribute Ixy : Real = -669.9800760520778;
                            attribute sigma_Ixy : Real = 1722.831148199917;
                            attribute Ixz : Real = -562.8410633731013;
                            attribute sigma_Ixz : Real = 1624.386952979338;
                            attribute Iyz : Real = -2742.992171535273;
                            attribute sigma_Iyz : Real = 1960.6594553578336;
                            part <'C.1.2.3.5.3.5.1'> 'Part 1265' {
                                attribute POIconv : String = "-";
                                attribute Ipoint : Boolean = false;
                                attribute mass : Real = 0.42090389098459857;
                                attribute sigma_mass : Real = 0.28909372274994966;
                                attribute Cx : Real = -6.534124352037907;
                                attribute sigma_Cx : Real = 28.721044428837228;
                                attribute Cy : Real = 83.6108683142811;
                                attribute sigma_Cy : Real = 28.23690002309109;
                                attribute Cz : Real = 2.581757726147771;
                                attribute sigma_Cz : Real = 29.057750463592832;
                                attribute Ixx : Real = 0.5046761020634841;
                                attribute sigma_Ixx : Real = 0.37074144170588635;
                                attribute Iyy : Real = 0.6031403992323359;
                                attribute sigma_Iyy : Real = 0.3723953238821935;
                                attribute Izz : Real = 0.5702913065379649;
                                attribute sigma_Izz : Real = 0.37017423652493897;
                                attribute Ixy : Real = -0.005545422399502046;
                                attribute sigma_Ixy : Real = 0.02351283871158888;
                                attribute Ixz : Real = -0.03195887161427102;
                                attribute sigma_Ixz : Real = 0.022566176940390956;
                                attribute Iyz : Real = 0.045982303943210553;
                                attribute sigma_Iyz : Real = 0.02209918015384651;
                            }
                            part <'C.1.2.3.5.3.5.2'> 'Part 1266' {
                                attribute POIconv : String = "-";
                                attribute Ipoint : Boolean = false;
                                attribute mass : Real = 0.6296246529894415;
                                attribute sigma_mass : Real = 0.28909372274994966;
                                attribute Cx : Real = -57.72018609568477;
                                attribute sigma_Cx : Real = 28.721044428837228;
                                attribute Cy : Real = -22.049976931884885;
                                attribute sigma_Cy : Real = 28.23690002309109;
                                attribute Cz : Real = -91.82306164875627;
                                attribute sigma_Cz : Real = 29.057750463592832;
                                attribute Ixx : Real = 0.6231644456469169;
                                attribute sigma_Ixx : Real = 0.37074144170588635;
                                attribute Iyy : Real = 0.6628805997296834;
                                attribute sigma_Iyy : Real = 0.3723953238821935;
                                attribute Izz : Real = 0.6527029964441059;
                                attribute sigma_Izz : Real = 0.37017423652493897;
                                attribute Ixy : Real = 0.052228824100441454;
                                attribute sigma_Ixy : Real = 0.02351283871158888;
                                attribute Ixz : Real = -0.046873321509659616;
                                attribute sigma_Ixz : Real = 0.022566176940390956;
                                attribute Iyz : Real = 0.028349500091427567;
                                attribute sigma_Iyz : Real = 0.02209918015384651;
                            }
                            part <'C.1.2.3.5.3.5.3'> 'Part 1267' {
                                attribute POIconv : String = "+";
                                attribute Ipoint : Boolean = false;
                                attribute mass : Real = 0.1852113326715771;
                                attribute sigma_mass : Real = 0.28909372274994966;
                                attribute Cx : Real = 75.75643570162356;
                                attribute sigma_Cx : Real = 28.721044428837228;
                                attribute Cy : Real = -18.75137803144753;
                                attribute sigma_Cy : Real = 28.23690002309109;
                                attribute Cz : Real = -90.89313428848982;
                                attribute sigma_Cz : Real = 29.057750463592832;
                                attribute Ixx : Real = 0.2560248456709822;
                                attribute sigma_Ixx : Real = 0.37074144170588635;
                                attribute Iyy : Real = 0.26465729564891216;
                                attribute sigma_Iyy : Real = 0.3723953238821935;
                                attribute Izz : Real = 0.25143480489790515;
                                attribute sigma_Izz : Real = 0.37017423652493897;
                                attribute Ixy : Real = 0.01376368747788926;
                                attribute sigma_Ixy : Real = 0.02351283871158888;
                                attribute Ixz : Real = 0.007029625680584375;
                                attribute sigma_Ixz : Real = 0.022566176940390956;
                                attribute Iyz : Real = -0.008164116654090416;
                                attribute sigma_Iyz : Real = 0.02209918015384651;
                            }
                        }
                    }
                }
            }
        }
    }
}
